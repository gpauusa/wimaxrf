-- 
--  $Id: pps.mib,v 1.13 2006/02/07 16:05:14 archy Exp $
--
-- pps-sentry.mib
--          This MIB file describes the objects that can be managed with
--          the Pigeon Point Systems IPM Sentry Shelf Manager 
--
-- History:
--   Feb 5, 2003 - Initial revision, ver. 0.5, Vyacheslav Vanyulin
--   Jul 1, 2003 - Added PTI subtrees (20, 21, 22)
--
-- Support:
--    E-mail: <support@pigeonpoint.com>
--
-- Copyright (c) 2003-2006 Pigeon Point Systems.
-- All rights reserved.
--   

PPS-SENTRY-MIB DEFINITIONS ::= BEGIN

IMPORTS
    OBJECT-TYPE,
    Counter, 
    enterprises,
    DisplayString
    FROM SNMPv2-SMI;

    MacAddress ::= OCTET STRING ( SIZE(6) )

    pps                 OBJECT IDENTIFIER ::= { enterprises 16394 }
    products            OBJECT IDENTIFIER ::= { pps 2 }
    chassis-management  OBJECT IDENTIFIER ::= { products 1 }
    ipm-sentry-shmm     OBJECT IDENTIFIER ::= { chassis-management 1 }

    -- ipm-controller      OBJECT IDENTIFIER ::= {ipm-sentry-shmm 1}

    ipm-controller OBJECT-TYPE
              SYNTAX  SEQUENCE OF Ipm-controller-entry
              ACCESS  not-accessible
              STATUS  mandatory
              DESCRIPTION
                      "A list of IPM Controllers"
              ::= { ipm-sentry-shmm 1 }

        ipm-controller-entry OBJECT-TYPE
              SYNTAX  Ipm-controller-entry
              ACCESS  not-accessible
              STATUS  mandatory
              DESCRIPTION
                      "An IPM Controller entry"
              INDEX   { ipm-controller-index }
              ::= { ipm-controller 1 }

        Ipm-controller-entry ::=
              SEQUENCE {
                  ipm-controller-index
                        INTEGER,
                  ipm-controller-sdr-version
                        INTEGER,
                  ipm-controller-picmg-version
                        INTEGER,
                  ipm-controller-slave-address
                        INTEGER,
                  ipm-controller-channel-number
                        INTEGER,
                  ipm-controller-power-state-notification
                        INTEGER,
                  ipm-controller-global-initialization
                        INTEGER,
                  ipm-controller-capabilities
                        INTEGER,
                  ipm-controller-id-string
                        DisplayString ( SIZE (0..255) ),
                  ipm-controller-maximum-fru
                        INTEGER,
                  ipm-controller-own-fru-id
                        INTEGER
              }

        ipm-controller-index OBJECT-TYPE
              SYNTAX  INTEGER
              ACCESS  read-only
              STATUS  mandatory
              DESCRIPTION
                      "index"
              ::= { ipm-controller-entry 1 }

        ipm-controller-sdr-version OBJECT-TYPE
              SYNTAX  INTEGER
              ACCESS  read-only
              STATUS  mandatory
              DESCRIPTION
                      ""
              ::= { ipm-controller-entry 2 }

        ipm-controller-picmg-version OBJECT-TYPE
              SYNTAX  INTEGER
              ACCESS  read-only
              STATUS  mandatory
              DESCRIPTION
                      ""
              ::= { ipm-controller-entry 3 }

        ipm-controller-slave-address OBJECT-TYPE
              SYNTAX  INTEGER
              ACCESS  read-only
              STATUS  mandatory
              DESCRIPTION
                      ""
              ::= { ipm-controller-entry 4 }

        ipm-controller-channel-number OBJECT-TYPE
              SYNTAX  INTEGER
              ACCESS  read-only
              STATUS  mandatory
              DESCRIPTION
                      ""
              ::= { ipm-controller-entry 5 }

        ipm-controller-power-state-notification OBJECT-TYPE
              SYNTAX  INTEGER
              ACCESS  read-only
              STATUS  mandatory
              DESCRIPTION
                      ""
              ::= { ipm-controller-entry 6 }

        ipm-controller-global-initialization OBJECT-TYPE
              SYNTAX  INTEGER
              ACCESS  read-only
              STATUS  mandatory
              DESCRIPTION
                      ""
              ::= { ipm-controller-entry 7 }

        ipm-controller-capabilities OBJECT-TYPE
              SYNTAX  INTEGER
              ACCESS  read-only
              STATUS  mandatory
              DESCRIPTION
                      ""
              ::= { ipm-controller-entry 8 }

        ipm-controller-id-string OBJECT-TYPE
              SYNTAX  DisplayString ( SIZE (0..255) )
              ACCESS  read-only
              STATUS  mandatory
              DESCRIPTION
                      ""
              ::= { ipm-controller-entry 9 }

        ipm-controller-maximum-fru OBJECT-TYPE
              SYNTAX  INTEGER
              ACCESS  read-only
              STATUS  mandatory
              DESCRIPTION
                      ""
              ::= { ipm-controller-entry 10 }

        ipm-controller-own-fru-id OBJECT-TYPE
              SYNTAX  INTEGER
              ACCESS  read-only
              STATUS  mandatory
              DESCRIPTION
                      ""
              ::= { ipm-controller-entry 11 }

    -- fru-device          OBJECT IDENTIFIER ::= {ipm-sentry-shmm 2}

    fru-device OBJECT-TYPE
              SYNTAX  SEQUENCE OF Fru-device-entry
              ACCESS  not-accessible
              STATUS  mandatory
              DESCRIPTION
                      "A list of IPM Controllers"
              ::= { ipm-sentry-shmm 2 }

        fru-device-entry OBJECT-TYPE
              SYNTAX  Fru-device-entry
              ACCESS  not-accessible
              STATUS  mandatory
              DESCRIPTION
                      "An IPM Controller entry"
              INDEX   { fru-device-index }
              ::= { fru-device 1 }

        Fru-device-entry ::=
              SEQUENCE {
                  fru-device-index
                        INTEGER,
                  fru-device-sdr-version
                        INTEGER,
                  fru-device-slave-address
                        INTEGER,
                  fru-device-fru-device-id
                        INTEGER,
                  fru-device-channel-number
                        INTEGER,
                  fru-device-device-type
                        INTEGER,
                  fru-device-device-type-modifier
                        INTEGER,
                  fru-device-fru-entity-id
                        INTEGER,
                  fru-device-fru-entity-instance
                        INTEGER,
                  fru-device-id-string
                        DisplayString ( SIZE (0..255) ),
                  fru-device-hot-swap-state
                        INTEGER,
                  fru-device-activated
                        INTEGER
              }

        fru-device-index OBJECT-TYPE
              SYNTAX  INTEGER
              ACCESS  read-only
              STATUS  mandatory
              DESCRIPTION
                      "index"
              ::= { fru-device-entry 1 }

        fru-device-sdr-version OBJECT-TYPE
              SYNTAX  INTEGER
              ACCESS  read-only
              STATUS  mandatory
              DESCRIPTION
                      ""
              ::= { fru-device-entry 2 }

        fru-device-slave-address OBJECT-TYPE
              SYNTAX  INTEGER
              ACCESS  read-only
              STATUS  mandatory
              DESCRIPTION
                      ""
              ::= { fru-device-entry 3 }

        fru-device-fru-device-id OBJECT-TYPE
              SYNTAX  INTEGER
              ACCESS  read-only
              STATUS  mandatory
              DESCRIPTION
                      ""
              ::= { fru-device-entry 4 }

        fru-device-channel-number OBJECT-TYPE
              SYNTAX  INTEGER
              ACCESS  read-only
              STATUS  mandatory
              DESCRIPTION
                      ""
              ::= { fru-device-entry 5 }

        fru-device-device-type OBJECT-TYPE
              SYNTAX  INTEGER
              ACCESS  read-only
              STATUS  mandatory
              DESCRIPTION
                      ""
              ::= { fru-device-entry 6 }

        fru-device-device-type-modifier OBJECT-TYPE
              SYNTAX  INTEGER
              ACCESS  read-only
              STATUS  mandatory
              DESCRIPTION
                      ""
              ::= { fru-device-entry 7 }

        fru-device-fru-entity-id OBJECT-TYPE
              SYNTAX  INTEGER
              ACCESS  read-only
              STATUS  mandatory
              DESCRIPTION
                      ""
              ::= { fru-device-entry 8 }

        fru-device-fru-entity-instance OBJECT-TYPE
              SYNTAX  INTEGER
              ACCESS  read-only
              STATUS  mandatory
              DESCRIPTION
                      ""
              ::= { fru-device-entry 9 }

        fru-device-id-string OBJECT-TYPE
              SYNTAX  DisplayString( SIZE(0..255) )
              ACCESS  read-only
              STATUS  mandatory
              DESCRIPTION
                      ""
              ::= { fru-device-entry 10 }

        fru-device-hot-swap-state OBJECT-TYPE
              SYNTAX  INTEGER {
                     M0 (0),
                     M1 (1),
                     M2 (2),
                     M3 (3),
                     M4 (4),
                     M5 (5),
                     M6 (6),
                     M7 (7)
                  }
              ACCESS  read-only
              STATUS  mandatory
              DESCRIPTION
                      ""
              ::= { fru-device-entry 11 }

        fru-device-activated OBJECT-TYPE
              SYNTAX  INTEGER
              ACCESS  read-write
              STATUS  mandatory
              DESCRIPTION
                      ""
              ::= { fru-device-entry 12 }

    -- sensor              OBJECT IDENTIFIER ::= {ipm-sentry-shmm 3}

    sensor OBJECT-TYPE
              SYNTAX  SEQUENCE OF Sensor-entry
              ACCESS  not-accessible
              STATUS  mandatory
              DESCRIPTION
                      "A list of IPM Controllers"
              ::= { ipm-sentry-shmm 3 }

        sensor-entry OBJECT-TYPE
              SYNTAX  Sensor-entry
              ACCESS  not-accessible
              STATUS  mandatory
              DESCRIPTION
                      "An IPM Controller entry"
              INDEX   { sensor-index }
              ::= { sensor 1 }

        Sensor-entry ::=
              SEQUENCE {
                  sensor-index
                        INTEGER,
                  sensor-sdr-version
                        INTEGER,
                  sensor-record-type
                        INTEGER,
                  sensor-owner-id
                        INTEGER,
                  sensor-owner-lun
                        INTEGER,
                  sensor-number
                        INTEGER,
                  sensor-entity-instance
                        INTEGER,
                  sensor-entity-id
                        INTEGER,
                  sensor-initialization
                        INTEGER,
                  sensor-capabilities
                        INTEGER,
                  sensor-type
                        INTEGER,
                  sensor-event
                        INTEGER,
                  sensor-assertion-event-mask
                        INTEGER,
                  sensor-deassertion-event-mask
                        INTEGER,
                  sensor-mask
                        INTEGER,
                  sensor-unit1
                        INTEGER,
                  sensor-unit2
                        INTEGER,
                  sensor-unit3
                        INTEGER,
                  sensor-linearization
                        INTEGER,
                  sensor-M
                        INTEGER,
                  sensor-tolerance
                        INTEGER,
                  sensor-B
                        INTEGER,
                  sensor-accuracy
                        INTEGER,
                  sensor-accuracy-exp
                        INTEGER,
                  sensor-R-exp
                        INTEGER,
                  sensor-B-exp
                        INTEGER,
                  sensor-characteristic-flags
                        INTEGER,
                  sensor-reading
                        INTEGER,
                  sensor-processed-reading
                        DisplayString,
                  sensor-nominal-reading
                        INTEGER,
                  sensor-nominal-maximum
                        INTEGER,
                  sensor-nominal-minimum
                        INTEGER,
                  sensor-maximum-reading
                        INTEGER,
                  sensor-minimum-reading
                        INTEGER,
                  sensor-upper-non-recoverable-threshold
                        INTEGER,
                  sensor-upper-critical-threshold
                        INTEGER,
                  sensor-upper-non-critical-threshold
                        INTEGER,
                  sensor-lower-non-recoverable-threshold
                        INTEGER,
                  sensor-lower-critical-threshold
                        INTEGER,
                  sensor-lower-non-critical-threshold
                        INTEGER,
                  sensor-positive-going-threshold-hysteresis
                        INTEGER,
                  sensor-negative-going-threshold-hysteresis
                        INTEGER,
                  sensor-id-string
                        DisplayString,
                  sensor-entire-sensor-data
                        OCTET STRING
              }

        sensor-index OBJECT-TYPE
              SYNTAX  INTEGER
              ACCESS  read-only
              STATUS  mandatory
              DESCRIPTION
                      "Index"
              ::= { sensor-entry 1 }

        sensor-sdr-version OBJECT-TYPE
              SYNTAX  INTEGER
              ACCESS  read-only
              STATUS  mandatory
              DESCRIPTION
                      ""
              ::= { sensor-entry 2 }

        sensor-record-type OBJECT-TYPE
              SYNTAX  INTEGER
              ACCESS  read-only
              STATUS  mandatory
              DESCRIPTION
                      ""
              ::= { sensor-entry 3 }

        sensor-owner-id OBJECT-TYPE
              SYNTAX  INTEGER
              ACCESS  read-only
              STATUS  mandatory
              DESCRIPTION
                      ""
              ::= { sensor-entry 4 }

        sensor-owner-lun OBJECT-TYPE
              SYNTAX  INTEGER
              ACCESS  read-only
              STATUS  mandatory
              DESCRIPTION
                      ""
              ::= { sensor-entry 5 }

        sensor-number OBJECT-TYPE
              SYNTAX  INTEGER
              ACCESS  read-only
              STATUS  mandatory
              DESCRIPTION
                      ""
              ::= { sensor-entry 6 }

        sensor-entity-instance OBJECT-TYPE
              SYNTAX  INTEGER
              ACCESS  read-only
              STATUS  mandatory
              DESCRIPTION
                      ""
              ::= { sensor-entry 7 }

        sensor-entity-id OBJECT-TYPE
              SYNTAX  INTEGER
              ACCESS  read-only
              STATUS  mandatory
              DESCRIPTION
                      ""
              ::= { sensor-entry 8 }

        sensor-initialization OBJECT-TYPE
              SYNTAX  INTEGER
              ACCESS  read-only
              STATUS  mandatory
              DESCRIPTION
                      ""
              ::= { sensor-entry 9 }

        sensor-capabilities OBJECT-TYPE
              SYNTAX  INTEGER
              ACCESS  read-only
              STATUS  mandatory
              DESCRIPTION
                      ""
              ::= { sensor-entry 10 }

        sensor-type OBJECT-TYPE
              SYNTAX  INTEGER {
                    reserved0(0),    
                    Temperature(1), 
                    Voltage(2),     
                    Current(3),
                    Fan(4), 
                    PhysicalSecurityChassisInrusion(5), 
                    PlatformSecurityViolationAttempt(6),
                    Processor(7),
                    PowerSupply(8),
                    PowerUnit(9),
                    CoolingDevice(10),
                    OtherUnitsBasedSensor(11),
                    Memory(12),
                    DriveSlotBay(13),
                    POSTMemoryResize(14),
                    SystemFirmwareProgressFormerlyPOSTError(15),
                    ErrorLoggingDisabled(16),
                    Watchdog1(17),
                    SystemEvent(18),
                    CriticalInterrupt(19),
                    Button(20),
                    ModuleOrBoard(21),
                    MicrocontrollerOrCoprocessor(22),
                    AddinCard(23),
                    Chassis(24),
                    ChipSet(25),
                    OtherFRU(26),
                    CableOrInterconnect(27),
                    Terminator(28),
                    SystemBootInitiated(29),
                    BootError(30),
                    OSBoot(31),
                    OSCriticalStop(32),
                    SlotOrConnector(33),
                    SystemACPIPowerState(34),
                    Watchdog2(35),
                    PlatformAlert(36),
                    EntityPresence(37),
                    MonitorASICOrIC(38),
                    LAN(39),
                    ManagementSubsystemHealth(40),
                    Battery(41),
                    reserved42(42),
                    reserved43(43),
                    reserved44(44),
                    reserved45(45),
                    reserved46(46),
                    reserved47(47),
                    reserved48(48),
                    reserved49(49),
                    reserved50(50),
                    reserved51(51),
                    reserved52(52),
                    reserved53(53),
                    reserved54(54),
                    reserved55(55),
                    reserved56(56),
                    reserved57(57),
                    reserved58(58),
                    reserved59(59),
                    reserved60(60),
                    reserved61(61),
                    reserved62(62),
                    reserved63(63),
                    reserved64(64),
                    reserved65(65),
                    reserved66(66),
                    reserved67(67),
                    reserved68(68),
                    reserved69(69),
                    reserved70(70),
                    reserved71(71),
                    reserved72(72),
                    reserved73(73),
                    reserved74(74),
                    reserved75(75),
                    reserved76(76),
                    reserved77(77),
                    reserved78(78),
                    reserved79(79),
                    reserved80(80),
                    reserved81(81),
                    reserved82(82),
                    reserved83(83),
                    reserved84(84),
                    reserved85(85),
                    reserved86(86),
                    reserved87(87),
                    reserved88(88),
                    reserved89(89),
                    reserved90(90),
                    reserved91(91),
                    reserved92(92),
                    reserved93(93),
                    reserved94(94),
                    reserved95(95),
                    reserved96(96),
                    reserved97(97),
                    reserved98(98),
                    reserved99(99),
                    reserved100(100),
                    reserved101(101),
                    reserved102(102),
                    reserved103(103),
                    reserved104(104),
                    reserved105(105),
                    reserved106(106),
                    reserved107(107),
                    reserved108(108),
                    reserved109(109),
                    reserved110(110),
                    reserved111(111),
                    reserved112(112),
                    reserved113(113),
                    reserved114(114),
                    reserved115(115),
                    reserved116(116),
                    reserved117(117),
                    reserved118(118),
                    reserved119(119),
                    reserved120(120),
                    reserved121(121),
                    reserved122(122),
                    reserved123(123),
                    reserved124(124),
                    reserved125(125),
                    reserved126(126),
                    reserved127(127),
                    reserved128(128),
                    reserved129(129),
                    reserved130(130),
                    reserved131(131),
                    reserved132(132),
                    reserved133(133),
                    reserved134(134),
                    reserved135(135),
                    reserved136(136),                                     -- 0x88
                    reserved137(137),                                     
                    reserved138(138),
                    reserved139(139),
                    reserved140(140),
                    reserved141(141),
                    reserved142(142),
                    reserved143(143),
                    reserved144(144),                                     -- 0x90
                    reserved145(145),                                         
                    reserved146(146),
                    reserved147(147),
                    reserved148(148),
                    reserved149(149),
                    reserved150(150),
                    reserved151(151),
                    reserved152(152),
                    reserved153(153),
                    reserved154(154),
                    reserved155(155),
                    reserved156(156),
                    reserved157(157),
                    reserved158(158),
                    reserved159(159),
                    reserved160(160),                                     -- 0xa0
                    reserved161(161),                                         
                    reserved162(162),
                    reserved163(163),
                    reserved164(164),
                    reserved165(165),
                    reserved166(166),
                    reserved167(167),
                    reserved168(168),
                    reserved169(169),
                    reserved170(170),
                    reserved171(171),
                    reserved172(172),
                    reserved173(173),
                    reserved174(174),
                    reserved175(175),
                    reserved176(176),                                     -- 0xb0
                    reserved177(177),
                    reserved178(178),
                    reserved179(179),
                    reserved180(180),
                    reserved181(181),
                    reserved182(182),
                    reserved183(183),
                    reserved184(184),
                    reserved185(185),
                    reserved186(186),
                    reserved187(187),
                    reserved188(188),
                    reserved189(189),
                    reserved190(190),
                    reserved191(191),
                    reserved192(192),                                     -- 0xc0
                    reserved193(193),
                    reserved194(194),
                    reserved195(195),
                    reserved196(196),
                    reserved197(197),
                    reserved198(198),
                    reserved199(199),
                    reserved200(200),
                    reserved201(201),
                    reserved202(202),
                    reserved203(203),
                    reserved204(204),
                    reserved205(205),
                    reserved206(206),
                    reserved207(207),
                    reserved208(208),                                     -- 0xd0
                    reserved209(209),
                    reserved210(210),
                    reserved211(211),
                    reserved212(212),
                    reserved213(213),
                    reserved214(214),
                    reserved215(215),
                    reserved216(216),
                    reserved217(217),
                    reserved218(218),
                    reserved219(219),
                    reserved220(220),
                    reserved221(221),
                    reserved222(222),
                    reserved223(223),
                    reserved224(224),                                     -- 0xe0
                    reserved225(225),
                    reserved226(226),
                    reserved227(227),
                    reserved228(228),
                    reserved229(229),
                    reserved230(230),
                    reserved231(231),
                    reserved232(232),
                    reserved233(233),
                    reserved234(234),
                    reserved235(235),
                    reserved236(236),
                    reserved237(237),
                    reserved238(238),
                    reserved239(239),
                    HotSwap(240),                                      -- 0xf0
                    IPMBLink(241),
                    reserved242(242),
                    reserved243(243),
                    reserved244(244),
                    reserved245(245),
                    reserved246(246),
                    reserved247(247),
                    reserved248(248),
                    reserved249(249),
                    reserved250(250),
                    reserved251(251),
                    reserved252(252),
                    reserved253(253),
                    reserved254(254),
                    reserved255(255) 
                }

              ACCESS  read-only
              STATUS  mandatory
              DESCRIPTION
                      ""
              ::= { sensor-entry 11 }

        sensor-event OBJECT-TYPE
              SYNTAX  INTEGER
              ACCESS  read-only
              STATUS  mandatory
              DESCRIPTION
                      ""
              ::= { sensor-entry 12 }

        sensor-assertion-event-mask OBJECT-TYPE
              SYNTAX  INTEGER
              ACCESS  read-only
              STATUS  mandatory
              DESCRIPTION
                      ""
              ::= { sensor-entry 13 }

        sensor-deassertion-event-mask OBJECT-TYPE
              SYNTAX  INTEGER
              ACCESS  read-only
              STATUS  mandatory
              DESCRIPTION
                      ""
              ::= { sensor-entry 14 }

        sensor-mask OBJECT-TYPE
              SYNTAX  INTEGER
              ACCESS  read-only
              STATUS  mandatory
              DESCRIPTION
                      ""
              ::= { sensor-entry 15 }

        sensor-unit1 OBJECT-TYPE
              SYNTAX  INTEGER
              ACCESS  read-only
              STATUS  mandatory
              DESCRIPTION
                      ""
              ::= { sensor-entry 16 }

        sensor-unit2 OBJECT-TYPE
              SYNTAX  INTEGER
              ACCESS  read-only
              STATUS  mandatory
              DESCRIPTION
                      ""
              ::= { sensor-entry 17 }

        sensor-unit3 OBJECT-TYPE
              SYNTAX  INTEGER
              ACCESS  read-only
              STATUS  mandatory
              DESCRIPTION
                      ""
              ::= { sensor-entry 18 }

        sensor-linearization OBJECT-TYPE
              SYNTAX  INTEGER
              ACCESS  read-only
              STATUS  mandatory
              DESCRIPTION
                      ""
              ::= { sensor-entry 19 }

        sensor-M OBJECT-TYPE
              SYNTAX  INTEGER
              ACCESS  read-only
              STATUS  mandatory
              DESCRIPTION
                      ""
              ::= { sensor-entry 20 }

        sensor-tolerance OBJECT-TYPE
              SYNTAX  INTEGER
              ACCESS  read-only
              STATUS  mandatory
              DESCRIPTION
                      ""
              ::= { sensor-entry 21 }

        sensor-B OBJECT-TYPE
              SYNTAX  INTEGER
              ACCESS  read-only
              STATUS  mandatory
              DESCRIPTION
                      ""
              ::= { sensor-entry 22 }

        sensor-accuracy OBJECT-TYPE
              SYNTAX  INTEGER
              ACCESS  read-only
              STATUS  mandatory
              DESCRIPTION
                      ""
              ::= { sensor-entry 23 }

        sensor-accuracy-exp OBJECT-TYPE
              SYNTAX  INTEGER
              ACCESS  read-only
              STATUS  mandatory
              DESCRIPTION
                      ""
              ::= { sensor-entry 24 }

        sensor-R-exp OBJECT-TYPE
              SYNTAX  INTEGER
              ACCESS  read-only
              STATUS  mandatory
              DESCRIPTION
                      ""
              ::= { sensor-entry 25 }

        sensor-B-exp OBJECT-TYPE
              SYNTAX  INTEGER
              ACCESS  read-only
              STATUS  mandatory
              DESCRIPTION
                      ""
              ::= { sensor-entry 26 }

        sensor-characteristic-flags OBJECT-TYPE
              SYNTAX  INTEGER
              ACCESS  read-only
              STATUS  mandatory
              DESCRIPTION
                      ""
              ::= { sensor-entry 27 }

        sensor-reading OBJECT-TYPE
              SYNTAX  INTEGER
              ACCESS  read-only
              STATUS  mandatory
              DESCRIPTION
                      ""
              ::= { sensor-entry 28 }

        sensor-processed-reading OBJECT-TYPE
              SYNTAX  DisplayString ( SIZE(0..255) )
              ACCESS  read-only
              STATUS  mandatory
              DESCRIPTION
                      ""
              ::= { sensor-entry 29 }


        sensor-nominal-reading OBJECT-TYPE
              SYNTAX  INTEGER
              ACCESS  read-only
              STATUS  mandatory
              DESCRIPTION
                      ""
              ::= { sensor-entry 30 }

        sensor-nominal-maximum OBJECT-TYPE
              SYNTAX  INTEGER
              ACCESS  read-only
              STATUS  mandatory
              DESCRIPTION
                      ""
              ::= { sensor-entry 31 }

        sensor-nominal-minimum OBJECT-TYPE
              SYNTAX  INTEGER
              ACCESS  read-only
              STATUS  mandatory
              DESCRIPTION
                      ""
              ::= { sensor-entry 32 }

        sensor-maximum-reading OBJECT-TYPE
              SYNTAX  INTEGER
              ACCESS  read-only
              STATUS  mandatory
              DESCRIPTION
                      ""
              ::= { sensor-entry 33 }

        sensor-minimum-reading OBJECT-TYPE
              SYNTAX  INTEGER
              ACCESS  read-only
              STATUS  mandatory
              DESCRIPTION
                      ""
              ::= { sensor-entry 34 }

        sensor-upper-non-recoverable-threshold OBJECT-TYPE
              SYNTAX  INTEGER
              ACCESS  read-write
              STATUS  mandatory
              DESCRIPTION
                      ""
              ::= { sensor-entry 35 }

        sensor-upper-critical-threshold OBJECT-TYPE
              SYNTAX  INTEGER
              ACCESS  read-write
              STATUS  mandatory
              DESCRIPTION
                      ""
              ::= { sensor-entry 36 }

        sensor-upper-non-critical-threshold OBJECT-TYPE
              SYNTAX  INTEGER
              ACCESS  read-write
              STATUS  mandatory
              DESCRIPTION
                      ""
              ::= { sensor-entry 37 }

        sensor-lower-non-recoverable-threshold OBJECT-TYPE
              SYNTAX  INTEGER
              ACCESS  read-write
              STATUS  mandatory
              DESCRIPTION
                      ""
              ::= { sensor-entry 38 }

        sensor-lower-critical-threshold OBJECT-TYPE
              SYNTAX  INTEGER
              ACCESS  read-write
              STATUS  mandatory
              DESCRIPTION
                      ""
              ::= { sensor-entry 39 }

        sensor-lower-non-critical-threshold OBJECT-TYPE
              SYNTAX  INTEGER
              ACCESS  read-write
              STATUS  mandatory
              DESCRIPTION
                      ""
              ::= { sensor-entry 40 }

        sensor-positive-going-threshold-hysteresis OBJECT-TYPE
              SYNTAX  INTEGER
              ACCESS  read-write
              STATUS  mandatory
              DESCRIPTION
                      ""
              ::= { sensor-entry 41 }

        sensor-negative-going-threshold-hysteresis OBJECT-TYPE
              SYNTAX  INTEGER
              ACCESS  read-write
              STATUS  mandatory
              DESCRIPTION
                      ""
              ::= { sensor-entry 42 }

        sensor-id-string OBJECT-TYPE
              SYNTAX  DisplayString ( SIZE (0..255) )
              ACCESS  read-only
              STATUS  mandatory
              DESCRIPTION
                      ""
              ::= { sensor-entry 43 }

        sensor-entire-sensor-data OBJECT-TYPE
              SYNTAX  OCTET STRING ( SIZE (0..128) )
              ACCESS  read-only
              STATUS  mandatory
              DESCRIPTION
                      ""
              ::= { sensor-entry 44 }


    -- board               OBJECT IDENTIFIER ::= { ipm-sentry-shmm 4 }

    board OBJECT-TYPE
              SYNTAX  SEQUENCE OF Board-entry
              ACCESS  not-accessible
              STATUS  mandatory
              DESCRIPTION
                      "A list of IPM Controllers"
              ::= { ipm-sentry-shmm 4 }

        board-entry OBJECT-TYPE
              SYNTAX  Board-entry
              ACCESS  not-accessible
              STATUS  mandatory
              DESCRIPTION
                      "An IPM Controller entry"
              INDEX   { board-index }
              ::= { board 1 }

        Board-entry ::=
              SEQUENCE {
                  board-index
                        INTEGER,
                  board-present
                        INTEGER,
                  board-healthy
                        INTEGER,
                  board-reset
                        INTEGER,
                  board-slave-address
                        INTEGER,
                  board-fru-device-id
                        INTEGER
              }

        board-index OBJECT-TYPE
              SYNTAX  INTEGER
              ACCESS  read-only
              STATUS  mandatory
              DESCRIPTION
                      "Index"
              ::= { board-entry 1 }
    
        board-present OBJECT-TYPE
              SYNTAX  INTEGER {
                    Absent (0),
                    Present (1)
                }
              ACCESS  read-only
              STATUS  mandatory
              DESCRIPTION
                      ""
              ::= { board-entry 2 }
    
        board-healthy OBJECT-TYPE
              SYNTAX  INTEGER
              ACCESS  read-only
              STATUS  mandatory
              DESCRIPTION
                      ""
              ::= { board-entry 3 }
    
        board-reset OBJECT-TYPE
              SYNTAX  INTEGER
              ACCESS  read-write
              STATUS  mandatory
              DESCRIPTION
                      ""
              ::= { board-entry 4 }
    
        board-slave-address OBJECT-TYPE
              SYNTAX  INTEGER
              ACCESS  read-only
              STATUS  mandatory
              DESCRIPTION
                      ""
              ::= { board-entry 5 }
    
        board-fru-device-id OBJECT-TYPE
              SYNTAX  INTEGER
              ACCESS  read-only
              STATUS  mandatory
              DESCRIPTION
                      ""
              ::= { board-entry 6 }
    
    -- sel                 OBJECT IDENTIFIER ::= { ipm-sentry-shmm 5 }

    sel OBJECT-TYPE
              SYNTAX  SEQUENCE OF Sel-entry
              ACCESS  not-accessible
              STATUS  mandatory
              DESCRIPTION
                      "A list of IPM Controllers"
              ::= { ipm-sentry-shmm 5 }

        sel-entry OBJECT-TYPE
              SYNTAX  Sel-entry
              ACCESS  not-accessible
              STATUS  mandatory
              DESCRIPTION
                      "An IPM Controller entry"
              INDEX   { sel-index }
              ::= { sel 1 }

        Sel-entry ::=
              SEQUENCE {
                  sel-index
                        INTEGER,
                  sel-contents
                        OCTET STRING
              }

        sel-index OBJECT-TYPE
              SYNTAX  INTEGER
              ACCESS  read-only
              STATUS  mandatory
              DESCRIPTION
                      "index"
              ::= { sel-entry 1 }

        sel-contents OBJECT-TYPE
              SYNTAX  OCTET STRING ( SIZE(0..128) )
              ACCESS  read-only
              STATUS  mandatory
              DESCRIPTION
                      ""
              ::= { sel-entry 2 }

    -- shelf               OBJECT IDENTIFIER ::= { ipm-sentry-shmm 6 }

    shelf OBJECT-TYPE
              SYNTAX  SEQUENCE OF Shelf-entry
              ACCESS  not-accessible
              STATUS  mandatory
              DESCRIPTION
                      "A list of IPM Controllers"
              ::= { ipm-sentry-shmm 6 }

        shelf-entry OBJECT-TYPE
              SYNTAX  Shelf-entry
              ACCESS  not-accessible
              STATUS  mandatory
              DESCRIPTION
                      "An IPM Controller entry"
              INDEX   { shelf-index }
              ::= { shelf 1 }

        Shelf-entry ::=
              SEQUENCE {
                  shelf-index
                        INTEGER,
                  shelf-healthy
                        INTEGER
              }

        shelf-index OBJECT-TYPE
              SYNTAX  INTEGER
              ACCESS  read-only
              STATUS  mandatory
              DESCRIPTION
                      "index"
              ::= { shelf-entry 1 }

        shelf-healthy OBJECT-TYPE
              SYNTAX  INTEGER
              ACCESS  read-only
              STATUS  mandatory
              DESCRIPTION
                      ""
              ::= { shelf-entry 2 }

--        host-state OBJECT-TYPE
--              SYNTAX  INTEGER {
--                    Backup (0),
--                    Active (1)
--                    }
--              ACCESS  read-write
--              STATUS  mandatory
--              DESCRIPTION
--                      "on read:     0   - Backup Host 
--                                    1   - Active Host 
--                       on write:    0   - do nothing 
--                                    !=0 - perform switchower"
--              ::= { shelf 2 }


    -- lan-configuration   OBJECT IDENTIFIER ::= { ipm-sentry-shmm 7 }

    lan-configuration OBJECT-TYPE
              SYNTAX  SEQUENCE OF Lan-configuration-entry
              ACCESS  not-accessible
              STATUS  mandatory
              DESCRIPTION
                      "A list of "
              ::= { ipm-sentry-shmm 7 }

        lan-configuration-entry OBJECT-TYPE
              SYNTAX  Lan-configuration-entry
              ACCESS  not-accessible
              STATUS  mandatory
              DESCRIPTION
                      "An IPM entry"
              INDEX   { lan-configuration-index }
              ::= { lan-configuration 1 }

        Lan-configuration-entry ::=
              SEQUENCE {
                  lan-configuration-index
                        INTEGER,
                  lan-configuration-set-in-progress
                        INTEGER,
                  lan-configuration-authentication-type-support
                        INTEGER,
                  lan-configuration-authentication-type-enable
                        OCTET STRING,
                  lan-configuration-ip-address
                        IpAddress,
                  lan-configuration-ip-address-source
                        INTEGER,
                  lan-configuration-mac-address
                        MacAddress,
                  lan-configuration-subnet-mask
                        IpAddress,
                  lan-configuration-ipv4-header-parameters
                        OCTET STRING,
                  lan-configuration-primary-rmcp-port-number
                        INTEGER,
                  lan-configuration-secondary-rmcp-port-number
                        INTEGER,
                  lan-configuration-bmc-generated-arp-control
                        INTEGER,
                  lan-configuration-gratuitous-arp-interval
                        INTEGER,
                  lan-configuration-default-gateway-address
                        IpAddress,
                  lan-configuration-default-gateway-mac-address
                        MacAddress,
                  lan-configuration-backup-gateway-address
                        IpAddress,
                  lan-configuration-backup-gateway-mac-address
                        MacAddress,
                  lan-configuration-community-string
                        DisplayString,
                  lan-configuration-number-of-destinations
                        INTEGER,
                  lan-configuration-destination-type-0
                        OCTET STRING,
                  lan-configuration-destination-type-1
                        OCTET STRING,
                  lan-configuration-destination-type-2
                        OCTET STRING,
                  lan-configuration-destination-type-3
                        OCTET STRING,
                  lan-configuration-destination-type-4
                        OCTET STRING,
                  lan-configuration-destination-type-5
                        OCTET STRING,
                  lan-configuration-destination-type-6
                        OCTET STRING,
                  lan-configuration-destination-type-7
                        OCTET STRING,
                  lan-configuration-destination-type-8
                        OCTET STRING,
                  lan-configuration-destination-type-9
                        OCTET STRING,
                  lan-configuration-destination-type-10
                        OCTET STRING,
                  lan-configuration-destination-type-11
                        OCTET STRING,
                  lan-configuration-destination-type-12
                        OCTET STRING,
                  lan-configuration-destination-type-13
                        OCTET STRING,
                  lan-configuration-destination-type-14
                        OCTET STRING,
                  lan-configuration-destination-type-15
                        OCTET STRING,
                  lan-configuration-destination-address-0
                        OCTET STRING,
                  lan-configuration-destination-address-1
                        OCTET STRING,
                  lan-configuration-destination-address-2
                        OCTET STRING,
                  lan-configuration-destination-address-3
                        OCTET STRING,
                  lan-configuration-destination-address-4
                        OCTET STRING,
                  lan-configuration-destination-address-5
                        OCTET STRING,
                  lan-configuration-destination-address-6
                        OCTET STRING,
                  lan-configuration-destination-address-7
                        OCTET STRING,
                  lan-configuration-destination-address-8
                        OCTET STRING,
                  lan-configuration-destination-address-9
                        OCTET STRING,
                  lan-configuration-destination-address-10
                        OCTET STRING,
                  lan-configuration-destination-address-11
                        OCTET STRING,
                  lan-configuration-destination-address-12
                        OCTET STRING,
                  lan-configuration-destination-address-13
                        OCTET STRING,
                  lan-configuration-destination-address-14
                        OCTET STRING,
                  lan-configuration-destination-address-15
                        OCTET STRING
              }

        lan-configuration-index OBJECT-TYPE
              SYNTAX  INTEGER
              ACCESS  read-only
              STATUS  mandatory
              DESCRIPTION
                      "index"
              ::= { lan-configuration-entry 1 }

        lan-configuration-set-in-progress OBJECT-TYPE
              SYNTAX  INTEGER
              ACCESS  read-only
              STATUS  mandatory
              DESCRIPTION
                      ""
              ::= { lan-configuration-entry 2 }

        lan-configuration-authentication-type-support OBJECT-TYPE
              SYNTAX  INTEGER
              ACCESS  read-only
              STATUS  mandatory
              DESCRIPTION
                      ""
              ::= { lan-configuration-entry 3 }

        lan-configuration-authentication-type-enable OBJECT-TYPE
              SYNTAX  OCTET STRING ( SIZE(5) )
              ACCESS  read-write
              STATUS  mandatory
              DESCRIPTION
                      ""
              ::= { lan-configuration-entry 4 }

        lan-configuration-ip-address OBJECT-TYPE
              SYNTAX  IpAddress
              ACCESS  read-write
              STATUS  mandatory
              DESCRIPTION
                      ""
              ::= { lan-configuration-entry 5 }

        lan-configuration-ip-address-source OBJECT-TYPE
              SYNTAX  INTEGER
              ACCESS  read-only
              STATUS  mandatory
              DESCRIPTION
                      ""
              ::= { lan-configuration-entry 6 }

        lan-configuration-mac-address OBJECT-TYPE
              SYNTAX  MacAddress
              ACCESS  read-write
              STATUS  mandatory
              DESCRIPTION
                      ""
              ::= { lan-configuration-entry 7 }

        lan-configuration-subnet-mask OBJECT-TYPE
              SYNTAX  IpAddress
              ACCESS  read-write
              STATUS  mandatory
              DESCRIPTION
                      ""
              ::= { lan-configuration-entry 8 }

        lan-configuration-ipv4-header-parameters OBJECT-TYPE
              SYNTAX  OCTET STRING ( SIZE(3) )
              ACCESS  read-write
              STATUS  mandatory
              DESCRIPTION
                      ""
              ::= { lan-configuration-entry 9 }

        lan-configuration-primary-rmcp-port-number OBJECT-TYPE
              SYNTAX  INTEGER
              ACCESS  read-write
              STATUS  mandatory
              DESCRIPTION
                      ""
              ::= { lan-configuration-entry 10 }

        lan-configuration-secondary-rmcp-port-number OBJECT-TYPE
              SYNTAX  INTEGER
              ACCESS  read-write
              STATUS  mandatory
              DESCRIPTION
                      ""
              ::= { lan-configuration-entry 11 }

        lan-configuration-bmc-generated-arp-control OBJECT-TYPE
              SYNTAX  INTEGER
              ACCESS  read-write
              STATUS  mandatory
              DESCRIPTION
                      ""
              ::= { lan-configuration-entry 12 }

        lan-configuration-gratuitous-arp-interval OBJECT-TYPE
              SYNTAX  INTEGER
              ACCESS  read-write
              STATUS  mandatory
              DESCRIPTION
                      ""
              ::= { lan-configuration-entry 13 }

        lan-configuration-default-gateway-address OBJECT-TYPE
              SYNTAX  IpAddress
              ACCESS  read-write
              STATUS  mandatory
              DESCRIPTION
                      ""
              ::= { lan-configuration-entry 14 }

        lan-configuration-default-gateway-mac-address OBJECT-TYPE
              SYNTAX  MacAddress
              ACCESS  read-write
              STATUS  mandatory
              DESCRIPTION
                      ""
              ::= { lan-configuration-entry 15 }

        lan-configuration-backup-gateway-address OBJECT-TYPE
              SYNTAX  IpAddress
              ACCESS  read-write
              STATUS  mandatory
              DESCRIPTION
                      ""
              ::= { lan-configuration-entry 16 }

        lan-configuration-backup-gateway-mac-address OBJECT-TYPE
              SYNTAX  MacAddress
              ACCESS  read-write
              STATUS  mandatory
              DESCRIPTION
                      ""
              ::= { lan-configuration-entry 17 }

        lan-configuration-community-string OBJECT-TYPE
              SYNTAX  DisplayString ( SIZE(0..255) )
              ACCESS  read-write
              STATUS  mandatory
              DESCRIPTION
                      ""
              ::= { lan-configuration-entry 18 }

        lan-configuration-number-of-destinations OBJECT-TYPE
              SYNTAX  INTEGER
              ACCESS  read-only
              STATUS  mandatory
              DESCRIPTION
                      ""
              ::= { lan-configuration-entry 19 }

        lan-configuration-destination-type-0 OBJECT-TYPE
              SYNTAX  OCTET STRING ( SIZE(3) )
              ACCESS  read-write
              STATUS  mandatory
              DESCRIPTION
                      ""
              ::= { lan-configuration-entry 20 }

        lan-configuration-destination-type-1 OBJECT-TYPE
              SYNTAX  OCTET STRING ( SIZE(3) )
              ACCESS  read-write
              STATUS  mandatory
              DESCRIPTION
                      ""
              ::= { lan-configuration-entry 21 }

        lan-configuration-destination-type-2 OBJECT-TYPE
              SYNTAX  OCTET STRING ( SIZE(3) )
              ACCESS  read-write
              STATUS  mandatory
              DESCRIPTION
                      ""
              ::= { lan-configuration-entry 22 }

        lan-configuration-destination-type-3 OBJECT-TYPE
              SYNTAX  OCTET STRING ( SIZE(3) )
              ACCESS  read-write
              STATUS  mandatory
              DESCRIPTION
                      ""
              ::= { lan-configuration-entry 23 }

        lan-configuration-destination-type-4 OBJECT-TYPE
              SYNTAX  OCTET STRING ( SIZE(3) )
              ACCESS  read-write
              STATUS  mandatory
              DESCRIPTION
                      ""
              ::= { lan-configuration-entry 24 }

        lan-configuration-destination-type-5 OBJECT-TYPE
              SYNTAX  OCTET STRING ( SIZE(3) )
              ACCESS  read-write
              STATUS  mandatory
              DESCRIPTION
                      ""
              ::= { lan-configuration-entry 25 }

        lan-configuration-destination-type-6 OBJECT-TYPE
              SYNTAX  OCTET STRING ( SIZE(3) )
              ACCESS  read-write
              STATUS  mandatory
              DESCRIPTION
                      ""
              ::= { lan-configuration-entry 26 }

        lan-configuration-destination-type-7 OBJECT-TYPE
              SYNTAX  OCTET STRING ( SIZE(3) )
              ACCESS  read-write
              STATUS  mandatory
              DESCRIPTION
                      ""
              ::= { lan-configuration-entry 27 }

        lan-configuration-destination-type-8 OBJECT-TYPE
              SYNTAX  OCTET STRING ( SIZE(3) )
              ACCESS  read-write
              STATUS  mandatory
              DESCRIPTION
                      ""
              ::= { lan-configuration-entry 28 }

        lan-configuration-destination-type-9 OBJECT-TYPE
              SYNTAX  OCTET STRING ( SIZE(3) )
              ACCESS  read-write
              STATUS  mandatory
              DESCRIPTION
                      ""
              ::= { lan-configuration-entry 29 }

        lan-configuration-destination-type-10 OBJECT-TYPE
              SYNTAX  OCTET STRING ( SIZE(3) )
              ACCESS  read-write
              STATUS  mandatory
              DESCRIPTION
                      ""
              ::= { lan-configuration-entry 30 }

        lan-configuration-destination-type-11 OBJECT-TYPE
              SYNTAX  OCTET STRING ( SIZE(3) )
              ACCESS  read-write
              STATUS  mandatory
              DESCRIPTION
                      ""
              ::= { lan-configuration-entry 31 }

        lan-configuration-destination-type-12 OBJECT-TYPE
              SYNTAX  OCTET STRING ( SIZE(3) )
              ACCESS  read-write
              STATUS  mandatory
              DESCRIPTION
                      ""
              ::= { lan-configuration-entry 32 }

        lan-configuration-destination-type-13 OBJECT-TYPE
              SYNTAX  OCTET STRING ( SIZE(3) )
              ACCESS  read-write
              STATUS  mandatory
              DESCRIPTION
                      ""
              ::= { lan-configuration-entry 33 }

        lan-configuration-destination-type-14 OBJECT-TYPE
              SYNTAX  OCTET STRING ( SIZE(3) )
              ACCESS  read-write
              STATUS  mandatory
              DESCRIPTION
                      ""
              ::= { lan-configuration-entry 34 }

        lan-configuration-destination-type-15 OBJECT-TYPE
              SYNTAX  OCTET STRING ( SIZE(3) )
              ACCESS  read-write
              STATUS  mandatory
              DESCRIPTION
                      ""
              ::= { lan-configuration-entry 35 }

        lan-configuration-destination-address-0 OBJECT-TYPE
              SYNTAX  OCTET STRING ( SIZE(1 | 12) )
              ACCESS  read-write
              STATUS  mandatory
              DESCRIPTION
                      ""
              ::= { lan-configuration-entry 36 }

        lan-configuration-destination-address-1 OBJECT-TYPE
              SYNTAX  OCTET STRING ( SIZE(1 | 12) )
              ACCESS  read-write
              STATUS  mandatory
              DESCRIPTION
                      ""
              ::= { lan-configuration-entry 37 }

        lan-configuration-destination-address-2 OBJECT-TYPE
              SYNTAX  OCTET STRING ( SIZE(1 | 12) )
              ACCESS  read-write
              STATUS  mandatory
              DESCRIPTION
                      ""
              ::= { lan-configuration-entry 38 }

        lan-configuration-destination-address-3 OBJECT-TYPE
              SYNTAX  OCTET STRING ( SIZE(1 | 12) )
              ACCESS  read-write
              STATUS  mandatory
              DESCRIPTION
                      ""
              ::= { lan-configuration-entry 39 }

        lan-configuration-destination-address-4 OBJECT-TYPE
              SYNTAX  OCTET STRING ( SIZE(1 | 12) )
              ACCESS  read-write
              STATUS  mandatory
              DESCRIPTION
                      ""
              ::= { lan-configuration-entry 40 }

        lan-configuration-destination-address-5 OBJECT-TYPE
              SYNTAX  OCTET STRING ( SIZE(1 | 12) )
              ACCESS  read-write
              STATUS  mandatory
              DESCRIPTION
                      ""
              ::= { lan-configuration-entry 41 }

        lan-configuration-destination-address-6 OBJECT-TYPE
              SYNTAX  OCTET STRING ( SIZE(1 | 12) )
              ACCESS  read-write
              STATUS  mandatory
              DESCRIPTION
                      ""
              ::= { lan-configuration-entry 42 }

        lan-configuration-destination-address-7 OBJECT-TYPE
              SYNTAX  OCTET STRING ( SIZE(1 | 12) )
              ACCESS  read-write
              STATUS  mandatory
              DESCRIPTION
                      ""
              ::= { lan-configuration-entry 43 }

        lan-configuration-destination-address-8 OBJECT-TYPE
              SYNTAX  OCTET STRING ( SIZE(1 | 12) )
              ACCESS  read-write
              STATUS  mandatory
              DESCRIPTION
                      ""
              ::= { lan-configuration-entry 44 }

        lan-configuration-destination-address-9 OBJECT-TYPE
              SYNTAX  OCTET STRING ( SIZE(1 | 12) )
              ACCESS  read-write
              STATUS  mandatory
              DESCRIPTION
                      ""
              ::= { lan-configuration-entry 45 }

        lan-configuration-destination-address-10 OBJECT-TYPE
              SYNTAX  OCTET STRING ( SIZE(1 | 12) )
              ACCESS  read-write
              STATUS  mandatory
              DESCRIPTION
                      ""
              ::= { lan-configuration-entry 46 }

        lan-configuration-destination-address-11 OBJECT-TYPE
              SYNTAX  OCTET STRING ( SIZE(1 | 12) )
              ACCESS  read-write
              STATUS  mandatory
              DESCRIPTION
                      ""
              ::= { lan-configuration-entry 47 }

        lan-configuration-destination-address-12 OBJECT-TYPE
              SYNTAX  OCTET STRING ( SIZE(1 | 12) )
              ACCESS  read-write
              STATUS  mandatory
              DESCRIPTION
                      ""
              ::= { lan-configuration-entry 48 }

        lan-configuration-destination-address-13 OBJECT-TYPE
              SYNTAX  OCTET STRING ( SIZE(1 | 12) )
              ACCESS  read-write
              STATUS  mandatory
              DESCRIPTION
                      ""
              ::= { lan-configuration-entry 49 }

        lan-configuration-destination-address-14 OBJECT-TYPE
              SYNTAX  OCTET STRING ( SIZE(1 | 12) )
              ACCESS  read-write
              STATUS  mandatory
              DESCRIPTION
                      ""
              ::= { lan-configuration-entry 50 }

        lan-configuration-destination-address-15 OBJECT-TYPE
              SYNTAX  OCTET STRING ( SIZE(1 | 12) )
              ACCESS  read-write
              STATUS  mandatory
              DESCRIPTION
                      ""
              ::= { lan-configuration-entry 51 }

    -- pef-configuration-set-in-progress   OBJECT IDENTIFIER ::= { ipm-sentry-shmm 8 }

        pef-configuration-set-in-progress OBJECT-TYPE
              SYNTAX  INTEGER
              ACCESS  read-only
              STATUS  mandatory
              DESCRIPTION
                      ""
              ::= { ipm-sentry-shmm 8 }

    -- pef-configuration-control   OBJECT IDENTIFIER ::= { ipm-sentry-shmm 9 }

        pef-configuration-control OBJECT-TYPE
              SYNTAX  INTEGER
              ACCESS  read-only
              STATUS  mandatory
              DESCRIPTION
                      ""
              ::= { ipm-sentry-shmm 9 }

    -- pef-configuration-action-global-control   OBJECT IDENTIFIER ::= { ipm-sentry-shmm 10 }

        pef-configuration-action-global-control OBJECT-TYPE
              SYNTAX  INTEGER
              ACCESS  read-only
              STATUS  mandatory
              DESCRIPTION
                      ""
              ::= { ipm-sentry-shmm 10 }

    -- pef-configuration-startup-delay   OBJECT IDENTIFIER ::= { ipm-sentry-shmm 11 }

        pef-configuration-startup-delay OBJECT-TYPE
              SYNTAX  INTEGER
              ACCESS  read-only
              STATUS  mandatory
              DESCRIPTION
                      ""
              ::= { ipm-sentry-shmm 11 }

    -- pef-configuration-alert-startup-delay   OBJECT IDENTIFIER ::= { ipm-sentry-shmm 12 }

        pef-configuration-alert-startup-delay OBJECT-TYPE
              SYNTAX  INTEGER
              ACCESS  read-only
              STATUS  mandatory
              DESCRIPTION
                      ""
              ::= { ipm-sentry-shmm 12 }

    -- pef-configuration-number-of-event-filters   OBJECT IDENTIFIER ::= { ipm-sentry-shmm 13 }

        pef-configuration-number-of-event-filters OBJECT-TYPE
              SYNTAX  INTEGER
              ACCESS  read-only
              STATUS  mandatory
              DESCRIPTION
                      ""
              ::= { ipm-sentry-shmm 13 }

    -- pef-configuration-event-filter-table  OBJECT IDENTIFIER ::= { ipm-sentry-shmm 14 }

    pef-configuration-event-filter-table OBJECT-TYPE
              SYNTAX  SEQUENCE OF Pef-configuration-event-filter-table-entry
              ACCESS  not-accessible
              STATUS  mandatory
              DESCRIPTION
                      ""
              ::= { ipm-sentry-shmm 14 }

        pef-configuration-event-filter-table-entry OBJECT-TYPE
              SYNTAX  Pef-configuration-event-filter-table-entry
              ACCESS  not-accessible
              STATUS  mandatory
              DESCRIPTION
                      ""
              INDEX   { pef-configuration-event-filter-index }
              ::= { pef-configuration-event-filter-table 1 }

        Pef-configuration-event-filter-table-entry ::=
              SEQUENCE {
                  pef-configuration-event-filter-index
                        INTEGER,
                  pef-configuration-event-filter-data
                        OCTET STRING
              }

        pef-configuration-event-filter-index OBJECT-TYPE
              SYNTAX  INTEGER
              ACCESS  read-only
              STATUS  mandatory
              DESCRIPTION
                      "index"
              ::= { pef-configuration-event-filter-table-entry 1 }

        pef-configuration-event-filter-data OBJECT-TYPE
              SYNTAX  OCTET STRING ( SIZE(20) )
              ACCESS  read-only
              STATUS  mandatory
              DESCRIPTION
                      ""
              ::= { pef-configuration-event-filter-table-entry 2 }

    -- pef-configuration-number-of-alert-policy-entries   OBJECT IDENTIFIER ::= { ipm-sentry-shmm 15 }

        pef-configuration-number-of-alert-policy-entries OBJECT-TYPE
              SYNTAX  INTEGER
              ACCESS  read-only
              STATUS  mandatory
              DESCRIPTION
                      ""
              ::= { ipm-sentry-shmm 15 }

    -- pef-configuration-alert-policy-table  OBJECT IDENTIFIER ::= { ipm-sentry-shmm 16 }

    pef-configuration-alert-policy-table OBJECT-TYPE
              SYNTAX  SEQUENCE OF Pef-configuration-alert-policy-table-entry
              ACCESS  not-accessible
              STATUS  mandatory
              DESCRIPTION
                      ""
              ::= { ipm-sentry-shmm 16 }

        pef-configuration-alert-policy-table-entry OBJECT-TYPE
              SYNTAX  Pef-configuration-alert-policy-table-entry
              ACCESS  not-accessible
              STATUS  mandatory
              DESCRIPTION
                      ""
              INDEX   { pef-configuration-alert-policy-index }
              ::= { pef-configuration-alert-policy-table 1 }

        Pef-configuration-alert-policy-table-entry ::=
              SEQUENCE {
                  pef-configuration-alert-policy-index
                        INTEGER,
                  pef-configuration-alert-policy-data
                        OCTET STRING
              }

        pef-configuration-alert-policy-index OBJECT-TYPE
              SYNTAX  INTEGER
              ACCESS  read-only
              STATUS  mandatory
              DESCRIPTION
                      "index"
              ::= { pef-configuration-alert-policy-table-entry 1 }

        pef-configuration-alert-policy-data OBJECT-TYPE
              SYNTAX  OCTET STRING ( SIZE(3) )
              ACCESS  read-only
              STATUS  mandatory
              DESCRIPTION
                      ""
              ::= { pef-configuration-alert-policy-table-entry 2 }

    -- pef-configuration-system-guid   OBJECT IDENTIFIER ::= { ipm-sentry-shmm 17 }

        pef-configuration-system-guid OBJECT-TYPE
              SYNTAX  OCTET STRING ( SIZE(16) )
              ACCESS  read-only
              STATUS  mandatory
              DESCRIPTION
                      ""
              ::= { ipm-sentry-shmm 17 }

    -- pef-configuration-number-of-alert-strings   OBJECT IDENTIFIER ::= { ipm-sentry-shmm 18 }

        pef-configuration-number-of-alert-strings OBJECT-TYPE
              SYNTAX  INTEGER
              ACCESS  read-only
              STATUS  mandatory
              DESCRIPTION
                      ""
              ::= { ipm-sentry-shmm 18 }

    -- pef-configuration-alert-string-table  OBJECT IDENTIFIER ::= { ipm-sentry-shmm 19 }

    pef-configuration-alert-string-table OBJECT-TYPE
              SYNTAX  SEQUENCE OF Pef-configuration-alert-string-table-entry
              ACCESS  not-accessible
              STATUS  mandatory
              DESCRIPTION
                      ""
              ::= { ipm-sentry-shmm 19 }

        pef-configuration-alert-string-table-entry OBJECT-TYPE
              SYNTAX  Pef-configuration-alert-string-table-entry
              ACCESS  not-accessible
              STATUS  mandatory
              DESCRIPTION
                      ""
              INDEX   { pef-configuration-alert-string-index }
              ::= { pef-configuration-alert-string-table 1 }

        Pef-configuration-alert-string-table-entry ::=
              SEQUENCE {
                  pef-configuration-alert-string-index
                        INTEGER,
                  pef-configuration-alert-string-key
                        OCTET STRING,
                  pef-configuration-alert-string
                        DisplayString
              }

        pef-configuration-alert-string-index OBJECT-TYPE
              SYNTAX  INTEGER
              ACCESS  read-only
              STATUS  mandatory
              DESCRIPTION
                      "index"
              ::= { pef-configuration-alert-string-table-entry 1 }

        pef-configuration-alert-string-key OBJECT-TYPE
              SYNTAX  OCTET STRING ( SIZE(2) )
              ACCESS  read-only
              STATUS  mandatory
              DESCRIPTION
                      ""
              ::= { pef-configuration-alert-string-table-entry 2 }

        pef-configuration-alert-string OBJECT-TYPE
              SYNTAX  DisplayString
              ACCESS  read-only
              STATUS  mandatory
              DESCRIPTION
                      ""
              ::= { pef-configuration-alert-string-table-entry 3 }


    -- fru-info-table  OBJECT IDENTIFIER ::= { ipm-sentry-shmm 20 }

    fru-info-table OBJECT-TYPE
              SYNTAX  SEQUENCE OF Fru-info-table-entry
              ACCESS  not-accessible
              STATUS  mandatory
              DESCRIPTION
                      ""
              ::= { ipm-sentry-shmm 20 }

        fru-info-table-entry OBJECT-TYPE
              SYNTAX  Fru-info-table-entry
              ACCESS  not-accessible
              STATUS  mandatory
              DESCRIPTION
                      ""
              INDEX   { fru-info-index }
              ::= { fru-info-table 1 }

        Fru-info-table-entry ::=
              SEQUENCE {
                  fru-info-index
                        INTEGER,
                  fru-info-data
                        OCTET STRING,
                  fru-info-data-wo
                        OCTET STRING
              }

        fru-info-index OBJECT-TYPE
              SYNTAX  INTEGER
              ACCESS  read-only
              STATUS  mandatory
              DESCRIPTION
                      "Index: <ipmb_addr>.<fru_id>.<32-bytes block number> 
                       Index = (addr << 24) | (id << 16) | number"
              ::= { fru-info-table-entry 1 }

        fru-info-data OBJECT-TYPE
              SYNTAX  OCTET STRING ( SIZE(1..32) )
              ACCESS  read-only
              STATUS  mandatory
              DESCRIPTION
                      ""
              ::= { fru-info-table-entry 2 }

        fru-info-data-wo OBJECT-TYPE
              SYNTAX  OCTET STRING ( SIZE(1..32) )
              ACCESS  write-only
              STATUS  mandatory
              DESCRIPTION
                      "As index use should use the following sequence
                       <ipmb_addr>.<fru_id>.<offset>
                       Due to specific of implementation
                           <ipmb_addr> should be u8
                           <fru_id> should be u8
                           <offset> should be u16 - offset in bytes
                       As a result _WRITEABLE_ FRU Info size is reduced to 65535 bytes"
              ::= { fru-info-table-entry 3 }

    -- fru-device-by-site          OBJECT IDENTIFIER ::= {ipm-sentry-shmm 21}
                                                                           
    fru-device-by-site OBJECT-TYPE
              SYNTAX  SEQUENCE OF Fru-device-by-site-entry
              ACCESS  not-accessible
              STATUS  mandatory
              DESCRIPTION
                      "A list of IPM Controllers"
              ::= { ipm-sentry-shmm 21 }

        fru-device-by-site-entry OBJECT-TYPE
              SYNTAX  Fru-device-by-site-entry
              ACCESS  not-accessible
              STATUS  mandatory
              DESCRIPTION
                      "An IPM Controller entry"
              INDEX   { fru-device-by-site-index }
              ::= { fru-device-by-site 1 }

        Fru-device-by-site-entry ::=
              SEQUENCE {
                  fru-device-by-site-index
                        INTEGER,
                  fru-device-by-site-sdr-version
                        INTEGER,
                  fru-device-by-site-slave-address
                        INTEGER,
                  fru-device-by-site-fru-device-by-site-id
                        INTEGER,
                  fru-device-by-site-channel-number
                        INTEGER,
                  fru-device-by-site-device-type
                        INTEGER,
                  fru-device-by-site-device-type-modifier
                        INTEGER,
                  fru-device-by-site-fru-entity-id
                        INTEGER,
                  fru-device-by-site-fru-entity-instance
                        INTEGER,
                  fru-device-by-site-id-string
                        DisplayString ( SIZE (0..255) ),
                  fru-device-by-site-hot-swap-state
                        INTEGER,
                  fru-device-by-site-activated
                        INTEGER
              }

        fru-device-by-site-index OBJECT-TYPE
              SYNTAX  INTEGER
              ACCESS  read-only
              STATUS  mandatory
              DESCRIPTION
                      "index"
              ::= { fru-device-by-site-entry 1 }

        fru-device-by-site-sdr-version OBJECT-TYPE
              SYNTAX  INTEGER
              ACCESS  read-only
              STATUS  mandatory
              DESCRIPTION
                      ""
              ::= { fru-device-by-site-entry 2 }

        fru-device-by-site-slave-address OBJECT-TYPE
              SYNTAX  INTEGER
              ACCESS  read-only
              STATUS  mandatory
              DESCRIPTION
                      ""
              ::= { fru-device-by-site-entry 3 }

        fru-device-by-site-fru-device-by-site-id OBJECT-TYPE
              SYNTAX  INTEGER
              ACCESS  read-only
              STATUS  mandatory
              DESCRIPTION
                      ""
              ::= { fru-device-by-site-entry 4 }

        fru-device-by-site-channel-number OBJECT-TYPE
              SYNTAX  INTEGER
              ACCESS  read-only
              STATUS  mandatory
              DESCRIPTION
                      ""
              ::= { fru-device-by-site-entry 5 }

        fru-device-by-site-device-type OBJECT-TYPE
              SYNTAX  INTEGER
              ACCESS  read-only
              STATUS  mandatory
              DESCRIPTION
                      ""
              ::= { fru-device-by-site-entry 6 }

        fru-device-by-site-device-type-modifier OBJECT-TYPE
              SYNTAX  INTEGER
              ACCESS  read-only
              STATUS  mandatory
              DESCRIPTION
                      ""
              ::= { fru-device-by-site-entry 7 }

        fru-device-by-site-fru-entity-id OBJECT-TYPE
              SYNTAX  INTEGER
              ACCESS  read-only
              STATUS  mandatory
              DESCRIPTION
                      ""
              ::= { fru-device-by-site-entry 8 }

        fru-device-by-site-fru-entity-instance OBJECT-TYPE
              SYNTAX  INTEGER
              ACCESS  read-only
              STATUS  mandatory
              DESCRIPTION
                      ""
              ::= { fru-device-by-site-entry 9 }

        fru-device-by-site-id-string OBJECT-TYPE
              SYNTAX  DisplayString( SIZE(0..255) )
              ACCESS  read-only
              STATUS  mandatory
              DESCRIPTION
                      ""
              ::= { fru-device-by-site-entry 10 }

        fru-device-by-site-hot-swap-state OBJECT-TYPE
              SYNTAX  INTEGER {
                     M0 (0),
                     M1 (1),
                     M2 (2),
                     M3 (3),
                     M4 (4),
                     M5 (5),
                     M6 (6),
                     M7 (7)
                  }
              ACCESS  read-only
              STATUS  mandatory
              DESCRIPTION
                      ""
              ::= { fru-device-by-site-entry 11 }

        fru-device-by-site-activated OBJECT-TYPE
              SYNTAX  INTEGER
              ACCESS  read-write
              STATUS  mandatory
              DESCRIPTION
                      ""
              ::= { fru-device-by-site-entry 12 }


    -- board-basic           OBJECT IDENTIFIER ::= { ipm-sentry-shmm 32 }

    board-basic OBJECT-TYPE
              SYNTAX  SEQUENCE OF Board-basic-entry
              ACCESS  not-accessible
              STATUS  mandatory
              DESCRIPTION
                      "A list of boards"
              ::= { ipm-sentry-shmm 32 }

        board-basic-entry OBJECT-TYPE
              SYNTAX  Board-basic-entry
              ACCESS  not-accessible
              STATUS  mandatory
              DESCRIPTION
                      "A board entry"
              INDEX   { board-basic-slot-number }
              ::= { board-basic 1 }

        Board-basic-entry ::=
              SEQUENCE {
                  board-basic-slot-number
                        INTEGER,
                  board-basic-present
                        INTEGER,
                  board-basic-healthy
                        INTEGER,
                  board-basic-reset
                        INTEGER,
                  board-basic-powered
                        INTEGER,
                  board-basic-slave-address
                        INTEGER,
                  board-basic-fru-device-id
                        INTEGER,
                  board-basic-fruinfo-product-area-present
                        INTEGER,
                  board-basic-fruinfo-product-manufacturer
                        DisplayString,
                  board-basic-fruinfo-product-name
                        DisplayString,
                  board-basic-fruinfo-product-part-model-number
                        DisplayString,
                  board-basic-fruinfo-product-version-number
                        DisplayString,
                  board-basic-fruinfo-product-serial-number
                        DisplayString,
                  board-basic-fruinfo-board-area-present
                        INTEGER,
                  board-basic-fruinfo-board-manufacturer
                        DisplayString,
                  board-basic-fruinfo-board-product-name
                        DisplayString,
                  board-basic-fruinfo-board-serial-number
                        DisplayString,
                  board-basic-fruinfo-board-part-number
                        DisplayString,
                  board-basic-fruinfo-board-manufacture-time
                        INTEGER
              }

        board-basic-slot-number OBJECT-TYPE
              SYNTAX  INTEGER
              ACCESS  read-only
              STATUS  mandatory
              DESCRIPTION
                      ""
              ::= { board-basic-entry 1 }
    
        board-basic-present OBJECT-TYPE
              SYNTAX  INTEGER {
                    absent (0),
                    present (1)
                }
              ACCESS  read-only
              STATUS  mandatory
              DESCRIPTION
                      ""
              ::= { board-basic-entry 2 }
    
        board-basic-healthy OBJECT-TYPE
              SYNTAX  INTEGER {
                    unhealthy (0),
                    healthy (1)
                }
              ACCESS  read-only
              STATUS  mandatory
              DESCRIPTION
                      ""
              ::= { board-basic-entry 3 }
    
        board-basic-reset OBJECT-TYPE
              SYNTAX  INTEGER
              ACCESS  read-write
              STATUS  mandatory
              DESCRIPTION
                      ""
              ::= { board-basic-entry 4 }
    
        board-basic-powered OBJECT-TYPE
              SYNTAX  INTEGER
              ACCESS  read-write
              STATUS  mandatory
              DESCRIPTION
                      ""
              ::= { board-basic-entry 5 }
    
        board-basic-slave-address OBJECT-TYPE
              SYNTAX  INTEGER
              ACCESS  read-only
              STATUS  mandatory
              DESCRIPTION
                      ""
              ::= { board-basic-entry 6 }
    
        board-basic-fru-device-id OBJECT-TYPE
              SYNTAX  INTEGER
              ACCESS  read-only
              STATUS  mandatory
              DESCRIPTION
                      ""
              ::= { board-basic-entry 7 }
    
        board-basic-fruinfo-product-area-present OBJECT-TYPE
              SYNTAX  INTEGER {
                    absent (0),
                    present (1)
                }
              ACCESS  read-only
              STATUS  mandatory
              DESCRIPTION
                      ""
              ::= { board-basic-entry 8 }
    
        board-basic-fruinfo-product-manufacturer OBJECT-TYPE
              SYNTAX  DisplayString
              ACCESS  read-only
              STATUS  mandatory
              DESCRIPTION
                      ""
              ::= { board-basic-entry 9 }
    
        board-basic-fruinfo-product-name OBJECT-TYPE
              SYNTAX  DisplayString
              ACCESS  read-only
              STATUS  mandatory
              DESCRIPTION
                      ""
              ::= { board-basic-entry 10 }
    
        board-basic-fruinfo-product-part-model-number OBJECT-TYPE
              SYNTAX  DisplayString
              ACCESS  read-only
              STATUS  mandatory
              DESCRIPTION
                      ""
              ::= { board-basic-entry 11 }
    
        board-basic-fruinfo-product-version-number OBJECT-TYPE
              SYNTAX  DisplayString
              ACCESS  read-only
              STATUS  mandatory
              DESCRIPTION
                      ""
              ::= { board-basic-entry 12 }
    
        board-basic-fruinfo-product-serial-number OBJECT-TYPE
              SYNTAX  DisplayString
              ACCESS  read-only
              STATUS  mandatory
              DESCRIPTION
                      ""
              ::= { board-basic-entry 13 }
    
        board-basic-fruinfo-board-area-present OBJECT-TYPE
              SYNTAX  INTEGER {
                    absent (0),
                    present (1)
                }
              ACCESS  read-only
              STATUS  mandatory
              DESCRIPTION
                      ""
              ::= { board-basic-entry 14 }
    
        board-basic-fruinfo-board-manufacturer OBJECT-TYPE
              SYNTAX  DisplayString
              ACCESS  read-only
              STATUS  mandatory
              DESCRIPTION
                      ""
              ::= { board-basic-entry 15 }
    
        board-basic-fruinfo-board-product-name OBJECT-TYPE
              SYNTAX  DisplayString
              ACCESS  read-only
              STATUS  mandatory
              DESCRIPTION
                      ""
              ::= { board-basic-entry 16 }
    
        board-basic-fruinfo-board-serial-number OBJECT-TYPE
              SYNTAX  DisplayString
              ACCESS  read-only
              STATUS  mandatory
              DESCRIPTION
                      ""
              ::= { board-basic-entry 17 }
    
        board-basic-fruinfo-board-part-number OBJECT-TYPE
              SYNTAX  DisplayString
              ACCESS  read-only
              STATUS  mandatory
              DESCRIPTION
                      ""
              ::= { board-basic-entry 18 }
    
        board-basic-fruinfo-board-manufacture-time OBJECT-TYPE
              SYNTAX  INTEGER
              ACCESS  read-only
              STATUS  mandatory
              DESCRIPTION
                      ""
              ::= { board-basic-entry 19 }
    



    -- fantray          OBJECT IDENTIFIER ::= { ipm-sentry-shmm 33 }

    fantray OBJECT-TYPE
              SYNTAX  SEQUENCE OF Fantray-entry
              ACCESS  not-accessible
              STATUS  mandatory
              DESCRIPTION
                      "A list of fan trays"
              ::= { ipm-sentry-shmm 33 }

        fantray-entry OBJECT-TYPE
              SYNTAX  Fantray-entry
              ACCESS  not-accessible
              STATUS  mandatory
              DESCRIPTION
                      "A fan tray entry"
              INDEX   { fantray-slot-number }
              ::= { fantray 1 }

        Fantray-entry ::=
              SEQUENCE {
                  fantray-slot-number
                        INTEGER,
                  fantray-present
                        INTEGER,
                  fantray-healthy
                        INTEGER,
                  fantray-health-led
                        INTEGER,
                  fantray-slave-address
                        INTEGER,
                  fantray-fru-device-id
                        INTEGER,
                  fantray-fruinfo-product-area-present
                        INTEGER,
                  fantray-fruinfo-product-manufacturer
                        DisplayString,
                  fantray-fruinfo-product-name
                        DisplayString,
                  fantray-fruinfo-product-part-model-number
                        DisplayString,
                  fantray-fruinfo-product-version-number
                        DisplayString,
                  fantray-fruinfo-product-serial-number
                        DisplayString,
                  fantray-fruinfo-board-area-present
                        INTEGER,
                  fantray-fruinfo-board-manufacturer
                        DisplayString,
                  fantray-fruinfo-board-product-name
                        DisplayString,
                  fantray-fruinfo-board-serial-number
                        DisplayString,
                  fantray-fruinfo-board-part-number
                        DisplayString,
                  fantray-fruinfo-board-manufacture-time
                        INTEGER
              }

        fantray-slot-number OBJECT-TYPE
              SYNTAX  INTEGER
              ACCESS  read-only
              STATUS  mandatory
              DESCRIPTION
                      ""
              ::= { fantray-entry 1 }
    
        fantray-present OBJECT-TYPE
              SYNTAX  INTEGER {
                    absent (0),
                    present (1)
                }
              ACCESS  read-only
              STATUS  mandatory
              DESCRIPTION
                      ""
              ::= { fantray-entry 2 }
    
        fantray-healthy OBJECT-TYPE
              SYNTAX  INTEGER {
                    unhealthy (0),
                    healthy (1)
                }
              ACCESS  read-only
              STATUS  mandatory
              DESCRIPTION
                      ""
              ::= { fantray-entry 3 }
    
        fantray-health-led OBJECT-TYPE
              SYNTAX  INTEGER {
                    off (0),
                    on (1)
                }
              ACCESS  read-write
              STATUS  mandatory
              DESCRIPTION
                      ""
              ::= { fantray-entry 4 }
    
        fantray-slave-address OBJECT-TYPE
              SYNTAX  INTEGER
              ACCESS  read-only
              STATUS  mandatory
              DESCRIPTION
                      ""
              ::= { fantray-entry 5 }
    
        fantray-fru-device-id OBJECT-TYPE
              SYNTAX  INTEGER
              ACCESS  read-only
              STATUS  mandatory
              DESCRIPTION
                      ""
              ::= { fantray-entry 6 }
    
        fantray-fruinfo-product-area-present OBJECT-TYPE
              SYNTAX  INTEGER {
                    absent (0),
                    present (1)
                }
              ACCESS  read-only
              STATUS  mandatory
              DESCRIPTION
                      ""
              ::= { fantray-entry 7 }
    
        fantray-fruinfo-product-manufacturer OBJECT-TYPE
              SYNTAX  DisplayString
              ACCESS  read-only
              STATUS  mandatory
              DESCRIPTION
                      ""
              ::= { fantray-entry 8 }
    
        fantray-fruinfo-product-name OBJECT-TYPE
              SYNTAX  DisplayString
              ACCESS  read-only
              STATUS  mandatory
              DESCRIPTION
                      ""
              ::= { fantray-entry 9 }
    
        fantray-fruinfo-product-part-model-number OBJECT-TYPE
              SYNTAX  DisplayString
              ACCESS  read-only
              STATUS  mandatory
              DESCRIPTION
                      ""
              ::= { fantray-entry 10 }
    
        fantray-fruinfo-product-version-number OBJECT-TYPE
              SYNTAX  DisplayString
              ACCESS  read-only
              STATUS  mandatory
              DESCRIPTION
                      ""
              ::= { fantray-entry 11 }
    
        fantray-fruinfo-product-serial-number OBJECT-TYPE
              SYNTAX  DisplayString
              ACCESS  read-only
              STATUS  mandatory
              DESCRIPTION
                      ""
              ::= { fantray-entry 12 }
    
        fantray-fruinfo-board-area-present OBJECT-TYPE
              SYNTAX  INTEGER {
                    absent (0),
                    present (1)
                }
              ACCESS  read-only
              STATUS  mandatory
              DESCRIPTION
                      ""
              ::= { fantray-entry 13 }
    
        fantray-fruinfo-board-manufacturer OBJECT-TYPE
              SYNTAX  DisplayString
              ACCESS  read-only
              STATUS  mandatory
              DESCRIPTION
                      ""
              ::= { fantray-entry 14 }
    
        fantray-fruinfo-board-product-name OBJECT-TYPE
              SYNTAX  DisplayString
              ACCESS  read-only
              STATUS  mandatory
              DESCRIPTION
                      ""
              ::= { fantray-entry 15 }
    
        fantray-fruinfo-board-serial-number OBJECT-TYPE
              SYNTAX  DisplayString
              ACCESS  read-only
              STATUS  mandatory
              DESCRIPTION
                      ""
              ::= { fantray-entry 16 }
    
        fantray-fruinfo-board-part-number OBJECT-TYPE
              SYNTAX  DisplayString
              ACCESS  read-only
              STATUS  mandatory
              DESCRIPTION
                      ""
              ::= { fantray-entry 17 }
    
        fantray-fruinfo-board-manufacture-time OBJECT-TYPE
              SYNTAX  INTEGER
              ACCESS  read-only
              STATUS  mandatory
              DESCRIPTION
                      ""
              ::= { fantray-entry 18 }
    



    -- powersupply          OBJECT IDENTIFIER ::= { ipm-sentry-shmm 34 }

    powersupply OBJECT-TYPE
              SYNTAX  SEQUENCE OF Powersupply-entry
              ACCESS  not-accessible
              STATUS  mandatory
              DESCRIPTION
                      "A list of power supplies"
              ::= { ipm-sentry-shmm 34 }

        powersupply-entry OBJECT-TYPE
              SYNTAX  Powersupply-entry
              ACCESS  not-accessible
              STATUS  mandatory
              DESCRIPTION
                      "A power supply entry"
              INDEX   { powersupply-slot-number }
              ::= { powersupply 1 }

        Powersupply-entry ::=
              SEQUENCE {
                  powersupply-slot-number
                        INTEGER,
                  powersupply-degrade
                        INTEGER,
                  powersupply-fail
                        INTEGER,
                  powersupply-inhibit
                        INTEGER,
                  powersupply-healthy
                        INTEGER,
                  powersupply-slave-address
                        INTEGER,
                  powersupply-fru-device-id
                        INTEGER,
                  powersupply-fruinfo-product-area-present
                        INTEGER,
                  powersupply-fruinfo-product-manufacturer
                        DisplayString,
                  powersupply-fruinfo-product-name
                        DisplayString,
                  powersupply-fruinfo-product-part-model-number
                        DisplayString,
                  powersupply-fruinfo-product-version-number
                        DisplayString,
                  powersupply-fruinfo-product-serial-number
                        DisplayString,
                  powersupply-fruinfo-board-area-present
                        INTEGER,
                  powersupply-fruinfo-board-manufacturer
                        DisplayString,
                  powersupply-fruinfo-board-product-name
                        DisplayString,
                  powersupply-fruinfo-board-serial-number
                        DisplayString,
                  powersupply-fruinfo-board-part-number
                        DisplayString,
                  powersupply-fruinfo-board-manufacture-time
                        INTEGER
              }

        powersupply-slot-number OBJECT-TYPE
              SYNTAX  INTEGER
              ACCESS  read-only
              STATUS  mandatory
              DESCRIPTION
                      ""
              ::= { powersupply-entry 1 }
    
        powersupply-degrade OBJECT-TYPE
              SYNTAX  INTEGER {
                    deasserted (0),
                    asserted (1)
                }
              ACCESS  read-only
              STATUS  mandatory
              DESCRIPTION
                      ""
              ::= { powersupply-entry 2 }
    
        powersupply-fail OBJECT-TYPE
              SYNTAX  INTEGER {
                    deasserted (0),
                    asserted (1)
                }
              ACCESS  read-only
              STATUS  mandatory
              DESCRIPTION
                      ""
              ::= { powersupply-entry 3 }
    
        powersupply-inhibit OBJECT-TYPE
              SYNTAX  INTEGER {
                    deasserted (0),
                    asserted (1)
                }
              ACCESS  read-write
              STATUS  mandatory
              DESCRIPTION
                      ""
              ::= { powersupply-entry 4 }
    
        powersupply-healthy OBJECT-TYPE
              SYNTAX  INTEGER {
                    unhealthy (0),
                    healthy (1)
                }
              ACCESS  read-only
              STATUS  mandatory
              DESCRIPTION
                      ""
              ::= { powersupply-entry 5 }
    
        powersupply-slave-address OBJECT-TYPE
              SYNTAX  INTEGER
              ACCESS  read-only
              STATUS  mandatory
              DESCRIPTION
                      ""
              ::= { powersupply-entry 6 }
    
        powersupply-fru-device-id OBJECT-TYPE
              SYNTAX  INTEGER
              ACCESS  read-only
              STATUS  mandatory
              DESCRIPTION
                      ""
              ::= { powersupply-entry 7 }
    
        powersupply-fruinfo-product-area-present OBJECT-TYPE
              SYNTAX  INTEGER {
                    absent (0),
                    present (1)
                }
              ACCESS  read-only
              STATUS  mandatory
              DESCRIPTION
                      ""
              ::= { powersupply-entry 8 }
    
        powersupply-fruinfo-product-manufacturer OBJECT-TYPE
              SYNTAX  DisplayString
              ACCESS  read-only
              STATUS  mandatory
              DESCRIPTION
                      ""
              ::= { powersupply-entry 9 }
    
        powersupply-fruinfo-product-name OBJECT-TYPE
              SYNTAX  DisplayString
              ACCESS  read-only
              STATUS  mandatory
              DESCRIPTION
                      ""
              ::= { powersupply-entry 10 }
    
        powersupply-fruinfo-product-part-model-number OBJECT-TYPE
              SYNTAX  DisplayString
              ACCESS  read-only
              STATUS  mandatory
              DESCRIPTION
                      ""
              ::= { powersupply-entry 11 }
    
        powersupply-fruinfo-product-version-number OBJECT-TYPE
              SYNTAX  DisplayString
              ACCESS  read-only
              STATUS  mandatory
              DESCRIPTION
                      ""
              ::= { powersupply-entry 12 }
    
        powersupply-fruinfo-product-serial-number OBJECT-TYPE
              SYNTAX  DisplayString
              ACCESS  read-only
              STATUS  mandatory
              DESCRIPTION
                      ""
              ::= { powersupply-entry 13 }
    
        powersupply-fruinfo-board-area-present OBJECT-TYPE
              SYNTAX  INTEGER {
                    absent (0),
                    present (1)
                }
              ACCESS  read-only
              STATUS  mandatory
              DESCRIPTION
                      ""
              ::= { powersupply-entry 14 }
    
        powersupply-fruinfo-board-manufacturer OBJECT-TYPE
              SYNTAX  DisplayString
              ACCESS  read-only
              STATUS  mandatory
              DESCRIPTION
                      ""
              ::= { powersupply-entry 15 }
    
        powersupply-fruinfo-board-product-name OBJECT-TYPE
              SYNTAX  DisplayString
              ACCESS  read-only
              STATUS  mandatory
              DESCRIPTION
                      ""
              ::= { powersupply-entry 16 }
    
        powersupply-fruinfo-board-serial-number OBJECT-TYPE
              SYNTAX  DisplayString
              ACCESS  read-only
              STATUS  mandatory
              DESCRIPTION
                      ""
              ::= { powersupply-entry 17 }
    
        powersupply-fruinfo-board-part-number OBJECT-TYPE
              SYNTAX  DisplayString
              ACCESS  read-only
              STATUS  mandatory
              DESCRIPTION
                      ""
              ::= { powersupply-entry 18 }
    
        powersupply-fruinfo-board-manufacture-time OBJECT-TYPE
              SYNTAX  INTEGER
              ACCESS  read-only
              STATUS  mandatory
              DESCRIPTION
                      ""
              ::= { powersupply-entry 19 }

    


    -- shelf-manager    OBJECT IDENTIFIER ::= { ipm-sentry-shmm 35 }

    shelf-manager OBJECT-TYPE
              SYNTAX  SEQUENCE OF Shelf-manager-entry
              ACCESS  not-accessible
              STATUS  mandatory
              DESCRIPTION
                      "A list of Shelf Manager instances"
              ::= { ipm-sentry-shmm 35 }

        shelf-manager-entry OBJECT-TYPE
              SYNTAX  Shelf-manager-entry
              ACCESS  not-accessible
              STATUS  mandatory
              DESCRIPTION
                      "A Shelf Manager instance"
              INDEX   { shelf-manager-instance }
              ::= { shelf-manager 1 }

        Shelf-manager-entry ::=
              SEQUENCE {
                  shelf-manager-instance
                        INTEGER,
                  shelf-manager-ipmc-slave-address
                        INTEGER,
                  shelf-manager-present
                        INTEGER,
                  shelf-manager-healthy
                        INTEGER,
                  shelf-manager-active
                        INTEGER,
                  shelf-manager-reset
                        INTEGER,
                  shelf-manager-fruinfo-product-area-present
                        INTEGER,
                  shelf-manager-fruinfo-product-manufacturer
                        DisplayString,
                  shelf-manager-fruinfo-product-name
                        DisplayString,
                  shelf-manager-fruinfo-product-part-model-number
                        DisplayString,
                  shelf-manager-fruinfo-product-version-number
                        DisplayString,
                  shelf-manager-fruinfo-product-serial-number
                        DisplayString,
                  shelf-manager-fruinfo-board-area-present
                        INTEGER,
                  shelf-manager-fruinfo-board-manufacturer
                        DisplayString,
                  shelf-manager-fruinfo-board-product-name
                        DisplayString,
                  shelf-manager-fruinfo-board-serial-number
                        DisplayString,
                  shelf-manager-fruinfo-board-part-number
                        DisplayString,
                  shelf-manager-fruinfo-board-manufacture-time
                        INTEGER
              }

        shelf-manager-instance OBJECT-TYPE
              SYNTAX  INTEGER
              ACCESS  read-only
              STATUS  mandatory
              DESCRIPTION
                      ""
              ::= { shelf-manager-entry 1 }
    
        shelf-manager-ipmc-slave-address OBJECT-TYPE
              SYNTAX  INTEGER
              ACCESS  read-only
              STATUS  mandatory
              DESCRIPTION
                      ""
              ::= { shelf-manager-entry 2 }
    
        shelf-manager-present OBJECT-TYPE
              SYNTAX  INTEGER {
                    absent (0),
                    present (1)
                }
              ACCESS  read-only
              STATUS  mandatory
              DESCRIPTION
                      ""
              ::= { shelf-manager-entry 3 }
    
        shelf-manager-healthy OBJECT-TYPE
              SYNTAX  INTEGER {
                    unhealthy (0),
                    healthy (1)
                }
              ACCESS  read-only
              STATUS  mandatory
              DESCRIPTION
                      ""
              ::= { shelf-manager-entry 4 }
    
        shelf-manager-active OBJECT-TYPE
              SYNTAX  INTEGER {
                    standby (0),
                    active (1)
                }
              ACCESS  read-write
              STATUS  mandatory
              DESCRIPTION
                      ""
              ::= { shelf-manager-entry 5 }
    
        shelf-manager-reset OBJECT-TYPE
              SYNTAX  INTEGER
              ACCESS  read-write
              STATUS  mandatory
              DESCRIPTION
                      ""
              ::= { shelf-manager-entry 6 }
    
        shelf-manager-fruinfo-product-area-present OBJECT-TYPE
              SYNTAX  INTEGER {
                    absent (0),
                    present (1)
                }
              ACCESS  read-only
              STATUS  mandatory
              DESCRIPTION
                      ""
              ::= { shelf-manager-entry 7 }
    
        shelf-manager-fruinfo-product-manufacturer OBJECT-TYPE
              SYNTAX  DisplayString
              ACCESS  read-only
              STATUS  mandatory
              DESCRIPTION
                      ""
              ::= { shelf-manager-entry 8 }
    
        shelf-manager-fruinfo-product-name OBJECT-TYPE
              SYNTAX  DisplayString
              ACCESS  read-only
              STATUS  mandatory
              DESCRIPTION
                      ""
              ::= { shelf-manager-entry 9 }
    
        shelf-manager-fruinfo-product-part-model-number OBJECT-TYPE
              SYNTAX  DisplayString
              ACCESS  read-only
              STATUS  mandatory
              DESCRIPTION
                      ""
              ::= { shelf-manager-entry 10 }
    
        shelf-manager-fruinfo-product-version-number OBJECT-TYPE
              SYNTAX  DisplayString
              ACCESS  read-only
              STATUS  mandatory
              DESCRIPTION
                      ""
              ::= { shelf-manager-entry 11 }
    
        shelf-manager-fruinfo-product-serial-number OBJECT-TYPE
              SYNTAX  DisplayString
              ACCESS  read-only
              STATUS  mandatory
              DESCRIPTION
                      ""
              ::= { shelf-manager-entry 12 }
    
        shelf-manager-fruinfo-board-area-present OBJECT-TYPE
              SYNTAX  INTEGER {
                    absent (0),
                    present (1)
                }
              ACCESS  read-only
              STATUS  mandatory
              DESCRIPTION
                      ""
              ::= { shelf-manager-entry 13 }
    
        shelf-manager-fruinfo-board-manufacturer OBJECT-TYPE
              SYNTAX  DisplayString
              ACCESS  read-only
              STATUS  mandatory
              DESCRIPTION
                      ""
              ::= { shelf-manager-entry 14 }
    
        shelf-manager-fruinfo-board-product-name OBJECT-TYPE
              SYNTAX  DisplayString
              ACCESS  read-only
              STATUS  mandatory
              DESCRIPTION
                      ""
              ::= { shelf-manager-entry 15 }
    
        shelf-manager-fruinfo-board-serial-number OBJECT-TYPE
              SYNTAX  DisplayString
              ACCESS  read-only
              STATUS  mandatory
              DESCRIPTION
                      ""
              ::= { shelf-manager-entry 16 }
    
        shelf-manager-fruinfo-board-part-number OBJECT-TYPE
              SYNTAX  DisplayString
              ACCESS  read-only
              STATUS  mandatory
              DESCRIPTION
                      ""
              ::= { shelf-manager-entry 17 }
    
        shelf-manager-fruinfo-board-manufacture-time OBJECT-TYPE
              SYNTAX  INTEGER
              ACCESS  read-only
              STATUS  mandatory
              DESCRIPTION
                      ""
              ::= { shelf-manager-entry 18 }

    


     chassis          OBJECT IDENTIFIER ::= { ipm-sentry-shmm 36 }

--    chassis OBJECT-TYPE
--              SYNTAX  Chassis
--              ACCESS  not-accessible
--              STATUS  mandatory
--              DESCRIPTION
--                      "Chassis variables"
--              ::= { ipm-sentry-shmm 36 }
--
--        Chassis ::=
--              SEQUENCE {
--                  chassis-id
--                        DisplayString,
--                  chassis-type
--                        INTEGER,
--                  chassis-part-number
--                        DisplayString,
--                  chassis-serial-number
--                        DisplayString,
--                  chassis-product-area-present
--                        INTEGER,
--                  chassis-product-manufacturer
--                        DisplayString,
--                  chassis-product-name
--                        DisplayString,
--                  chassis-product-part-model-number
--                        DisplayString,
--                  chassis-product-version-number
--                        DisplayString,
--                  chassis-product-serial-number
--                        DisplayString,
--                  chassis-board-area-present
--                        INTEGER,
--                  chassis-board-manufacturer
--                        DisplayString,
--                  chassis-board-product-name
--                        DisplayString,
--                  chassis-board-serial-number
--                        DisplayString,
--                  chassis-board-part-number
--                        DisplayString,
--                  chassis-board-manufacture-time
--                        INTEGER
--              }

        chassis-id OBJECT-TYPE
              SYNTAX  DisplayString
              ACCESS  read-write
              STATUS  mandatory
              DESCRIPTION
                      ""
              ::= { chassis 1 }
    
        chassis-type OBJECT-TYPE
              SYNTAX  INTEGER
              ACCESS  read-only
              STATUS  mandatory
              DESCRIPTION
                      ""
              ::= { chassis 2 }
    
        chassis-part-number OBJECT-TYPE
              SYNTAX  DisplayString
              ACCESS  read-only
              STATUS  mandatory
              DESCRIPTION
                      ""
              ::= { chassis 3 }
    
        chassis-serial-number OBJECT-TYPE
              SYNTAX  DisplayString
              ACCESS  read-only
              STATUS  mandatory
              DESCRIPTION
                      ""
              ::= { chassis 4 }
    
        chassis-product-area-present OBJECT-TYPE
              SYNTAX  INTEGER {
                    absent (0),
                    present (1)
                }
              ACCESS  read-only
              STATUS  mandatory
              DESCRIPTION
                      ""
              ::= { chassis 5 }
    
        chassis-product-manufacturer OBJECT-TYPE
              SYNTAX  DisplayString
              ACCESS  read-only
              STATUS  mandatory
              DESCRIPTION
                      ""
              ::= { chassis 6 }
    
        chassis-product-name OBJECT-TYPE
              SYNTAX  DisplayString
              ACCESS  read-only
              STATUS  mandatory
              DESCRIPTION
                      ""
              ::= { chassis 7 }
    
        chassis-product-part-model-number OBJECT-TYPE
              SYNTAX  DisplayString
              ACCESS  read-only
              STATUS  mandatory
              DESCRIPTION
                      ""
              ::= { chassis 8 }
    
        chassis-product-version-number OBJECT-TYPE
              SYNTAX  DisplayString
              ACCESS  read-only
              STATUS  mandatory
              DESCRIPTION
                      ""
              ::= { chassis 9 }
    
        chassis-product-serial-number OBJECT-TYPE
              SYNTAX  DisplayString
              ACCESS  read-only
              STATUS  mandatory
              DESCRIPTION
                      ""
              ::= { chassis 10 }
    
        chassis-board-area-present OBJECT-TYPE
              SYNTAX  INTEGER {
                    absent (0),
                    present (1)
                }
              ACCESS  read-only
              STATUS  mandatory
              DESCRIPTION
                      ""
              ::= { chassis 11 }
    
        chassis-board-manufacturer OBJECT-TYPE
              SYNTAX  DisplayString
              ACCESS  read-only
              STATUS  mandatory
              DESCRIPTION
                      ""
              ::= { chassis 12 }
    
        chassis-board-product-name OBJECT-TYPE
              SYNTAX  DisplayString
              ACCESS  read-only
              STATUS  mandatory
              DESCRIPTION
                      ""
              ::= { chassis 13 }
    
        chassis-board-serial-number OBJECT-TYPE
              SYNTAX  DisplayString
              ACCESS  read-only
              STATUS  mandatory
              DESCRIPTION
                      ""
              ::= { chassis 14 }
    
        chassis-board-part-number OBJECT-TYPE
              SYNTAX  DisplayString
              ACCESS  read-only
              STATUS  mandatory
              DESCRIPTION
                      ""
              ::= { chassis 15 }
    
        chassis-board-manufacture-time OBJECT-TYPE
              SYNTAX  INTEGER
              ACCESS  read-only
              STATUS  mandatory
              DESCRIPTION
                      ""
              ::= { chassis 16 }

    


    -- events           OBJECT IDENTIFIER ::= { ipm-sentry-shmm 37 }

    events OBJECT-TYPE
              SYNTAX  SEQUENCE OF Event-entry
              ACCESS  not-accessible
              STATUS  mandatory
              DESCRIPTION
                      "Event Log"
              ::= { ipm-sentry-shmm 37 }

        event-entry OBJECT-TYPE
              SYNTAX  Event-entry
              ACCESS  not-accessible
              STATUS  mandatory
              DESCRIPTION
                      "Event"
              INDEX   { event-index }
              ::= { events 1 }

        Event-entry ::=
              SEQUENCE {
                  event-index
                        INTEGER,
                  event-delete
                        INTEGER,
                  event-timestamp
                        INTEGER,
                  event-class
                        INTEGER,
                  event-type
                        INTEGER,
                  event-asserted
                        INTEGER,
                  event-origin-site-type
                        INTEGER,
                  event-origin-site-number
                        INTEGER,
                  event-origin-slave-address
                        INTEGER,
                  event-origin-fru-id
                        INTEGER,
                  event-origin-sensor-number
                        INTEGER
              }

        event-index OBJECT-TYPE
              SYNTAX  INTEGER
              ACCESS  read-only
              STATUS  mandatory
              DESCRIPTION
                      ""
              ::= { event-entry 1 }
    
        event-delete OBJECT-TYPE
              SYNTAX  INTEGER
              ACCESS  read-write
              STATUS  mandatory
              DESCRIPTION
                      ""
              ::= { event-entry 2 }
    
        event-timestamp OBJECT-TYPE
              SYNTAX  INTEGER
              ACCESS  read-only
              STATUS  mandatory
              DESCRIPTION
                      ""
              ::= { event-entry 3 }
    
        event-class OBJECT-TYPE
              SYNTAX  INTEGER {
                    other (0),
                    temperature (1),
                    voltage (2),
                    current (3),
                    fan (4),
                    hotSwap ('F0'H),
                    powerState ('E1'H)
                }
              ACCESS  read-only
              STATUS  mandatory
              DESCRIPTION
                      ""
              ::= { event-entry 4 }
    
        event-type OBJECT-TYPE
              SYNTAX  INTEGER {
                    other (0),
                    aboveUpperNonRecoverable (1),
                    aboveUpperCritical (2),
                    aboveUpperNonCritical (3),
                    belowLowerNonRecoverable (4),
                    belowLowerCritical (5),
                    belowLowerNonCritical (6),
                    inserted (7),
                    activated (8),
                    communicationLost (9),
                    communicationRestored (10),
                    deactivated (11),
                    extracted (12),
                    powerDegrade (13),
                    powerFail (14),
                    powerInhibit (15)
                }
              ACCESS  read-only
              STATUS  mandatory
              DESCRIPTION
                      ""
              ::= { event-entry 5 }
    
        event-asserted OBJECT-TYPE
              SYNTAX  INTEGER {
                    deasserted (0),
                    asserted (1)
                }
              ACCESS  read-only
              STATUS  mandatory
              DESCRIPTION
                      ""
              ::= { event-entry 6 }
    
        event-origin-site-type OBJECT-TYPE
              SYNTAX  INTEGER {
                    atcaBoard (0),
                    powerEntryModule (1),
                    shelfFruInfo (2),
                    dedicatedShMC (3),
                    fanTray (4),
                    fanFilterTray (5),
                    alarm (6),
                    atcaModule (7),
                    pmc (8),
                    cPCIBoardSlot ('C4'H),
                    powerSupply ('C5'H)
                }
              ACCESS  read-only
              STATUS  mandatory
              DESCRIPTION
                      ""
              ::= { event-entry 7 }
    
        event-origin-site-number OBJECT-TYPE
              SYNTAX  INTEGER
              ACCESS  read-only
              STATUS  mandatory
              DESCRIPTION
                      ""
              ::= { event-entry 8 }
    
        event-origin-slave-address OBJECT-TYPE
              SYNTAX  INTEGER
              ACCESS  read-only
              STATUS  mandatory
              DESCRIPTION
                      ""
              ::= { event-entry 9 }
    
        event-origin-fru-id OBJECT-TYPE
              SYNTAX  INTEGER
              ACCESS  read-only
              STATUS  mandatory
              DESCRIPTION
                      ""
              ::= { event-entry 10 }
    
        event-origin-sensor-number OBJECT-TYPE
              SYNTAX  INTEGER
              ACCESS  read-only
              STATUS  mandatory
              DESCRIPTION
                      ""
              ::= { event-entry 11 }
    
END
