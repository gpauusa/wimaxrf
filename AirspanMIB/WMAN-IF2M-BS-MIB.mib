WMAN-IF2M-BS-MIB DEFINITIONS ::= BEGIN
                                    
  IMPORTS
        MODULE-IDENTITY,
        OBJECT-TYPE,
        NOTIFICATION-TYPE,
        Unsigned32, Integer32, Counter32,
        Counter64, transmission
                FROM SNMPv2-SMI
        SnmpAdminString
                FROM SNMP-FRAMEWORK-MIB
        TEXTUAL-CONVENTION,
        MacAddress, RowStatus, TruthValue,
        TimeStamp, DateAndTime        
                FROM SNMPv2-TC
        InetAddressType, InetAddress
                FROM INET-ADDRESS-MIB
        OBJECT-GROUP,
        MODULE-COMPLIANCE,
        NOTIFICATION-GROUP
                FROM SNMPv2-CONF
        ifIndex
                FROM IF-MIB
        wman
                FROM WMAN-DEV-MIB;

wmanIf2mBsMib MODULE-IDENTITY
        LAST-UPDATED    "200802110000Z" -- February 11, 2008
        ORGANIZATION    "IEEE 802.16"
        CONTACT-INFO
            "WG E-mail: stds-802-16@ieee.org
             WG Chair:  Roger B. Marks
             Postal:    NextWave Broadband, Inc.
             E-mail:    r.b.marks@ieee.org
             
             TG Chair:  Phillip Barber
             Postal:    Huawei Technologies Co., Ltd
             E-mail:    pbarber@Huawei.com             

             Editor:    Joey Chou
             Postal:    Intel Corporation
                        5000 W. Chandler Blvd,
                        Chandler, AZ 85227, USA
             E-mail:    joey.chou@intel.com"                     
        DESCRIPTION
            "This MIB Module defines managed objects for Base Station
             based on IEEE Std 802.16. The MIB contains managed objects
             that are specific to mobile Broadband Wireless Networks."
        REVISION        "200802110000Z"
        DESCRIPTION
            "Includes changes as per comment resolutions agreed at the
             Levi meeting"
        REVISION        "200711300000Z"
        DESCRIPTION
            "The 1st revision of WMAN-IF2M-BS-MIB module."             
        ::= { wman 3 }

wmanIf2mBsCm OBJECT IDENTIFIER ::= { wmanIf2mBsMib 1 }
wmanIf2mBsPm OBJECT IDENTIFIER ::= { wmanIf2mBsMib 2 }
wmanIf2mBsFm OBJECT IDENTIFIER ::= { wmanIf2mBsMib 3 }
wmanIf2mBsSm OBJECT IDENTIFIER ::= { wmanIf2mBsMib 4 }
wmanIf2mBsAm OBJECT IDENTIFIER ::= { wmanIf2mBsMib 5 }

--
-- Textual Conventions
--                                                                                                              
WmanIf2mOfdmaMobility ::= TEXTUAL-CONVENTION
        STATUS      current
        DESCRIPTION
            "This field indicates whether or not the MS supports
             mobility hand-over, Slee-pmode, and Idle-mode. A bit value
             of 0 indicates 'not supported' while 1 indicates it is
             supported."
        REFERENCE
            "Subclause 11.7.14.1"
        SYNTAX      BITS {handoverSupport(0),
                          sleepModeSupport(1),
                          idleModeSupport(2)}

WmanIf2mHandoverType ::= TEXTUAL-CONVENTION
        STATUS      current
        DESCRIPTION
            "Indicates what type(s) of Handover the BS and the MS
             supports.
             bit#0: if set to 1, MDHO/FBSS HO not supported, the BS
                    shall ignore all other bits.
             bit#1: if set to 1, FBSS/MDHO DL RF Combining is supported
                    with monitoring MAPs from active BSs
             bit#2: if set to 1, MDHO DL soft Combining is supported
                    with monitoring single MAP from anchor BS 
             bit#3: if set to 1, MDHO DL soft combining is supported
                    with monitoring MAPs from active BSs
             bit#3: if set to 1, MDHO UL Multiple transmission is
                    supported"
        REFERENCE
            "Subclause 11.7.13.5"
        SYNTAX      BITS {mdhcFbssHoNotSpported(0),
                          mdhcFbssDlMapsFromActiveBss(1),
                          mdhcDlMapFromAnchorBs(2),
                          mdhcDlMapsFromActiveBss(3),
                          mdhcUlMultipleTx(4)}

WmanIf2mCidType ::= TEXTUAL-CONVENTION
        STATUS      current
        DESCRIPTION
            "Type of CID."                     
        SYNTAX      INTEGER (0 .. 65535)
        
WmanIf2mPsClassId ::= TEXTUAL-CONVENTION
        STATUS      current
        DESCRIPTION
            "Indicates the index to Power Saving Classes. The ID shall
             be unique within the group of Power Saving Classes
             associated with the MS. This ID may be used in further
             MOB_SLP-REQ/RSP messages for activation / deactivation of
             Power Saving Class."
        REFERENCE
            "Subclause 6.3.2.3.40"
        SYNTAX      INTEGER (0..63)

WmanIf2mPsClassType ::= TEXTUAL-CONVENTION
        STATUS      current
        DESCRIPTION
            "The types of power saving classes."
        REFERENCE
            "Table 551"
        SYNTAX      INTEGER {powerSavingClassTypeI(1),
                             powerSavingClassTypeII(2),
                             powerSavingClassTypeIII(3)}

WmanIf2mPsClassCidDir ::= TEXTUAL-CONVENTION
        STATUS      current
        DESCRIPTION
            "The direction of power saving class's CIDs.
             0b00 = Unspecified. Each CID has its own direction assign
                    in its connection creation. Can be DL, UL, or both
                    (in the case of management connections).
             0b01 = Downlink direction only.
             0b10 = Uplink direction only."
        REFERENCE
            "Subclause 6.3.2.3.44 in IEEE Std 802.16e-2005"
        SYNTAX      INTEGER {unspecified(0),
                             downlink(1),
                             uplink(2)}

WmanIf2mPowerSavingMode ::= TEXTUAL-CONVENTION
        STATUS      current
        DESCRIPTION
            "Operation of Power saving class mode.
                 0 = Deactivation of power saving class
                     (for types 1 and 2 only).
                 1 = Activation of power saving class."
        REFERENCE
            "Subclause 6.3.2.3.40"
        SYNTAX      INTEGER {deactionPs(0),
                             actionPs(1)}
                                                               
WmanIf2mSkipOptBitMap ::= TEXTUAL-CONVENTION
        STATUS      current
        DESCRIPTION
            "If set to 1, its corresponding field will be omitted."
        REFERENCE
            "Subclause 6.3.2.3.43"
        SYNTAX      BITS {omitOperatorId(0),
                          omitNeighborBsId(1),
                          omitHoProcOptimization(2),
                          omitQosRelatedField(3)}
                                    
WmanIf2mNbrBsId ::= TEXTUAL-CONVENTION
        STATUS      current
        DESCRIPTION     
            "The least significant 24 bits of the Base Station ID
             parameter in the DL-MAP message broadcast by the Neighbor
             BS. The BSID is a 6 byte number and follows the encoding
             rules of MacAddress textual convention, i.e. as if it were
             transmitted least-significant bit first. The value should
             be displayed with 2 parts clearly separated by a colon.
             Example 001DFF:00003A - 00003A is the Base Station ID. "
        REFERENCE
            "Subclause 6.3.2.3.43"
        SYNTAX      OCTET STRING (SIZE(3))

WmanIf2mNbrOperatorId ::= TEXTUAL-CONVENTION
        STATUS      current
        DESCRIPTION     
            "The most significant 24 bits of the Base Station ID
             parameter in the DL-MAP message broadcast by the Neighbor
             BS. The BSID is a 6 byte number and follows the encoding
             rules of MacAddress textual convention, i.e. as if it were
             transmitted least-significant bit first. The value should
             be displayed with 2 parts clearly separated by a colon.
             Example 001DFF:00003A - 001DFF is the Operator ID. "
        REFERENCE
            "Subclause 6.3.2.3.43"
        SYNTAX      OCTET STRING (SIZE(3))
                    
WmanIf2mPhyProfileId ::= TEXTUAL-CONVENTION
        STATUS      current
        DESCRIPTION
            "For systems using OFDM or OFDMA, the definition of the PHY
             Profile ID is shown as follows:
             bit#0: If set to 1, BS (or FA) is co-located with the
                    serving BS
             bit#1: If set to 1, the BS has the same number of FAs and
                    frequencies as the BS broadcasting the NBR-ADV
             bit#2: 0b00 = Unsynchronized
             bit#3: 0b01 = Time synchronization
                    0b10 = Time and Frequency synchronization   
                    If time synchronization is indicated for the OFDMA
                    PHY, then the downlink frames transmitted by the
                    serving BS and the Neighbor BS shall be synchronized
                    to a level of at least 1/8 cyclic prefix length. If
                    frequency synchronization is indicated for the OFDMA
                    PHY, then the BS reference clocks shall be
                    synchronized to a level that yields RF center
                    frequency offset of no more than 1% of the OFDMA
                    carrier spacing of the Neighbor BS. 
             bit#4: If set to 1, the BS EIRP follows the PHY Profile ID
             bit#5: 0b0- The DCD/UCD settings of this neighbor BS are
                         the same as those of the serving BS unless the
                         TLV information specifies. 
                    0b1- The DCD/UCD settings of this neighbor BS are
                         the same as those of the preceding neighbor BS
                         unless the TLV information specifies.
             bit#6: If set to 1, the FA Index follows the PHY Profile ID.
                    In addition, if the FA Indicator is followed, the DL
                    center frequency shall be omitted in the DCD/UCD
                    difference TLV information.
             bit#7: The Trigger Reference Indicator is related to the
                    Neighbor BS trigger metric TLV information of this
                    neighbor BS.
                    0b0- The trigger settings of this neighbor BS are
                         the same as those provided by the serving BS
                         (via DCD).If the TLV information is present, it
                         overrides values inherited from preceding
                         neighbor BS.
                    0b1- The trigger settings of this neighbor BS are
                         the same as those of the preceding neighbor BS."
        REFERENCE
            "Table 142"
        SYNTAX      BITS {colocatedFaInd(0),
                          faConfigInd(1),
                          timeFreqSyncInd1(2),
                          timeFreqSyncInd2(3),
                          bsEirpInd(4),
                          dcdUcdRefInd(5),
                          faIndexInd(6),
                          triggRefInd(7)}        


WmanIf2mHoProcOptm ::= TEXTUAL-CONVENTION
        STATUS      current
        DESCRIPTION
            "For each Bit location, a value of '0' indicates the
             associated reentry management messages shall be required,
             a value of '1' indicates the reentry management message may
             be omitted. Regardless of the HO Process Optimization TLV
             settings, the target BS may send unsolicited SBC-RSP and/ or
             REG-RSP management messages
             bit#0: Omit SBC-REQ/RSP management messages during re-entry
                    processing
             bit#1: Omit PKM Authentication phase except TEK phase during
                    current re-entry processing
             bit#2: Omit PKM TEK creation phase during reentry processing
             bit#3: Omit REG-REQ/RSP management during current re-entry
                    processing
             bit#4: Omit Network Address Acquisition management messages
                    during current reentry processing
             bit#5: Omit Time of Day Acquisition management messages
                    during current reentry processing
             bit#6: Omit TFTP management messages during current re-entry
                    processing
             bit#7: Full service and operational state transfer or
                    sharing between serving BS and target BS (ARQ, timers
                    , counters, MAC state machines, etc...)"
        REFERENCE
            "Table 109f in IEEE Std 802.16e-2005"
        SYNTAX      BITS {omitSbcReq(0),
                          omitPkmAuth(1),
                          omitPkmTek(2),
                          omitRegReq(3),
                          omitNtwkAddrAcq(4),
                          omitTimeOfDay(5),
                          omitTftp(6),
                          fullService(7)}

WmanIf2mSchedulingSupp ::= TEXTUAL-CONVENTION
        STATUS      current
        DESCRIPTION
            "Bitmap to indicate if BS supports a particular scheduling
             service. 1 indicates support, 0 indicates not support:
             
             bit#0: Unsolicited Grant Service (UGS)
             bit#1: Real-time Polling Service (rtPS)
             bit#2: Non-real-time Polling Service (nrtPS)
             bit#3: Best Effort
             bit#4: Extended real-time Polling Service (ertPS)

             If the value of bit 0 through bit 4 is 0b00000, it indicates
             no information on service available."
        REFERENCE
            "Table 109f in IEEE Std 802.16e-2005"
        SYNTAX      BITS {ugs(0),
                          rtPs(1),
                          nrtPs(2),
                          be(3),
                          ertPs(4)}
                          
WmanIf2mMacVersion ::= TEXTUAL-CONVENTION
        STATUS      current
        DESCRIPTION
            "Version number of IEEE 802.16."
        REFERENCE
            "Subclause 11.1.3"
        SYNTAX      INTEGER {ieee802Dot16Of2001(1),
                             ieee802Dot16cOf2002andPredcessors(2),
                             ieee802Dot16aOf2003andPredcessors(3),
                             ieee802Dot16Of2004(4),
                             ieee802Dot16Of2004and16eOf2005(5),
                             ieee802Dot16Of2004and16efOf2005(6),
                             ieee802Dot16Of04and16efOf05and16gOf07(7),
                             ieee802Dot16Of2008(8)}

WmanIf2mHarqAckDelay ::= TEXTUAL-CONVENTION
        STATUS      current
        DESCRIPTION
            "HARQ ACK delay for UL and DL bursts
               1 = one frame offset
               2 = two frames offset
               3 = three frames offset"
        REFERENCE
            "Table 353 in IEEE Std 802.16e-2005"
        SYNTAX      INTEGER {oneframeoffset(1),
                             twoframesoffset(2),
                             threeframesoffset(3)}                             
        
WmanIf2mPowerSaveType ::= TEXTUAL-CONVENTION
        STATUS      current
        DESCRIPTION
            "For MS supporting sleep mode, this parameter defines the
             capability of the MS supporting different power save class
             types in sleep mode.
             A bit 0 - 'not supported'
                   1 - 'supported'"
        REFERENCE
            "Subclause 11.7.4.2"
        SYNTAX      BITS {psClassTypeI(0),
                          psClassTypeII(1),
                          psClassTypeIII(2)}
                                  
WmanIf2mHoTrigMatrix ::= TEXTUAL-CONVENTION
        STATUS      current
        DESCRIPTION
            "This field indicates trigger metrics that MS or BS supports.
             A bit 0 - 'not supported'
                   1 - 'supported'"
        REFERENCE
            "Subclause 11.8.7 in IEEE Std 802.16e-2005"
        SYNTAX      BITS {bsCinrMean(0),
                          bsRssiMean(1),
                          relativeDelay(2),
                          bsRoundTripDelay(3)}
        
WmanIf2mAssociationTyp ::= TEXTUAL-CONVENTION
        STATUS      current
        DESCRIPTION
            "This field indicates the association level supported by the
             MS or the BS. If a bit is set to '1', then MS or BS
             indicates support at the respective association type and
             level. The MS may associate according to arrangements by
             the BS at levels up to and including the one for which the
             MS has indicated support."
        REFERENCE
            "Subclause 11.8.8 in IEEE Std 802.16e-2005"
        SYNTAX      BITS {scanWoAssociation(0),
                          scanOrAssocWoCoordination(1),
                          assocWithCoordination(2),
                          ntwkAssistAssociation(3),
                          directAssociation(4)}

WmanIf2mOfdmaFftSize ::= TEXTUAL-CONVENTION
        STATUS      current
        DESCRIPTION
            "FFT size for OFDMA PHY
             0b00 = 2048
             0b01 = 1024
             0b10 = 512
             0b11 = 128"
        REFERENCE
            "Subclause 11.18.1, Table 574"
        SYNTAX      INTEGER {fft2048(0),
                             fft1024(1),
                             fft512(2),
                             fft128(3)}                          

WmanIf2mOfdmaCp ::= TEXTUAL-CONVENTION
        STATUS      current
        DESCRIPTION
            "Cycle prefix for OFDMA PHY
             0b00 = 1/4
             0b01 = 1/8
             0b10 = 1/16
             0b11 = 1/32"
        REFERENCE
            "Subclause 11.18.1, Table 574"
        SYNTAX      INTEGER {oneForth(0),
                             oneEighth(1),
                             oneSixteenth(2),
                             oneThirtySecond(3)}

WmanIf2mOfdmaFrame ::= TEXTUAL-CONVENTION
        STATUS      current
        DESCRIPTION
            "Frame duration for OFDMA PHY
             0b0000 = 2.0 ms
             0b0001 = 2.5 ms
             0b0010 = 4 ms
             0b0011 = 5 ms
             0b0100 = 8 ms
             0b0101 = 10 ms
             0b0110 = 12.5 ms
             0b0111 = 20 ms"
        REFERENCE
            "Subclause 11.18.1, Table 574"
        SYNTAX      INTEGER {twoMs(0),
                             twoPointFiveMs(1),
                             fourMs(2),
                             fiveMs(3),
                             eightMs(4),
                             tenMs(5),
                             twelvePointFiveMs(6),
                             twentyMs(7)}

WmanIf2mPagingAction ::= TEXTUAL-CONVENTION
        STATUS      current
        DESCRIPTION
            "Paging action instruction to MS
             0b00 = No Action Required
             0b01 = Perform Ranging to establish location and
                    acknowledge message
             0b10 = Enter Network"
        REFERENCE
            "Subclause 6.3.2.3.52, Table 152"
        SYNTAX      INTEGER {noAction(0),
                             performRanging(1),
                             enterNetwork(2)}

WmanIf2mSsMacAddrHash ::= TEXTUAL-CONVENTION
        STATUS      current
        DESCRIPTION
        	"24 bit SS MAC address hash that is obtained by computing a
        	 CRC24 on the MS 48-bit MAC address."
        REFERENCE
            "Subclause 6.3.2.3.52, Table 152"
        SYNTAX      OCTET STRING (SIZE(3))                             
                                                       
WmanIf2mSfState ::= TEXTUAL-CONVENTION
        STATUS      current
        DESCRIPTION     
            "Defines the state of a service flow.
             'inactive' - A service flow is inactive, when the MS owns
                          this service flow has handoff to another BS.
             'provisioned' - A service flow is provisioned, but not
                             yet activated. 
             'admitted' - This maps to the 1st phase of the two-phase
                          activation model that the bandwidth a service
                          flow is reserved. But, no traffic can be
                          sent on this service flow yet.
             'active' - This maps to the 2nd phase of the two-phase
                        activation model that bandwidth is granted,
                        (e.g., is actively sending UL maps containing
                        unsolicited grants for a UGS service flow)."
        REFERENCE
            "Subclause 6.3.14.2"
        SYNTAX      INTEGER {inactive(0),
                             provisioned(1),
                             admitted(2),
                             active(3)}

WmanIf2mGlobalSrvClass ::= TEXTUAL-CONVENTION
        STATUS      current
        DESCRIPTION
            "Global Service Class Name contains 8 information fields
             that map to predefined QoS attributes as shown in
             subclause 6.3.14.4.1.
              
             bit#0:     Uplink/Downlink indicator
                        0 - uplink
                        1 - downlink
             bit#1-6:   Maximum sustained traffic rate in bps that is
                        defined in Table 124b  
             bit#7:     0 - no traffic indication
                        1 - traffic indication
             bit#8-13:  Maximum traffic burst defines the maximum burst
                        size that must be accommodated for the service. 
             bit#14-19: Minimum reserved traffic rate parameter
                        specifies the minimum rate, in bits per second,
                        reserved for this service flow.
             bit#20-25: Maximum latency specifies the maximum interval
                        between the reception of a packet at CS of BS
                        or SS and the arrival of the packet to the peer
                        device.
             bit#26:    SDU indicator specifies whether the SDUs on the
                        service flow are fixed-length or variable-length.
                        0 - variable length
                        1 - fixed length
             bit#27:    Paging indicator of an MS preference for the
                        reception of paging advisory messages during
                        idle mode. When set, it indicates that the BS
                        may present paging advisory messages or other
                        indicative messages to the MS when data SDUs
                        bound for the MS are present while the MS is in
                        Idle Mode.
                        0 - no paging generation
                        1 - paging generation
             bit#28-35: Req/Tx Policy - An attribute is enabled by
                        setting the corresponding bit position to 1. For
                        attributes affecting UL BR types, a value of
                        zero indicates the default actions described in
                        the scheduling service description in 6.3.5
                        shall be used. A value of 1 indicates that the
                        action associated with the attribute bit
                        overrides the default action.
                 bit28: No broadcast BR opportunities. (UL only)
                 bit29: No use multicast BR opportunities. (UL only)
                 bit30: No piggyback requests with data. (UL only)
                 bit31: No fragment data.
                 bit32: No suppress payload headers (CS parameter).
                 bit33: No pack multiple SDUs (or fragments) into single
                        MAC PDUs.
                 bit34: Not include CRC in the MAC PDU.
                 bit35: Reserved
             bit#36-38: The value of this parameter specifies the UL
                        grant scheduling type that shall be enabled for
                        the associated UL service flow (see 6.3.5.2).
                 Value = 1: Undefined (BS implementation-dependenta)
                         2: BE (default)
                         3: nrtPS
                         4: rtPS
                         5: Extended rtPS
                         6: UGS"
        REFERENCE
            "Subclause 6.3.14.4.1 Table 124a in IEEE Std 802.16e-2005"
        SYNTAX      BITS {ulDlIndicator(0),
                          maxSustainedRate0(1),
                          maxSustainedRate1(2),
                          maxSustainedRate2(3),
                          maxSustainedRate3(4),
                          maxSustainedRate4(5),
                          maxSustainedRate5(6),
                          trafficIndication(7),
                          maxTrafficBurst0(8),
                          maxTrafficBurst1(9),
                          maxTrafficBurst2(10),
                          maxTrafficBurst3(11),
                          maxTrafficBurst4(12),
                          maxTrafficBurst5(13),
                          minReservedRate0(14),
                          minReservedRate1(15),
                          minReservedRate2(16),
                          minReservedRate3(17),
                          minReservedRate4(18),
                          minReservedRate5(19),
                          maxLatency0(20),
                          maxLatency1(21),
                          maxLatency2(22),
                          maxLatency3(23),
                          maxLatency4(24),
                          maxLatency5(25),
                          sduIndicator(26),
                          pagingGeneration(27),
                          noBroadcastBr(28),
                          noMulticastBr(29),
                          noPiggybackReq(30),
                          noFragmentData(31),
                          noSurpressPayload(32),
                          noPackedSdu(33),
                          noCrcInMacPdu(34),
                          ulGrantType0(35),
                          ulGrantType1(36),
                          ulGrantType2(37)}

WmanIf2mSfDirection ::= TEXTUAL-CONVENTION
        STATUS      current
        DESCRIPTION
            "The direction of a service flow"
        SYNTAX      INTEGER {downstream(1),
                             upstream(2)}

WmanIf2mReqTxPolicy ::= TEXTUAL-CONVENTION
        STATUS      current
        DESCRIPTION
            "Specify certain attributes for the associated service
             flow. An attribute is enabled by setting the
             corresponding bit position to 1.
              
             bit#0: Service flow shall not use broadcast bandwidth
                    request opportunities. (Uplink only)
             bit#1: Service flow shall not use multicast BR
                    opportunities. (UL only)
             bit#2: The service flow shall not piggyback requests with
                    data. (Uplink only)
             bit#3: The service flow shall not fragment data.
             bit#4: The service flow shall not suppress payload headers
                    (CS parameter)     
             bit#5: The service flow shall not pack multiple SDUs (or
                    fragments) into single MAC PDUs.
             bit#6: The service flow shall not include CRC in the MAC
                    PDU." 
        REFERENCE
            "Subclause 11.13.12"
        SYNTAX      BITS {noBroadcastBwReq(0),
                          noMulticastBwReq(1),
                          noPiggybackReq(2),
                          noFragmentData(3),
                          noPHS(4),
                          noSduPacking(5),
                          noCrc(6),
                          reserved2(7)}

WmanIf2mPhsRuleVerify ::= TEXTUAL-CONVENTION
        STATUS      current
        DESCRIPTION
            "The value of this field indicates to the sending entity   
             whether or not the packet header contents are to be
             verified prior to performing suppression. If PHSV is
             enabled, the sender shall compare the bytes in the packet
             header with the bytes in the PHSF that are to be
             suppressed as indicated by the PHSM."
        REFERENCE
            "Subclause 11.13.19.3.7.5"
        SYNTAX      INTEGER {phsVerifyEnable(0),
                             phsVerifyDisable(1)}

WmanIf2mSchedulingType ::= TEXTUAL-CONVENTION
        STATUS      current
        DESCRIPTION     
            "The scheduling service provided by a SC for an
             upstream service flow. If the parameter is omitted
             from an upstream QOS Parameter Set, this object takes
             the value of bestEffort (2). This parameter must be
             reported as undefined (1) for downstream QOS Parameter
             Sets."
        REFERENCE
            "Subclause 11.13.11"
        SYNTAX      INTEGER {undefined(1),
                             bestEffort(2),
                             nonRealTimePollingService(3),
                             realTimePollingService(4),
                             extRealTimePollingService(5),
                             unsolicitedGrantService(6)}
                                                                                                                                                                               
WmanIf2mCsSpecification ::= TEXTUAL-CONVENTION
        STATUS      current
        DESCRIPTION     
            "Defines the types of convergence sublayer."
        REFERENCE
            "Subclause 11.13.19.1"
        SYNTAX      INTEGER {reserved(0),
                             packetIpV4(1),
                             packetIpV6(2),
                             packet802dot3Ethernet(3),
                             reserved4(4),
                             packetIpV4Over802dot3(5),
                             packetIpV6Over802dot3(6),
                             reserved7(7),
                             reserved8(8),
                             atm(9),
                             packet802dot3EthernetRohcHc(10),
                             packet802dot3EthernetEcrtpHc(11),
                             packetIpRohcHc(12),
                             packetIpEcrtpHc(13),
                             packetIp(14)}

WmanIf2mIpv6FlowLabel ::= TEXTUAL-CONVENTION
        STATUS      current
        DESCRIPTION     
            "The value of this field specifies the matching values for
             the IPv6 Flow label field. As the flow label field has a
             length of 20 bits, the first 4 bits of the most
             significant byte shall be set to 0x0 and disregarded."
        SYNTAX      OCTET STRING (SIZE(3))
        
WmanIf2mClassifierBitMap ::= TEXTUAL-CONVENTION
        STATUS      current
        DESCRIPTION     
            "A bit of of this object is set to 1 if the parameter
             indicated by the comment was present in the classifier
             encoding, and 0 otherwise.
             Note: that BITS are encoded most significant bit first,
             so that if e.g. bits 6 and 7 are set, this object is
             encoded as the octet string '030000'H."
        REFERENCE
            "Subclause 11.13.19.3.4"
        SYNTAX      BITS {priority(0),
                          ipTos(1),
                          ipProtocol(2),
                          ipMaskedSrcAddr(3),
                          ipMaskedDestAddr(4),
                          srcPort(5),
                          destPort(6),
                          destMacAddr(7),
                          srcMacAddr(8),
                          ethernetProtocol(9),
                          userPriority(10),
                          vlanId(11),
                          ipv6FlowLabel(12)}                                     

WmanIf2mReportMode ::= TEXTUAL-CONVENTION
        STATUS      current
        DESCRIPTION     
            "Action code for an MS's report of CINR measurement: 
            
             0b00: The MS measures channel quality of the Available BSs
                   without reporting.
             0b01: The MS reports the result of the measurement to
                   Serving BS periodically. The period of reporting is
                   different from that of scanning.
             0b10: The MS reports the result of the measurement to
                   Serving BS after each measurement."
        REFERENCE
            "Subclause 6.3.2.3.49 in IEEE Std 802.16e-2005"
        SYNTAX      INTEGER {noReport(0),
                             periodicReport(1),
                             eventTriggeredReport(2)}

WmanIf2mReportMatric ::= TEXTUAL-CONVENTION
        STATUS      current
        DESCRIPTION     
            "Bitmap indicator of trigger metrics that the serving BS
             requests the MS to report. Serving BS shall indicate only
             the trigger metrics agreed during SBC-REQ/RSP negotiation.
             Each bit indicates whether reports will be initiated by
             trigger based on the corresponding metric:

               Bit 0:    BS CINR mean
               Bit 1:    BS RSSI mean
               Bit 2:    Relative delay
               Bit 3:    BS RTD; this metric shall be only measured on
                         serving BS/anchor BS"
        REFERENCE
            "Subclause 6.3.2.3.45"
        SYNTAX      BITS {bsCinrMean(0),
                          bsRssiMean(1),
                          relativeDelay(2),
                          bsRtd(3)}

WmanIf2mFullBsId ::= TEXTUAL-CONVENTION
        STATUS      current
        DESCRIPTION     
            "The 48 bit field sent in the DL-MAP message to identifies
             the BS."
        REFERENCE
            "Subclause 6.3.2.3.44"
        SYNTAX      OCTET STRING (SIZE(6))


WmanIf2mScanType ::= TEXTUAL-CONVENTION
        STATUS      current
        DESCRIPTION     
            "Type of scanning or association used by the MS and
             coordinated by the Serving BS: 
            
             0b000: Scanning without Association Scanning
             0b001: Scanning with Association level 0: association
                    without coordination
             0b010: Scanning with Association level 1: association
                    with coordination
             0b011: Scanning with Association level 2: network assisted
                    association"
        REFERENCE
            "Subclause 6.3.2.3.44"
        SYNTAX      INTEGER {scanWoAssociation(0),
                             scanWithAssociation0(1),
                             scanWithAssociation1(2),
                             scanWithAssociation2(3)}

WmanIf2mBsSsCapType ::= TEXTUAL-CONVENTION
        STATUS      current
        DESCRIPTION
            "xxxReq: Indicates that SS reports its capabilities in
                     RNG-REQ, SBC-REQ, or REG-REQ messages.
             xxxRsp: Indicates that BS confirms SS capabilities in
                     RNG-RSP, SBC-RSP, or REG-RSP messages."
        SYNTAX INTEGER {xxxReq (1),
                        xxxRsp (2)}

WmanIf2mBsCapType ::= TEXTUAL-CONVENTION
        STATUS      current
        DESCRIPTION
            "inheritedBsCap: Indicates BS' basic HW and SW capabilities.
             configedBsCap: Indicates BS' capabilities that has been
                            configured."
        SYNTAX      INTEGER {inheritedBsCap (1),
                             configedBsCap (2)}

WmanIf2mTrafficWkFlag ::= TEXTUAL-CONVENTION
        STATUS      current
        DESCRIPTION
            "Traffic Triggered Wakening flag"
        REFERENCE
            "Subclause 6.3.19.40"
        SYNTAX      INTEGER {psNotBeDeactivated(1),
                             psBeDeactivated(2)}

                  
--
-- wmanIf2mBsCm contain the Base Station Configuration Management
-- objects
--

--
-- Base Station configuration
--
wmanIf2mBsConfiguration OBJECT IDENTIFIER ::= { wmanIf2mBsCm 1 }

--
-- wmanIf2mBsConfigurationTable contains global parameters for BS      
--
wmanIf2mBsConfigurationTable OBJECT-TYPE
        SYNTAX      SEQUENCE OF WmanIf2mBsConfigurationEntry
        MAX-ACCESS  not-accessible
        STATUS      current
        DESCRIPTION
            "This table contains one row for the BS system parameters."
        REFERENCE
            "Subclause 10.1, Table 342 in IEEE Std 802.16e-2005"
        ::= { wmanIf2mBsConfiguration 1 }

wmanIf2mBsConfigurationEntry OBJECT-TYPE
        SYNTAX      WmanIf2mBsConfigurationEntry
        MAX-ACCESS  not-accessible
        STATUS      current
        DESCRIPTION
            ""
        INDEX     { ifIndex }
        ::= { wmanIf2mBsConfigurationTable 1 }

WmanIf2mBsConfigurationEntry ::= SEQUENCE {
        wmanIf2mBsMobNbrAdvInterval             INTEGER,
        wmanIf2mBsAscAgingTimer                 INTEGER,
        wmanIf2mBsPagingRetryCount              INTEGER,
        wmanIf2mBsModeSelectFeedbackProcTime    INTEGER,
        wmanIf2mBsIdleModeSystemTimer           Unsigned32,
        wmanIf2mBsMgmtResourceHoldingTimer      INTEGER,
        wmanIf2mBsDregCommandRetryCount         INTEGER,
        wmanIf2mBsT46Timer                      INTEGER,
        wmanIf2mBsT47Timer                      INTEGER,
        wmanIf2mBsPagingInterval                INTEGER,
        wmanIf2mBs2ndMgmtDlQoSProfileIndex      INTEGER,
        wmanIf2mBs2ndMgmtUlQoSProfileIndex      INTEGER,
        wmanIf2mBsBasicCidDlQosProfileIndex     INTEGER,
        wmanIf2mBsBasicCidUlQosProfileIndex     INTEGER,        
        wmanIf2mBsPrimaryCidDlQosProfileIndex   INTEGER,
        wmanIf2mBsPrimaryCidUlQosProfileIndex   INTEGER}
                                                      
wmanIf2mBsMobNbrAdvInterval OBJECT-TYPE
        SYNTAX      INTEGER (1 .. 30)
        UNITS       "seconds"
        MAX-ACCESS  read-write
        STATUS      current
        DESCRIPTION
        	"Nominal time between transmission of MOB_NBR-ADV messages"
        ::= { wmanIf2mBsConfigurationEntry 1 }

wmanIf2mBsAscAgingTimer OBJECT-TYPE
        SYNTAX      INTEGER (100 .. 10000)            
        UNITS       "milliseconds"
        MAX-ACCESS  read-write
        STATUS      current
        DESCRIPTION
            "Nominal time for aging of MS associations"
        ::= { wmanIf2mBsConfigurationEntry 2 }

wmanIf2mBsPagingRetryCount OBJECT-TYPE
        SYNTAX      INTEGER (1 .. 16)
        MAX-ACCESS  read-write
        STATUS      current
        DESCRIPTION
            "Number of retries on paging transmission. If the BS does
             not receive RNG-REQ from the MS until this value decreases
             to zero, it determines that the MS is unavailable."
        DEFVAL      { 3 }
        ::= { wmanIf2mBsConfigurationEntry 3 }

wmanIf2mBsModeSelectFeedbackProcTime OBJECT-TYPE
        SYNTAX      INTEGER (1 .. 65535)
        UNITS       "microseconds"
        MAX-ACCESS  read-write
        STATUS      current
        DESCRIPTION
            "The time allowed between the end of the burst carrying the
             Mode Selection Feedback subheader and the start of the UL
             subframe carrying the Mode Selection Feedback response.
             Minimum value = 1 frame duration for TDD
                             1/2 Frame duration for FDD"
        ::= { wmanIf2mBsConfigurationEntry 4 }

wmanIf2mBsIdleModeSystemTimer OBJECT-TYPE
        SYNTAX      Unsigned32 (128 .. 65536)
        UNITS       "seconds"
        MAX-ACCESS  read-write
        STATUS      current
        DESCRIPTION
            "For BS acting as Paging Controller, timed interval to
             receive notification of MS Idle Mode Location Update. Set
             timer to MS Idle Mode Timeout. Timer recycles on
             successful Idle Mode Location Update."
        DEFVAL      { 4096 }
        ::= { wmanIf2mBsConfigurationEntry 5 }

wmanIf2mBsMgmtResourceHoldingTimer OBJECT-TYPE
        SYNTAX      INTEGER (1 .. 1000)
        UNITS       "milliseconds"
        MAX-ACCESS  read-write
        STATUS      current
        DESCRIPTION
            "Time the BS maintain connection information with the MS
             after the BS send DREG-CMD to the MS."
        DEFVAL      { 500 }
        ::= { wmanIf2mBsConfigurationEntry 6 }
                
wmanIf2mBsDregCommandRetryCount OBJECT-TYPE
        SYNTAX      INTEGER (3 .. 16)
        MAX-ACCESS  read-write
        STATUS      current
        DESCRIPTION
            "Number of retries on DREG Command Message."
        DEFVAL      { 3 }
        ::= { wmanIf2mBsConfigurationEntry 7 }

wmanIf2mBsT46Timer OBJECT-TYPE
        SYNTAX      INTEGER (1 .. 65535)
        UNITS       "milliseconds"
        MAX-ACCESS  read-write
        STATUS      current
        DESCRIPTION
            "Time the BS waits for DREG-REQ in case of unsolicited Idle
             Mode initiation from BS."
        ::= { wmanIf2mBsConfigurationEntry 8 }
        
wmanIf2mBsT47Timer OBJECT-TYPE
        SYNTAX      INTEGER (8 .. 1024)
        UNITS       "frames"
        MAX-ACCESS  read-write
        STATUS      current
        DESCRIPTION
            "PMC_RSP Timer: BS shall send the PMC_RSP before T47 + 1
             frames after BS receives PMC_REQ (confirmation = 0)
             correctly."
        DEFVAL      { 64 }
        ::= { wmanIf2mBsConfigurationEntry 9 }        

wmanIf2mBsPagingInterval OBJECT-TYPE
        SYNTAX      INTEGER (8 .. 1024)
        UNITS       "frames"
        MAX-ACCESS  read-write
        STATUS      current
        DESCRIPTION
            "Time duration of Paging Interval of the BS."
        DEFVAL      { 64 }
        ::= { wmanIf2mBsConfigurationEntry 10 }
        
wmanIf2mBs2ndMgmtDlQoSProfileIndex OBJECT-TYPE
        SYNTAX      INTEGER (1..65535)
        MAX-ACCESS  read-write
        STATUS      current
        DESCRIPTION
            "This object defines the index of a row in
             wmanIf2mBsQoSProfileTable which is used to obtain all QoS
             parameters required for the BS downlink scheduler to
             properly allocate and manage the bandwidth and schedule
             the 2nd Management Connection traffic. The 2nd Management
             Connection traffic doesn't differ from Traffic Connection
             traffic in the area of QoS management."
        ::= { wmanIf2mBsConfigurationEntry 11 }

wmanIf2mBs2ndMgmtUlQoSProfileIndex OBJECT-TYPE
        SYNTAX      INTEGER (1..65535)
        MAX-ACCESS  read-write
        STATUS      current
        DESCRIPTION
            "This object defines the index of a row in
             wmanIf2mBsQoSProfileTable which is used to obtain all QoS
             parameters required for the BS uplink scheduler to
             properly allocate and manage the bandwidth and schedule
             the 2nd Management Connection traffic. The 2nd Management
             Connection traffic doesn't differ from Traffic Connection
             traffic in the area of QoS management."
        ::= { wmanIf2mBsConfigurationEntry 12 }

wmanIf2mBsBasicCidDlQosProfileIndex OBJECT-TYPE
        SYNTAX      INTEGER (1 .. 65535)
        MAX-ACCESS  read-write
        STATUS      current
        DESCRIPTION
            "This index points to an entry in wmanIf2mBsQoSProfileTable
             that defines the QoS parameter set for downlink basic CID."
        ::= { wmanIf2mBsConfigurationEntry 13 }

wmanIf2mBsBasicCidUlQosProfileIndex OBJECT-TYPE
        SYNTAX      INTEGER (1 .. 65535)
        MAX-ACCESS  read-write
        STATUS      current
        DESCRIPTION
            "This index points to an entry in wmanIf2mBsQoSProfileTable
             that defines the QoS parameter set for uplink basic CID."
        ::= { wmanIf2mBsConfigurationEntry 14 }        

wmanIf2mBsPrimaryCidDlQosProfileIndex OBJECT-TYPE
        SYNTAX      INTEGER (1 .. 65535)
        MAX-ACCESS  read-write
        STATUS      current
        DESCRIPTION
            "This index points to an entry in wmanIf2mBsQoSProfileTable
             that defines the QoS parameter set for downlink primary CID
             ."
        ::= { wmanIf2mBsConfigurationEntry 15 }

wmanIf2mBsPrimaryCidUlQosProfileIndex OBJECT-TYPE
        SYNTAX      INTEGER (1 .. 65535)
        MAX-ACCESS  read-write
        STATUS      current
        DESCRIPTION
            "This index points to an entry in wmanIf2mBsQoSProfileTable
             that defines the QoS parameter set for uplink primary CID."
        ::= { wmanIf2mBsConfigurationEntry 16 }
        
wmanIf2mBsSsReqCapabilitiesTable OBJECT-TYPE
        SYNTAX      SEQUENCE OF WmanIf2mBsSsReqCapabilitiesEntry
        MAX-ACCESS  not-accessible
        STATUS      current
        DESCRIPTION
            "This table contains the SS's capabilities that are
             necessary for supporting mobility. SS reports these
             capabilities in the REG-REQ messages."
        REFERENCE
            "Subclause 6.3.2.3.7 in IEEE Std 802.16e-2005"
        ::= { wmanIf2mBsConfiguration 2 }

wmanIf2mBsSsReqCapabilitiesEntry OBJECT-TYPE
        SYNTAX      WmanIf2mBsSsReqCapabilitiesEntry
        MAX-ACCESS  not-accessible
        STATUS      current
        DESCRIPTION
            "This table provides one row for each SS that has entered
             and registered into the BS. The primary index is the
             ifIndex with an ifType of ieee80216WMAN, indicating the BS
             sector with which the SS is associated.
             wmanIf2mBsSsMacAddress identifies the SS being registered."
        INDEX     { ifIndex, wmanIf2mBsSsMacAddress }
        ::= { wmanIf2mBsSsReqCapabilitiesTable 1 }

WmanIf2mBsSsReqCapabilitiesEntry ::= SEQUENCE {        
        wmanIf2mBsSsReqCapHandoverSupported     WmanIf2mHandoverType,
        wmanIf2mBsSsReqCapHoProcessTimer        Unsigned32,
        wmanIf2mBsSsReqCapMobilityFeature       WmanIf2mOfdmaMobility,
        wmanIf2mBsSsReqCapSleepRecoveryTime     Unsigned32,
        wmanIf2mBsSsReqCapPreviousIpAddr        OCTET STRING,
        wmanIf2mBsSsReqCapIdleModeTimeout       Unsigned32,
        wmanIf2mBsSsReqCapHoConnProcessTime     Unsigned32,
        wmanIf2mBsSsReqCapHoTekProcessTime      Unsigned32,
        wmanIf2mBsSsReqCapPowerSavingType       WmanIf2mPowerSaveType,
        wmanIf2mBsSsReqCapNumOfPsClassIandII    INTEGER,
        wmanIf2mBsSsReqCapNumOfPsClassIII       INTEGER, 
        wmanIf2mBsSsReqCapHoTrigMatrix          WmanIf2mHoTrigMatrix, 
        wmanIf2mBsSsReqCapAssociationType       WmanIf2mAssociationTyp}

wmanIf2mBsSsReqCapHandoverSupported OBJECT-TYPE
        SYNTAX      WmanIf2mHandoverType 
        MAX-ACCESS  read-only
        STATUS      current
        DESCRIPTION 
            "Indicates what type(s) of Handover the BS or MS supports."
        REFERENCE
            "Subclause 11.7.12 in IEEE Std 802.16e-2005"
        ::= { wmanIf2mBsSsReqCapabilitiesEntry 1 }        

wmanIf2mBsSsReqCapHoProcessTimer OBJECT-TYPE
        SYNTAX      Unsigned32 
        UNITS       "frames"
        MAX-ACCESS  read-only
        STATUS      current
        DESCRIPTION 
            "The duration in frames the MS shall wait until receipt of
             the next unsolicited network re-entry MAC management
             message as indicated in the HO Process Optimization
             element of the RNG-RSP message."
        REFERENCE
            "Subclause 11.7.13.2 in IEEE Std 802.16e-2005"
        ::= { wmanIf2mBsSsReqCapabilitiesEntry 2 }
               
wmanIf2mBsSsReqCapMobilityFeature OBJECT-TYPE
        SYNTAX      WmanIf2mOfdmaMobility
        MAX-ACCESS  read-only
        STATUS      current
        DESCRIPTION
            "The field indicates whether or not the MS supports
             mobility hand-over, Slee-pmode, and Idle-mode."
        REFERENCE
            "Subclause 11.7.14.1"
        ::= { wmanIf2mBsSsReqCapabilitiesEntry 3 }
               
wmanIf2mBsSsReqCapSleepRecoveryTime OBJECT-TYPE
        SYNTAX      Unsigned32
        UNITS       "frames"
        MAX-ACCESS  read-only
        STATUS      current
        DESCRIPTION
            "The object indicates the time required for an MS that is
             in a sleep mode to return to awake-mode. This may be used
             by the BS to determine sleep interval window sizes when
             initiating sleep mode with an MS."
        REFERENCE
            "Subclause 11.7.15"
        ::= { wmanIf2mBsSsReqCapabilitiesEntry 4 }
               
wmanIf2mBsSsReqCapPreviousIpAddr OBJECT-TYPE
        SYNTAX      OCTET STRING
        MAX-ACCESS  read-only
        STATUS      current
        DESCRIPTION
            "The object indicates the IP address that the MS was
             assigned on the secondary management connection based on an
             association with its last serving BS. An IPv4 address shall
             be specified in conventional dotted format; e.g.,
             '134.234.2.3'. An IPv6 address may be expressed in abridged
             or unabridged form; however, the form chosen shall be
             consistent with RFC4291."
        REFERENCE
            "Subclause 11.7.16 in IEEE Std 802.16e-2005"
        ::= { wmanIf2mBsSsReqCapabilitiesEntry 5 }
                
wmanIf2mBsSsReqCapIdleModeTimeout OBJECT-TYPE
        SYNTAX      Unsigned32 
        UNITS       "seconds"
        MAX-ACCESS  read-only
        STATUS      current
        DESCRIPTION 
            "Max time interval between MS Idle Mode Location Updates."
        REFERENCE
            "Subclause 11.7.20.1 in IEEE Std 802.16e-2005"
        ::= { wmanIf2mBsSsReqCapabilitiesEntry 6 }

wmanIf2mBsSsReqCapHoConnProcessTime OBJECT-TYPE
        SYNTAX      Unsigned32 
        UNITS       "milliseconds"
        MAX-ACCESS  read-only
        STATUS      current
        DESCRIPTION 
            "The duration that the MS needs to process information on
             connections provided in RNG-RSP or REG-RSP message during
             Handoff."
        REFERENCE
            "Subclause 11.7.24 in IEEE Std 802.16e-2005"
        ::= { wmanIf2mBsSsReqCapabilitiesEntry 7 }

wmanIf2mBsSsReqCapHoTekProcessTime OBJECT-TYPE
        SYNTAX      Unsigned32 
        UNITS       "milliseconds"
        MAX-ACCESS  read-only
        STATUS      current
        DESCRIPTION 
            "The duration that the MS needs to completely process TEK
             information during Handoff."
        REFERENCE
            "Subclause 11.7.24 in IEEE Std 802.16e-2005"
        ::= { wmanIf2mBsSsReqCapabilitiesEntry 8 }

wmanIf2mBsSsReqCapPowerSavingType OBJECT-TYPE
        SYNTAX      WmanIf2mPowerSaveType 
        MAX-ACCESS  read-only
        STATUS      current
        DESCRIPTION 
            "For MS supporting sleep mode, this parameter defines the
             capability of the MS supporting different power save class
             types in sleep mode."
        REFERENCE
            "Subclause 11.7.4.2"
        ::= { wmanIf2mBsSsReqCapabilitiesEntry 9 }        

wmanIf2mBsSsReqCapNumOfPsClassIandII OBJECT-TYPE
        SYNTAX      INTEGER (0 .. 7) 
        MAX-ACCESS  read-only
        STATUS      current
        DESCRIPTION 
            "Number of power save class instances supported from class
             types 1 and 2."
        REFERENCE
            "Subclause 11.8.5 in IEEE Std 802.16e-2005"
        ::= { wmanIf2mBsSsReqCapabilitiesEntry 10 }

wmanIf2mBsSsReqCapNumOfPsClassIII OBJECT-TYPE
        SYNTAX      INTEGER (0 .. 7) 
        MAX-ACCESS  read-only
        STATUS      current
        DESCRIPTION 
            "Number of power save class instances supported from class
             types 3."
        REFERENCE
            "Subclause 11.8.5 in IEEE Std 802.16e-2005"
        ::= { wmanIf2mBsSsReqCapabilitiesEntry 11 }
                                          
wmanIf2mBsSsReqCapHoTrigMatrix OBJECT-TYPE
        SYNTAX      WmanIf2mHoTrigMatrix 
        MAX-ACCESS  read-only
        STATUS      current
        DESCRIPTION 
            "Indicates trigger metrics that MS or BS supports."
        REFERENCE
            "Subclause 11.8.7"
        ::= { wmanIf2mBsSsReqCapabilitiesEntry 12 }        

wmanIf2mBsSsReqCapAssociationType OBJECT-TYPE
        SYNTAX      WmanIf2mAssociationTyp 
        MAX-ACCESS  read-only
        STATUS      current
        DESCRIPTION 
            "Indicates the association level supported by the MS or the
             BS."
        REFERENCE
            "Subclause 11.8.8"
        ::= { wmanIf2mBsSsReqCapabilitiesEntry 13 }        
                                              
wmanIf2mBsSsRspCapabilitiesTable OBJECT-TYPE
        SYNTAX      SEQUENCE OF WmanIf2mBsSsRspCapabilitiesEntry
        MAX-ACCESS  not-accessible
        STATUS      current
        DESCRIPTION
            "This table contains the SS's capabilities that are necessary
             for supporting mobility. BS acknowledges the capabilities in
             the REG-RSP message in response to REG-REQ messages."
        REFERENCE
            "Subclause 6.3.2.3.7 in IEEE Std 802.16e-2005"
        ::= { wmanIf2mBsConfiguration 3 }

wmanIf2mBsSsRspCapabilitiesEntry OBJECT-TYPE
        SYNTAX      WmanIf2mBsSsRspCapabilitiesEntry
        MAX-ACCESS  not-accessible
        STATUS      current
        DESCRIPTION
            "This table provides one row for each SS that has entered and
             registered into the BS. The primary index is the ifIndex
             with an ifType of ieee80216WMAN, indicating the BS sector
             with which the SS is associated. wmanIf2mBsSsMacAddress
             identifies the SS being registered."
        INDEX     { ifIndex, wmanIf2mBsSsMacAddress }
        ::= { wmanIf2mBsSsRspCapabilitiesTable 1 }

WmanIf2mBsSsRspCapabilitiesEntry ::= SEQUENCE {        
        wmanIf2mBsSsRspCapHandoverSupported     WmanIf2mHandoverType,
        wmanIf2mBsSsRspCapRetrainTime           Unsigned32,
        wmanIf2mBsSsRspCapHoProcessTimer        Unsigned32,
        wmanIf2mBsSsRspCapRetransmissionTimer   Unsigned32,
        wmanIf2mBsSsRspCapMobilityFeature       WmanIf2mOfdmaMobility,
        wmanIf2mBsSsRspCapIdleModeTimeout       Unsigned32,
        wmanIf2mBsSsRspCapHoConnProcessTime     Unsigned32,
        wmanIf2mBsSsRspCapHoTekProcessTime      Unsigned32,
        wmanIf2mBsSsRspCapPowerSavingType       WmanIf2mPowerSaveType,
        wmanIf2mBsSsRspCapNumOfPsClassIandII    INTEGER,
        wmanIf2mBsSsRspCapNumOfPsClassIII       INTEGER, 
        wmanIf2mBsSsRspCapHoTrigMatrix          WmanIf2mHoTrigMatrix, 
        wmanIf2mBsSsRspCapAssociationType       WmanIf2mAssociationTyp}

wmanIf2mBsSsRspCapHandoverSupported OBJECT-TYPE
        SYNTAX      WmanIf2mHandoverType 
        MAX-ACCESS  read-only
        STATUS      current
        DESCRIPTION 
           "Indicates what type(s) of Handover the BS or MS supports."
        REFERENCE
            "Subclause 11.7.12 in IEEE Std 802.16e-2005"
        ::= { wmanIf2mBsSsRspCapabilitiesEntry 1 }

wmanIf2mBsSsRspCapRetrainTime OBJECT-TYPE
        SYNTAX      Unsigned32 
        UNITS       "100 milliseconds"
        MAX-ACCESS  read-only
        STATUS      current
        DESCRIPTION 
           "Indicates the duration for MS's connection information that
            will be retained in serving BS. BS shall start
            Resource_Retain_Time timer at MS notification of pending HO
            attempt through MOB_HO-IND or by detecting an MS drop."
        REFERENCE
            "Subclause 11.7.13.1 in IEEE Std 802.16e-2005"
        ::= { wmanIf2mBsSsRspCapabilitiesEntry 2 }

wmanIf2mBsSsRspCapHoProcessTimer OBJECT-TYPE
        SYNTAX      Unsigned32 
        UNITS       "frames"
        MAX-ACCESS  read-only
        STATUS      current
        DESCRIPTION 
            "The duration in frames the MS shall wait until receipt of
             the next unsolicited network re-entry MAC management
             message as indicated in the HO Process Optimization element
             of the RNG-RSP message. On HO Process Optimization MS Timer
             timeout and while HO Process Optimization MS Timer Retries
             is valid, MS shall send the network re-entry MAC management
             request message corresponding to the expected and pending
             network re-entry MAC management response message as
             indicated in HO Process Optimization and recycle HO Process
             Optimization MS Timer."
        REFERENCE
            "Subclause 11.7.13.2 in IEEE Std 802.16e-2005"
        ::= { wmanIf2mBsSsRspCapabilitiesEntry 3 }

wmanIf2mBsSsRspCapRetransmissionTimer OBJECT-TYPE
        SYNTAX      Unsigned32 
        UNITS       "frames"
        MAX-ACCESS  read-only
        STATUS      current
        DESCRIPTION 
            "When an MS transmits MOB_MSHO-REQ to initiate a handover
             process, it shall start MS Handover Retransmission Timer
             and shall not transmit another MOB_MSHO-REQ until the
             expiration of the MS Handover Retransmission Timer."
        REFERENCE
            "Subclause 11.7.13.3 in IEEE Std 802.16e-2005"
        ::= { wmanIf2mBsSsRspCapabilitiesEntry 4 }
        
wmanIf2mBsSsRspCapMobilityFeature OBJECT-TYPE
        SYNTAX      WmanIf2mOfdmaMobility
        MAX-ACCESS  read-only
        STATUS      current
        DESCRIPTION
            "The field indicates the mobility hand-over, Sleep-mode, and
             Idle-mode negotiated for MS."
        REFERENCE
            "Subclause 11.7.14.1"
        ::= { wmanIf2mBsSsRspCapabilitiesEntry 5 }        
       
wmanIf2mBsSsRspCapIdleModeTimeout OBJECT-TYPE
        SYNTAX      Unsigned32 
        UNITS       "seconds"
        MAX-ACCESS  read-only
        STATUS      current
        DESCRIPTION 
            "Max time interval between MS Idle Mode Location Updates."
        REFERENCE
            "Subclause 11.7.20.1 in IEEE Std 802.16e-2005"
        ::= { wmanIf2mBsSsRspCapabilitiesEntry 6 }
        
wmanIf2mBsSsRspCapHoConnProcessTime OBJECT-TYPE
        SYNTAX      Unsigned32 
        UNITS       "milliseconds"
        MAX-ACCESS  read-only
        STATUS      current
        DESCRIPTION 
            "The duration that the MS needs to process information on
             connections provided in RNG-RSP or REG-RSP message during
             Handoff."
        REFERENCE
            "Subclause 11.7.24 in IEEE Std 802.16e-2005"
        ::= { wmanIf2mBsSsRspCapabilitiesEntry 7 }

wmanIf2mBsSsRspCapHoTekProcessTime OBJECT-TYPE
        SYNTAX      Unsigned32 
        UNITS       "milliseconds"
        MAX-ACCESS  read-only
        STATUS      current
        DESCRIPTION 
            "The duration that the MS needs to completely process TEK
             information during Handoff."
        REFERENCE
            "Subclause 11.7.24 in IEEE Std 802.16e-2005"
        ::= { wmanIf2mBsSsRspCapabilitiesEntry 8 }

wmanIf2mBsSsRspCapPowerSavingType OBJECT-TYPE
        SYNTAX      WmanIf2mPowerSaveType 
        MAX-ACCESS  read-only
        STATUS      current
        DESCRIPTION 
            "For MS supporting sleep mode, this parameter defines the
             capability of the MS supporting different power save class
             types in sleep mode."
        REFERENCE
            "Subclause 11.7.4.2"
        ::= { wmanIf2mBsSsRspCapabilitiesEntry 9 }        

wmanIf2mBsSsRspCapNumOfPsClassIandII OBJECT-TYPE
        SYNTAX      INTEGER (0 .. 7) 
        MAX-ACCESS  read-only
        STATUS      current
        DESCRIPTION 
            "Number of power save class instances supported from class
             types 1 and 2."
        REFERENCE
            "Subclause 11.8.5 in IEEE Std 802.16e-2005"
        ::= { wmanIf2mBsSsRspCapabilitiesEntry 10 }

wmanIf2mBsSsRspCapNumOfPsClassIII OBJECT-TYPE
        SYNTAX      INTEGER (0 .. 7) 
        MAX-ACCESS  read-only
        STATUS      current
        DESCRIPTION 
            "Number of power save class instances supported from class
             types 3."
        REFERENCE
            "Subclause 11.8.5 in IEEE Std 802.16e-2005"
        ::= { wmanIf2mBsSsRspCapabilitiesEntry 11 }
                                  
wmanIf2mBsSsRspCapHoTrigMatrix OBJECT-TYPE
        SYNTAX      WmanIf2mHoTrigMatrix 
        MAX-ACCESS  read-only
        STATUS      current
        DESCRIPTION 
            "Indicates trigger metrics that MS or BS supports."
        REFERENCE
            "Subclause 11.8.7 in IEEE Std 802.16e-2005"
        ::= { wmanIf2mBsSsRspCapabilitiesEntry 12 }        

wmanIf2mBsSsRspCapAssociationType OBJECT-TYPE
        SYNTAX      WmanIf2mAssociationTyp 
        MAX-ACCESS  read-only
        STATUS      current
        DESCRIPTION 
            "Indicates the association level supported by the MS or the
             BS."
        REFERENCE
            "Subclause 11.8.8 in IEEE Std 802.16e-2005"
        ::= { wmanIf2mBsSsRspCapabilitiesEntry 13 }
                                        
wmanIf2mBsBasicCapabilitiesTable OBJECT-TYPE
        SYNTAX      SEQUENCE OF WmanIf2mBsBasicCapabilitiesEntry
        MAX-ACCESS  not-accessible
        STATUS      current
        DESCRIPTION
            "This table contains the basic capabilities of the BS as
             implemented in BS hardware and software. These capabilities
             along with the configuration for them
             (wmanIf2mBsCapabilitiesConfigTable) are used for negotiation
             of basic capabilities with SS using RNG-RSP, SBC-RSP and 
             REG-RSP messages. The negotiated capabilities are obtained
             by interSubclause of SS raw reported capabilities, BS raw
             capabilities and BS configured capabilities. The objects in
             the table have read-only access. The table is maintained
             by BS."
        ::= { wmanIf2mBsConfiguration 4 }

wmanIf2mBsBasicCapabilitiesEntry OBJECT-TYPE
        SYNTAX      WmanIf2mBsBasicCapabilitiesEntry
        MAX-ACCESS  not-accessible
        STATUS      current
        DESCRIPTION
            "This table provides one row for each BS sector."
        INDEX     { ifIndex }
        ::= { wmanIf2mBsBasicCapabilitiesTable 1 }

WmanIf2mBsBasicCapabilitiesEntry ::= SEQUENCE {
        wmanIf2mBsCapHandoverSupported          WmanIf2mHandoverType,
        wmanIf2mBsCapRetrainTime                Unsigned32,
        wmanIf2mBsCapHoProcessTimer             Unsigned32,
        wmanIf2mBsCapRetransmissionTimer        Unsigned32,
        wmanIf2mBsCapMobilityFeature            WmanIf2mOfdmaMobility,
        wmanIf2mBsCapIdleModeTimeout            Unsigned32,
        wmanIf2mBsCapHoConnProcessTime          Unsigned32,
        wmanIf2mBsCapHoTekProcessTime           Unsigned32,
        wmanIf2mBsCapPowerSavingType            WmanIf2mPowerSaveType,
        wmanIf2mBsCapNumOfPsClassIandII         INTEGER,
        wmanIf2mBsCapNumOfPsClassIII            INTEGER, 
        wmanIf2mBsCapHoTrigMatrix               WmanIf2mHoTrigMatrix, 
        wmanIf2mBsCapAssociationType            WmanIf2mAssociationTyp}

wmanIf2mBsCapHandoverSupported OBJECT-TYPE
        SYNTAX      WmanIf2mHandoverType 
        MAX-ACCESS  read-only
        STATUS      current
        DESCRIPTION 
            "Indicates what type(s) of Handover the BS or MS supports."
        REFERENCE
            "Subclause 11.7.12 in IEEE Std 802.16e-2005"
        ::= { wmanIf2mBsBasicCapabilitiesEntry 1 }

wmanIf2mBsCapRetrainTime OBJECT-TYPE
        SYNTAX      Unsigned32 
        UNITS       "100 milliseconds"
        MAX-ACCESS  read-only
        STATUS      current
        DESCRIPTION 
           "Indicates the duration for MS's connection information that
            will be retained in serving BS. BS shall start
            Resource_Retain_Time timer at MS notification of pending HO
            attempt through MOB_HO-IND or by detecting an MS drop."
        REFERENCE
            "Subclause 11.7.13.1 in IEEE Std 802.16e-2005"
        ::= { wmanIf2mBsBasicCapabilitiesEntry 2 }

wmanIf2mBsCapHoProcessTimer OBJECT-TYPE
        SYNTAX      Unsigned32 
        UNITS       "frames"
        MAX-ACCESS  read-only
        STATUS      current
        DESCRIPTION 
            "The duration in frames the MS shall wait until receipt of
             the next unsolicited network re-entry MAC management
             message as indicated in the HO Process Optimization element
             of the RNG-RSP message."
        REFERENCE
            "Subclause 11.7.13.2 in IEEE Std 802.16e-2005"
        ::= { wmanIf2mBsBasicCapabilitiesEntry 3 }

wmanIf2mBsCapRetransmissionTimer OBJECT-TYPE
        SYNTAX      Unsigned32 
        UNITS       "frames"
        MAX-ACCESS  read-only
        STATUS      current
        DESCRIPTION 
            "When an MS transmits MOB_MSHO-REQ to initiate a handover
             process, it shall start MS Handover Retransmission Timer
             and shall not transmit another MOB_MSHO-REQ until the
             expiration of the MS Handover Retransmission Timer."
        REFERENCE
            "Subclause 11.7.13.3 in IEEE Std 802.16e-2005"
        ::= { wmanIf2mBsBasicCapabilitiesEntry 4 }

wmanIf2mBsCapMobilityFeature OBJECT-TYPE
        SYNTAX      WmanIf2mOfdmaMobility
        MAX-ACCESS  read-only
        STATUS      current
        DESCRIPTION
            "The field indicates the mobility hand-over, Sleep-mode, and
             Idle-mode supported by BS."
        REFERENCE
            "Subclause 11.7.14.1"
        ::= { wmanIf2mBsBasicCapabilitiesEntry 5 }
        
wmanIf2mBsCapIdleModeTimeout OBJECT-TYPE
        SYNTAX      Unsigned32 
        UNITS       "seconds"
        MAX-ACCESS  read-only
        STATUS      current
        DESCRIPTION 
            "Max time interval between MS Idle Mode Location Updates."
        REFERENCE
            "Subclause 11.7.20.1 in IEEE Std 802.16e-2005"
        ::= { wmanIf2mBsBasicCapabilitiesEntry 6 }
        
wmanIf2mBsCapHoConnProcessTime OBJECT-TYPE
        SYNTAX      Unsigned32 
        UNITS       "milliseconds"
        MAX-ACCESS  read-only
        STATUS      current
        DESCRIPTION 
            "The duration that the MS needs to process information on
             connections provided in RNG-RSP or REG-RSP message during
             Handoff."
        REFERENCE
            "Subclause 11.7.24 in IEEE Std 802.16e-2005"
        ::= { wmanIf2mBsBasicCapabilitiesEntry 7 }

wmanIf2mBsCapHoTekProcessTime OBJECT-TYPE
        SYNTAX      Unsigned32 
        UNITS       "milliseconds"
        MAX-ACCESS  read-only
        STATUS      current
        DESCRIPTION 
            "The duration that the MS needs to completely process TEK
             information during Handoff."
        REFERENCE
            "Subclause 11.7.24 in IEEE Std 802.16e-2005"
        ::= { wmanIf2mBsBasicCapabilitiesEntry 8 }

wmanIf2mBsCapPowerSavingType OBJECT-TYPE
        SYNTAX      WmanIf2mPowerSaveType 
        MAX-ACCESS  read-only
        STATUS      current
        DESCRIPTION 
            "For MS supporting sleep mode, this parameter defines the
             capability of the MS supporting different power save class
             types in sleep mode."
        REFERENCE
            "Subclause 11.7.4.2"
        ::= { wmanIf2mBsBasicCapabilitiesEntry 9 }        

wmanIf2mBsCapNumOfPsClassIandII OBJECT-TYPE
        SYNTAX      INTEGER (0 .. 7) 
        MAX-ACCESS  read-only
        STATUS      current
        DESCRIPTION 
            "Number of power save class instances supported from class
             types 1 and 2."
        REFERENCE
            "Subclause 11.8.5 in IEEE Std 802.16e-2005"
        ::= { wmanIf2mBsBasicCapabilitiesEntry 10 }

wmanIf2mBsCapNumOfPsClassIII OBJECT-TYPE
        SYNTAX      INTEGER (0 .. 7) 
        MAX-ACCESS  read-only
        STATUS      current
        DESCRIPTION 
            "Number of power save class instances supported from class
             types 3."
        REFERENCE
            "Subclause 11.8.5 in IEEE Std 802.16e-2005"
        ::= { wmanIf2mBsBasicCapabilitiesEntry 11 }
                                  
wmanIf2mBsCapHoTrigMatrix OBJECT-TYPE
        SYNTAX      WmanIf2mHoTrigMatrix 
        MAX-ACCESS  read-only
        STATUS      current
        DESCRIPTION 
            "Indicates trigger metrics that MS or BS supports."
        REFERENCE
            "Subclause 11.8.7 in IEEE Std 802.16e-2005"
        ::= { wmanIf2mBsBasicCapabilitiesEntry 12 }        

wmanIf2mBsCapAssociationType OBJECT-TYPE
        SYNTAX      WmanIf2mAssociationTyp 
        MAX-ACCESS  read-only
        STATUS      current
        DESCRIPTION 
            "Indicates the association level supported by the MS or the
             BS."
        REFERENCE
            "Subclause 11.8.8 in IEEE Std 802.16e-2005"
        ::= { wmanIf2mBsBasicCapabilitiesEntry 13 }
                        
wmanIf2mBsCapabilitiesConfigTable OBJECT-TYPE
        SYNTAX      SEQUENCE OF WmanIf2mBsCapabilitiesConfigEntry
        MAX-ACCESS  not-accessible
        STATUS      current
        DESCRIPTION
            "This table contains the configuration for basic capabilities
             of BS. The table is intended to be used to restrict the
             Capabilities implemented by BS, for example in order to
             comply with local regulatory requirements. The BS should use
             the configuration along with the implemented Capabilities
             (wmanIf2mBsBasicCapabilitiesTable) for negotiation of basic
             capabilities with SS using RNG-RSP, SBC-RSP and REG-RSP
             messages. The negotiated capabilities are obtained by
             interSubclause of SS reported capabilities, BS raw
             capabilities and BS configured capabilities. The objects in
             the table have read-write access. The rows are created by
             BS as a copy of wmanIf2mBsBasicCapabilitiesTable and can be
             modified by NMS."
        ::= { wmanIf2mBsConfiguration 5 }

wmanIf2mBsCapabilitiesConfigEntry OBJECT-TYPE
        SYNTAX      WmanIf2mBsCapabilitiesConfigEntry
        MAX-ACCESS  not-accessible
        STATUS      current
        DESCRIPTION
            "This table provides one row for each BS sector."
        INDEX     { ifIndex }
        ::= { wmanIf2mBsCapabilitiesConfigTable 1 }

WmanIf2mBsCapabilitiesConfigEntry ::= SEQUENCE {
        wmanIf2mBsCapCfgHandoverSupported       WmanIf2mHandoverType,
        wmanIf2mBsCapCfgRetrainTime             Unsigned32,
        wmanIf2mBsCapCfgHoProcessTimer          Unsigned32,
        wmanIf2mBsCapCfgRetransmissionTimer     Unsigned32,
        wmanIf2mBsCapCfgMobilityFeature         WmanIf2mOfdmaMobility,
        wmanIf2mBsCapCfgIdleModeTimeout         Unsigned32,
        wmanIf2mBsCapCfgHoConnProcessTime       Unsigned32,
        wmanIf2mBsCapCfgHoTekProcessTime        Unsigned32,
        wmanIf2mBsCapCfgPowerSavingType         WmanIf2mPowerSaveType,
        wmanIf2mBsCapCfgNumOfPsClassIandII      INTEGER,
        wmanIf2mBsCapCfgNumOfPsClassIII         INTEGER, 
        wmanIf2mBsCapCfgHoTrigMatrix            WmanIf2mHoTrigMatrix, 
        wmanIf2mBsCapCfgAssociationType         WmanIf2mAssociationTyp}

wmanIf2mBsCapCfgHandoverSupported OBJECT-TYPE
        SYNTAX      WmanIf2mHandoverType 
        MAX-ACCESS  read-write
        STATUS      current
        DESCRIPTION 
            "Indicates what type(s) of Handover the BS or MS supports."
        REFERENCE
            "Subclause 11.7.12 in IEEE Std 802.16e-2005"
        ::= { wmanIf2mBsCapabilitiesConfigEntry 1 }

wmanIf2mBsCapCfgRetrainTime OBJECT-TYPE
        SYNTAX      Unsigned32 
        UNITS       "100 milliseconds"
        MAX-ACCESS  read-write
        STATUS      current
        DESCRIPTION 
           "Indicates the duration for MS's connection information that
            will be retained in serving BS. BS shall start
            Resource_Retain_Time timer at MS notification of pending HO
            attempt through MOB_HO-IND or by detecting an MS drop."
        REFERENCE
            "Subclause 11.7.13.1 in IEEE Std 802.16e-2005"
        DEFVAL		{ 1 }
        ::= { wmanIf2mBsCapabilitiesConfigEntry 2 }

wmanIf2mBsCapCfgHoProcessTimer OBJECT-TYPE
        SYNTAX      Unsigned32 
        UNITS       "frames"
        MAX-ACCESS  read-write
        STATUS      current
        DESCRIPTION 
            "The duration in frames the MS shall wait until receipt of
             the next unsolicited network re-entry MAC management
             message as indicated in the HO Process Optimization element
             of the RNG-RSP message."
        REFERENCE
            "Subclause 11.7.13.2 in IEEE Std 802.16e-2005"
        ::= { wmanIf2mBsCapabilitiesConfigEntry 3 }
        
wmanIf2mBsCapCfgRetransmissionTimer OBJECT-TYPE
        SYNTAX      Unsigned32 
        UNITS       "frames"
        MAX-ACCESS  read-write
        STATUS      current
        DESCRIPTION 
            "When an MS transmits MOB_MSHO-REQ to initiate a handover
             process, it shall start MS Handover Retransmission Timer
             and shall not transmit another MOB_MSHO-REQ until the
             expiration of the MS Handover Retransmission Timer."
        REFERENCE
            "Subclause 11.7.13.3 in IEEE Std 802.16e-2005"
        ::= { wmanIf2mBsCapabilitiesConfigEntry 4 }
        
wmanIf2mBsCapCfgMobilityFeature OBJECT-TYPE
        SYNTAX      WmanIf2mOfdmaMobility
        MAX-ACCESS  read-write
        STATUS      current
        DESCRIPTION
            "The field indicates the mobility hand-over, Sleep-mode, and
             Idle-mode configured for the BS."
        REFERENCE
            "Subclause 11.7.14.1"
        ::= { wmanIf2mBsCapabilitiesConfigEntry 5 }

wmanIf2mBsCapCfgIdleModeTimeout OBJECT-TYPE
        SYNTAX      Unsigned32 
        UNITS       "seconds"
        MAX-ACCESS  read-write
        STATUS      current
        DESCRIPTION 
            "Max time interval between MS Idle Mode Location Updates."
        REFERENCE
            "Subclause 11.7.20.1 in IEEE Std 802.16e-2005"
        DEFVAL         { 4096 }
        ::= { wmanIf2mBsCapabilitiesConfigEntry 6 }
        
wmanIf2mBsCapCfgHoConnProcessTime OBJECT-TYPE
        SYNTAX      Unsigned32 
        UNITS       "milliseconds"
        MAX-ACCESS  read-write
        STATUS      current
        DESCRIPTION 
            "The duration that the MS needs to process information on
             connections provided in RNG-RSP or REG-RSP message during
             Handoff."
        REFERENCE
            "Subclause 11.7.24 in IEEE Std 802.16e-2005"
        ::= { wmanIf2mBsCapabilitiesConfigEntry 7 }

wmanIf2mBsCapCfgHoTekProcessTime OBJECT-TYPE
        SYNTAX      Unsigned32 
        UNITS       "milliseconds"
        MAX-ACCESS  read-write
        STATUS      current
        DESCRIPTION 
            "The duration that the MS needs to completely process TEK
             information during Handoff."
        REFERENCE
            "Subclause 11.7.24 in IEEE Std 802.16e-2005"
        ::= { wmanIf2mBsCapabilitiesConfigEntry 8 }

wmanIf2mBsCapCfgPowerSavingType OBJECT-TYPE
        SYNTAX      WmanIf2mPowerSaveType 
        MAX-ACCESS  read-only
        STATUS      current
        DESCRIPTION 
            "For MS supporting sleep mode, this parameter defines the
             capability of the MS supporting different power save class
             types in sleep mode."
        REFERENCE
            "Subclause 11.7.4.2"
        ::= { wmanIf2mBsCapabilitiesConfigEntry 9 }        

wmanIf2mBsCapCfgNumOfPsClassIandII OBJECT-TYPE
        SYNTAX      INTEGER (0 .. 7) 
        MAX-ACCESS  read-only
        STATUS      current
        DESCRIPTION 
            "Number of power save class instances supported from class
             types 1 and 2."
        REFERENCE
            "Subclause 11.8.5 in IEEE Std 802.16e-2005"
        ::= { wmanIf2mBsCapabilitiesConfigEntry 10 }

wmanIf2mBsCapCfgNumOfPsClassIII OBJECT-TYPE
        SYNTAX      INTEGER (0 .. 7) 
        MAX-ACCESS  read-only
        STATUS      current
        DESCRIPTION 
            "Number of power save class instances supported from class
             types 3."
        REFERENCE
            "Subclause 11.8.5 in IEEE Std 802.16e-2005"
        ::= { wmanIf2mBsCapabilitiesConfigEntry 11 }
                                  
wmanIf2mBsCapCfgHoTrigMatrix OBJECT-TYPE
        SYNTAX      WmanIf2mHoTrigMatrix 
        MAX-ACCESS  read-only
        STATUS      current
        DESCRIPTION 
            "Indicates trigger metrics that MS or BS supports."
        REFERENCE
            "Subclause 11.8.7 in IEEE Std 802.16e-2005"
        ::= { wmanIf2mBsCapabilitiesConfigEntry 12 }        

wmanIf2mBsCapCfgAssociationType OBJECT-TYPE
        SYNTAX      WmanIf2mAssociationTyp 
        MAX-ACCESS  read-only
        STATUS      current
        DESCRIPTION 
            "Indicates the association level supported by the MS or the
             BS."
        REFERENCE
            "Subclause 11.8.8 in IEEE Std 802.16e-2005"
        ::= { wmanIf2mBsCapabilitiesConfigEntry 13 }

wmanIf2mBsSsCidUpdateTable OBJECT-TYPE
        SYNTAX      SEQUENCE OF WmanIf2mBsSsCidUpdateEntry
        MAX-ACCESS  not-accessible
        STATUS      current
        DESCRIPTION
            "This table contains the 'CID update' TLV that is send in
             the REG-RSP message to allow an MS to update its service
             flows and connection information so that it may continue
             service after a handover to a new serving BS.
             
             The wmanIf2BsCid and wmanIf2BsSfTargetSaid objects in
             wmanIf2BsServiceFlowTable in wmanIf2Mib shall be updated
             with the CIDs and SAIDs included in the 'CID update' TLV.
             If the service flow parameters changes are included in the
             'Connection Info' TLV, the service flow information can be
             found in wmanIf2BsServiceFlowTable."
        REFERENCE
            "Subclause 6.3.2.3.8 in IEEE Std 802.16e-2005"
        ::= { wmanIf2mBsConfiguration 6 }

wmanIf2mBsSsCidUpdateEntry OBJECT-TYPE
        SYNTAX      WmanIf2mBsSsCidUpdateEntry
        MAX-ACCESS  not-accessible
        STATUS      current
        DESCRIPTION
            "This table provides one row for each service flow."
        INDEX     { ifIndex,
                    wmanIf2mBsSsMacAddress,
                    wmanIf2mBsSsSfId }
        ::= { wmanIf2mBsSsCidUpdateTable 1 }

WmanIf2mBsSsCidUpdateEntry ::= SEQUENCE {        
        wmanIf2mBsSsSfId                        Unsigned32,
        wmanIf2mBsSsNewCid                      WmanIf2mCidType,
        wmanIf2mBsSsNewSaid                     Integer32,
        wmanIf2mBsSsOldSaid                     Integer32}
        
wmanIf2mBsSsSfId OBJECT-TYPE
        SYNTAX      Unsigned32 (1 .. 4294967295)
        MAX-ACCESS  not-accessible
        STATUS      current
        DESCRIPTION
            "A 32 bit quantity that uniquely identifies a service flow."
        ::= { wmanIf2mBsSsCidUpdateEntry 1 }
        
wmanIf2mBsSsNewCid OBJECT-TYPE
        SYNTAX      WmanIf2mCidType
        MAX-ACCESS  read-only
        STATUS      current
        DESCRIPTION
            "The new CID at the target BS for a service flow that was
             used by MS in the previous serving BS."
        REFERENCE
            "Subclause 11.7.10 in IEEE Std 802.16e-2005"
        ::= { wmanIf2mBsSsCidUpdateEntry 2 }

wmanIf2mBsSsNewSaid OBJECT-TYPE
        SYNTAX      Integer32 (0 .. 65535)
        MAX-ACCESS  read-only
        STATUS      current
        DESCRIPTION
            "The field indicates New SAID after handover to new BS. It
             provides a translation table that allows an MS to update
             its security associations so that it may continue security
             service after a handover to a new serving BS."
        REFERENCE
            "Subclause 11.7.18 in IEEE Std 802.16e-2005"
        ::= { wmanIf2mBsSsCidUpdateEntry 3 }
        
wmanIf2mBsSsOldSaid OBJECT-TYPE
        SYNTAX      Integer32 (0 .. 65535)
        MAX-ACCESS  read-only
        STATUS      current
        DESCRIPTION
            "The field indicates Old SAID after handover to new BS. It
             provides a translation table that allows an MS to update
             its security associations so that it may continue security
             service after a handover to a new serving BS."
        REFERENCE
            "Subclause 11.7.18 in IEEE Std 802.16e-2005"
        ::= { wmanIf2mBsSsCidUpdateEntry 4 }
                                        
--
-- Base Station Power Saving Mode
--
wmanIf2mBsPowerSavingMode OBJECT IDENTIFIER ::= { wmanIf2mBsCm 2 }

--
-- wmanIf2mBsSsPwrSaving2CidMapTable contains the power saving status         
-- 
wmanIf2mBsSsPwrSaving2CidMapTable OBJECT-TYPE
        SYNTAX      SEQUENCE OF WmanIf2mBsSsPwrSaving2CidMapEntry
        MAX-ACCESS  not-accessible
        STATUS      current
        DESCRIPTION
            "This table contains the list of CIDs for each power saving
             class of every MS supporting sleep mode. When the MS roams
             to a different BS, all entries associated with such MS will
             be deleted."
        ::= { wmanIf2mBsPowerSavingMode 1 }

wmanIf2mBsSsPwrSaving2CidMapEntry OBJECT-TYPE
        SYNTAX      WmanIf2mBsSsPwrSaving2CidMapEntry
        MAX-ACCESS  not-accessible
        STATUS      current
        DESCRIPTION
            "This table provides one row for each CID in an MS."
        INDEX     { ifIndex,
                    wmanIf2mBsSsMacAddress,
                    wmanIf2mBsSsCid  }
        ::= { wmanIf2mBsSsPwrSaving2CidMapTable 1 }

WmanIf2mBsSsPwrSaving2CidMapEntry::= SEQUENCE {
        wmanIf2mBsSsCid                         WmanIf2mCidType,
        wmanIf2mBsSsPowerSavingClassId          WmanIf2mPsClassId}

wmanIf2mBsSsCid OBJECT-TYPE
        SYNTAX      WmanIf2mCidType
        MAX-ACCESS  not-accessible
        STATUS      current
        DESCRIPTION
            "A 16 bit channel identifier to identify a connection."
        ::= { wmanIf2mBsSsPwrSaving2CidMapEntry 1 }                        

wmanIf2mBsSsPowerSavingClassId OBJECT-TYPE
        SYNTAX      WmanIf2mPsClassId
        MAX-ACCESS  read-only
        STATUS      current
        DESCRIPTION
            "wmanIf2mBsSsPowerSavingClassId identifies the power saving
             class associated with this CID. It maps to an entry in
             wmanIf2mBsSsPowerSavingClassesTable."
        ::= { wmanIf2mBsSsPwrSaving2CidMapEntry 2 }

--
-- wmanIf2mBsSsPowerSavingClassesTable contains the power saving classes
-- information         
--        
wmanIf2mBsSsPowerSavingClassesTable OBJECT-TYPE
        SYNTAX      SEQUENCE OF WmanIf2mBsSsPowerSavingClassesEntry
        MAX-ACCESS  not-accessible
        STATUS      current
        DESCRIPTION
            "This table reports the parameters of all the power saving
             classes negotiated between BS and MS using MOB_SLP-REQ and
             MOB_SLP-RSP messages. When the MS roams to a different BS,
             all entries associated with such MS will be deleted."
        REFERENCE
            "Subclause 6.3.2.3.40, 6.3.2.3.41"
        ::= { wmanIf2mBsPowerSavingMode 2 }

wmanIf2mBsSsPowerSavingClassesEntry OBJECT-TYPE
        SYNTAX      WmanIf2mBsSsPowerSavingClassesEntry
        MAX-ACCESS  not-accessible
        STATUS      current
        DESCRIPTION
            "It is intended to support both unicast and multicast
             service flows. wmanIf2mBsSsMacAddress contains the MAC
             address of the MS to which the power saving classes are
             associated."
        INDEX     { ifIndex,
                    wmanIf2mBsSsMacAddress,
                    wmanIf2mBsSsPsClassId }
        ::= { wmanIf2mBsSsPowerSavingClassesTable 1 }

WmanIf2mBsSsPowerSavingClassesEntry ::= SEQUENCE {
        wmanIf2mBsSsPsClassId                   WmanIf2mPsClassId,
        wmanIf2mBsSsStartFrameNumber            INTEGER,
        wmanIf2mBsSsPowerSavingClassType        WmanIf2mPsClassType,
        wmanIf2mBsSsPsClassCidDirection         WmanIf2mPsClassCidDir,
        wmanIf2mBsSsTrafficTriggeredWakening    WmanIf2mTrafficWkFlag,
        wmanIf2mBsSsInitialSleepWindow          INTEGER,
        wmanIf2mBsSsFinalSleepWindowBase        INTEGER,
        wmanIf2mBsSsFinalSleepWindowExponent    INTEGER,
        wmanIf2mBsSsListeningWindow             INTEGER,
        wmanIf2mBsSsPowerSavingMode             WmanIf2mPowerSavingMode,
        wmanIf2mBsSsSlpId                       INTEGER}
                         
wmanIf2mBsSsPsClassId OBJECT-TYPE
        SYNTAX      WmanIf2mPsClassId
        MAX-ACCESS  not-accessible
        STATUS      current
        DESCRIPTION
            "This object uniquely identifies the power saving classes in
             a MS."
        ::= { wmanIf2mBsSsPowerSavingClassesEntry 1 }

wmanIf2mBsSsStartFrameNumber OBJECT-TYPE
        SYNTAX      INTEGER
        MAX-ACCESS  read-only
        STATUS      current
        DESCRIPTION
            "Start frame number for first sleep window."
        REFERENCE
            "Subclause 6.3.2.3.40"
        ::= { wmanIf2mBsSsPowerSavingClassesEntry 2 }

wmanIf2mBsSsPowerSavingClassType OBJECT-TYPE
        SYNTAX      WmanIf2mPsClassType 
        MAX-ACCESS  read-only
        STATUS      current
        DESCRIPTION
            "Power saving classes type I - BE & NRT-VR,
             Power saving classes type II - UGS & RT-VR,
             Power saving classes type III - multicast, management CID"
        REFERENCE
            "Subclause 6.3.2.3.40, Table 551"
        ::= { wmanIf2mBsSsPowerSavingClassesEntry 3 }

wmanIf2mBsSsPsClassCidDirection OBJECT-TYPE
        SYNTAX      WmanIf2mPsClassCidDir
        MAX-ACCESS  read-only
        STATUS      current
        DESCRIPTION
            "The direction of power saving class's CIDs."
        REFERENCE
            "Subclause 6.3.2.3.40"
        ::= { wmanIf2mBsSsPowerSavingClassesEntry 4 }

wmanIf2mBsSsTrafficTriggeredWakening OBJECT-TYPE
        SYNTAX      WmanIf2mTrafficWkFlag
        MAX-ACCESS  read-only
        STATUS      current
        DESCRIPTION
            "Traffic Triggered Wakening flag
             0 = Power Saving Class shall not be deactivated if traffic
                 appears at the connection as per 6.3.21.2.
             1 = Power Saving Class shall be deactivated if traffic
                 appears at the connection as 6.3.21.2."
        REFERENCE
            "Subclause 6.3.19.40"
        ::= { wmanIf2mBsSsPowerSavingClassesEntry 5 }

wmanIf2mBsSsInitialSleepWindow OBJECT-TYPE
        SYNTAX      INTEGER (0..255)
        UNITS       "frame"
        MAX-ACCESS  read-only
        STATUS      current
        DESCRIPTION
            "The initial duration for the sleep window. It is not
             relevant for Power Saving Class type III, and shall
             return '0'."
        REFERENCE
            "Subclause 6.3.2.3.40"
        ::= { wmanIf2mBsSsPowerSavingClassesEntry 6 }

wmanIf2mBsSsFinalSleepWindowBase OBJECT-TYPE
        SYNTAX      INTEGER (0..1023)
        UNITS       "frame"
        MAX-ACCESS  read-only
        STATUS      current
        DESCRIPTION
            "The final value for the sleep interval. It is not
             relevant for Power Saving Class type II, and shall
             return '0'. For Power Saving Class type III, it is the
             base for duration of single sleep window request."
        REFERENCE
            "Subclause 6.3.2.3.40"
        ::= { wmanIf2mBsSsPowerSavingClassesEntry 7 }

wmanIf2mBsSsFinalSleepWindowExponent OBJECT-TYPE
        SYNTAX      INTEGER (0..7)
        MAX-ACCESS  read-only
        STATUS      current
        DESCRIPTION
            "The factor by which the final-sleep window base is
             multiplied in order to calculate the final-sleep window.
             The following formula is used:
             final-sleep window = final-sleep window base x 
                                  2^(final-sleep window exponent)
             For Power Saving Class type III, it is the exponent for
             the duration of single sleep window request."
        REFERENCE
            "Subclause 6.3.2.3.40"
        ::= { wmanIf2mBsSsPowerSavingClassesEntry 8 }

wmanIf2mBsSsListeningWindow OBJECT-TYPE
        SYNTAX      INTEGER (0..255)
        UNITS       "frame"
        MAX-ACCESS  read-only
        STATUS      current
        DESCRIPTION
            "The Duration of MS listening window. It is not relevant for
             Power Saving Class type III, and shall return '0'."
        REFERENCE
            "Subclause 6.3.2.3.40"
        ::= { wmanIf2mBsSsPowerSavingClassesEntry 9 }

wmanIf2mBsSsPowerSavingMode OBJECT-TYPE
        SYNTAX      WmanIf2mPowerSavingMode
        MAX-ACCESS  read-only
        STATUS      current
        DESCRIPTION
            "Indicate whether the power saving class is active or not."
        REFERENCE
            "Subclause 6.3.2.3.41"
        ::= { wmanIf2mBsSsPowerSavingClassesEntry 10 }

wmanIf2mBsSsSlpId OBJECT-TYPE
        SYNTAX      INTEGER (0..1023)
        MAX-ACCESS  read-only
        STATUS      current
        DESCRIPTION
            "wmanIf2mBsSsSlpId is assigned by the BS whenever an MS is
             instructed to enter sleep mode. This number shall be unique
             among all MSs that are in sleep mode."
        REFERENCE
            "Subclause 6.3.2.3.41"
        ::= { wmanIf2mBsSsPowerSavingClassesEntry 11 }
               
--
--
-- Neighbor Base Stations Advertizement
--
wmanIf2mBsNeighborAdv OBJECT IDENTIFIER ::= { wmanIf2mBsCm 3 }

wmanIf2mBsNeighborAdvCommonTable OBJECT-TYPE
        SYNTAX      SEQUENCE OF WmanIf2mBsNeighborAdvCommonEntry
        MAX-ACCESS  not-accessible
        STATUS      current
        DESCRIPTION
            "This table contains the common attributes for the
             MOB_NBR-ADV message."
        REFERENCE
            "Subclause 6.3.2.3.47, in IEEE Std 802.16e-2005"
        ::= { wmanIf2mBsNeighborAdv 1 }

wmanIf2mBsNeighborAdvCommonEntry OBJECT-TYPE
        SYNTAX      WmanIf2mBsNeighborAdvCommonEntry
        MAX-ACCESS  not-accessible
        STATUS      current
        DESCRIPTION
            "This table provides one row for each BS sector."
        INDEX     { ifIndex }
        ::= { wmanIf2mBsNeighborAdvCommonTable 1 }

WmanIf2mBsNeighborAdvCommonEntry::= SEQUENCE {
        wmanIf2mBsSkipOptions                   WmanIf2mSkipOptBitMap,
        wmanIf2mBsOperatorId                    WmanIf2mNbrOperatorId,
        wmanIf2mBsNumOfNeighbors                Unsigned32,
        wmanIf2mBsConfigChangeCount             INTEGER}

wmanIf2mBsSkipOptions OBJECT-TYPE
        SYNTAX      WmanIf2mSkipOptBitMap
        MAX-ACCESS  read-write
        STATUS      current
        DESCRIPTION
            "When a bit is set to 1, its corresponding field will be
             omitted."
        REFERENCE
            "Subclause 6.3.2.3.43"
        ::= { wmanIf2mBsNeighborAdvCommonEntry 1 } 

wmanIf2mBsOperatorId OBJECT-TYPE
        SYNTAX      WmanIf2mNbrOperatorId
        MAX-ACCESS  read-write
        STATUS      current
        DESCRIPTION
            "The unique network ID shared by an association of BS. The
             'Operator IE' field is present only if Bit #0 of
             wmanIf2mBsSkipOptions is 0."
        REFERENCE
            "Subclause 6.3.2.3.43"
        ::= { wmanIf2mBsNeighborAdvCommonEntry 2 }

wmanIf2mBsNumOfNeighbors OBJECT-TYPE
        SYNTAX      Unsigned32 (0 .. 15)
        MAX-ACCESS  read-write
        STATUS      current
        DESCRIPTION
            "The count of the unique combination of Neighbor BSID,
             Preamble Index, and DCD."
        REFERENCE
            "Subclause 6.3.2.3.47 in IEEE Std 802.16e-2005"
        ::= { wmanIf2mBsNeighborAdvCommonEntry 3 }

wmanIf2mBsConfigChangeCount OBJECT-TYPE
        SYNTAX      INTEGER (0 .. 255)
        MAX-ACCESS  read-write
        STATUS      current
        DESCRIPTION
            "Incremented by one (modulo 256) whenever any of the values
             relating to any included data element changes, including
             DCD and UCD parameters. If the value of this count in a
             subsequent MOB_NBR-ADV message remains the same, the MS
             can quickly disregard the entire message."
        REFERENCE
            "Subclause 6.3.2.3.47 in IEEE Std 802.16e-2005"
        ::= { wmanIf2mBsNeighborAdvCommonEntry 4 }
                           
wmanIf2mBsNeighborAdvertizementTable OBJECT-TYPE
        SYNTAX      SEQUENCE OF WmanIf2mBsNeighborAdvertizementEntry
        MAX-ACCESS  not-accessible
        STATUS      current
        DESCRIPTION
            "This table contains the attributes specific to each neighbor
             BS for the MOB_NBR-ADV message."
        REFERENCE
            "Subclause 6.3.2.3.47, in IEEE Std 802.16e-2005"
        ::= { wmanIf2mBsNeighborAdv 2 }

wmanIf2mBsNeighborAdvertizementEntry OBJECT-TYPE
        SYNTAX      WmanIf2mBsNeighborAdvertizementEntry
        MAX-ACCESS  not-accessible
        STATUS      current
        DESCRIPTION
            "This table provides one row for each neighboring BSs."
        INDEX     { ifIndex, wmanIf2mBsNeighborBsIndex }
        ::= { wmanIf2mBsNeighborAdvertizementTable 1 }

WmanIf2mBsNeighborAdvertizementEntry::= SEQUENCE {
        wmanIf2mBsNeighborBsIndex               INTEGER,
        wmanIf2mBsNeighborBsId                  WmanIf2mNbrBsId,
        wmanIf2mBsPhyProfileId                  WmanIf2mPhyProfileId,
        wmanIf2mBsFaIndex                       Unsigned32,        
        wmanIf2mBsEirp                          INTEGER,
        wmanIf2mBsPreampleSubchIndex            Unsigned32,
        wmanIf2mBsHandoverProcOptimization      WmanIf2mHoProcOptm,
        wmanIf2mBsSchedulingService             WmanIf2mSchedulingSupp,
        wmanIf2mBsChannelBandwidth              INTEGER,
        wmanIf2mBsFftSize                       WmanIf2mOfdmaFftSize,
        wmanIf2mBsCyclicPrefix                  WmanIf2mOfdmaCp,
        wmanIf2mBsFrameDurationCode             WmanIf2mOfdmaFrame,
        wmanIf2mBsMobilityFeatureSupported      WmanIf2mOfdmaMobility,
        wmanIf2mBsNrbBsPagingGroupListIndex     INTEGER,
        wmanIf2BsNeighborAdvertizementRowStatus RowStatus}

wmanIf2mBsNeighborBsIndex OBJECT-TYPE
        SYNTAX      INTEGER (0 .. 15)
        MAX-ACCESS  not-accessible
        STATUS      current
        DESCRIPTION
            "Index to entries in wmanIf2mBsNeighborAdvertizementTable."
        ::= { wmanIf2mBsNeighborAdvertizementEntry 1 }
        
wmanIf2mBsNeighborBsId OBJECT-TYPE
        SYNTAX      WmanIf2mNbrBsId
        MAX-ACCESS  read-create
        STATUS      current
        DESCRIPTION
            "The least significant 24 bits of the Base Station ID
             parameter in the DL-MAP message of the Neighbor BS. The
             'Neighbor BSID' field is present only if Bit #1 of
             wmanIf2mBsSkipOptions bitmap is 0."
        ::= { wmanIf2mBsNeighborAdvertizementEntry 2 }
                
wmanIf2mBsPhyProfileId OBJECT-TYPE
        SYNTAX      WmanIf2mPhyProfileId
        MAX-ACCESS  read-create
        STATUS      current
        DESCRIPTION
            "Aggregated IDs of Co-located FA Indicator, FA Configuration
             Indicator, FFT size, Bandwidth, Operation Mode of the
             starting subchannelization of a frame, and Channel Number."
        REFERENCE
            "Subclause 6.3.2.3.43, Table 142"
        ::= { wmanIf2mBsNeighborAdvertizementEntry 3 }
                        
wmanIf2mBsFaIndex OBJECT-TYPE
        SYNTAX      Unsigned32 (0..255)
        MAX-ACCESS  read-create
        STATUS      current
        DESCRIPTION
            "This field is present only if the faIndexInd bit in
             WmanIf2mPhyProfileId is set to 1. Its definition shall be
             determined by a service provider or a governmental body
             like FCC after the licensed band is determined."
        REFERENCE
            "Subclause 6.3.2.3.43, Table 142"
        ::= { wmanIf2mBsNeighborAdvertizementEntry 4 }        
                        
wmanIf2mBsEirp OBJECT-TYPE
        SYNTAX      INTEGER (-128 .. 127)
        UNITS       "dBm"
        MAX-ACCESS  read-create
        STATUS      current
        DESCRIPTION
            "This field is present only if the bsEirpInd bit in
             WmanIf2mPhyProfileId is not set. Otherwise, the BS has the
             same EIRP as the serving BS."
        REFERENCE
            "Subclause 6.3.2.3.43, Table 142"
        ::= { wmanIf2mBsNeighborAdvertizementEntry 5 }                
                        
wmanIf2mBsPreampleSubchIndex OBJECT-TYPE
        SYNTAX      Unsigned32 (0 .. 255)
        MAX-ACCESS  read-create
        STATUS      current
        DESCRIPTION
            "OFDMA PHY - this field defines the PHY specific preamble.
             OFDM PHY - the 5 LSB contain the active DL subchannel
                        index. The 3 MSB shall be Reserved and set to
                        '0b000'"
        REFERENCE
            "Subclause 6.3.2.3.43, Table 142"
        ::= { wmanIf2mBsNeighborAdvertizementEntry 6 }
                        
wmanIf2mBsHandoverProcOptimization OBJECT-TYPE
        SYNTAX      WmanIf2mHoProcOptm
        MAX-ACCESS  read-create
        STATUS      current
        DESCRIPTION
            "This field is present only if omitHoProcOptimization bit in
             WmanIf2mPhyProfileId is not set. Each bit in this field
             indicates certain reentry message may be omitted."
        REFERENCE
            "Subclause 6.3.2.3.43, Table 142"
        ::= { wmanIf2mBsNeighborAdvertizementEntry 7 }
                        
wmanIf2mBsSchedulingService OBJECT-TYPE
        SYNTAX      WmanIf2mSchedulingSupp
        MAX-ACCESS  read-create
        STATUS      current
        DESCRIPTION
            "This field is present only if omitQosRelatedField bit in
             WmanIf2mPhyProfileId is not set."
        REFERENCE
            "Subclause 6.3.2.3.43, Table 142"
        ::= { wmanIf2mBsNeighborAdvertizementEntry 8 }

wmanIf2mBsChannelBandwidth OBJECT-TYPE
        SYNTAX      INTEGER (0 .. 127)
        UNITS       "125KHz"
        MAX-ACCESS  read-create
        STATUS      current
        DESCRIPTION
            "This field indicates the channel BW in units of 125 kHz."
        REFERENCE
            "Subclause 11.18.1 in IEEE Std 802.16e-2005"
        ::= { wmanIf2mBsNeighborAdvertizementEntry 9 }

wmanIf2mBsFftSize OBJECT-TYPE
        SYNTAX      WmanIf2mOfdmaFftSize
        MAX-ACCESS  read-create
        STATUS      current
        DESCRIPTION
            "This field indicates the channel BW in units of 125 kHz
             for OFDMA PHY."
        REFERENCE
            "Subclause 11.18.1, Table 384b in IEEE Std 802.16e-2005"
        ::= { wmanIf2mBsNeighborAdvertizementEntry 10 }

wmanIf2mBsCyclicPrefix OBJECT-TYPE
        SYNTAX      WmanIf2mOfdmaCp
        MAX-ACCESS  read-create
        STATUS      current
        DESCRIPTION
            "This field indicates the CP for OFDMA PHY."
        REFERENCE
            "Subclause 11.18.1, Table 574"
        ::= { wmanIf2mBsNeighborAdvertizementEntry 11 }

wmanIf2mBsFrameDurationCode OBJECT-TYPE
        SYNTAX      WmanIf2mOfdmaFrame
        MAX-ACCESS  read-create
        STATUS      current
        DESCRIPTION
            "This field indicates the frame duration for ODMA PHY."
        REFERENCE
            "Subclause 11.18.1, Table 574"
        ::= { wmanIf2mBsNeighborAdvertizementEntry 12 }

wmanIf2mBsMobilityFeatureSupported OBJECT-TYPE
        SYNTAX      WmanIf2mOfdmaMobility
        MAX-ACCESS  read-create
        STATUS      current
        DESCRIPTION
            "This field indicates whether the neighbor BS supports
             mobility features."
        REFERENCE
            "Subclause 11.7.14.1"
        ::= { wmanIf2mBsNeighborAdvertizementEntry 13 }

wmanIf2mBsNrbBsPagingGroupListIndex OBJECT-TYPE
        SYNTAX      INTEGER (0 .. 65535)
        MAX-ACCESS  read-create
        STATUS      current
        DESCRIPTION
            "If idle mode is supported, this index maps to 
             wmanIf2mBsPagingGroupListId in wmanIf2mBsPagingGroupsTable
             , and is used to identify the list of paging group IDs,
             assigned to a neighbor BS."
        ::= { wmanIf2mBsNeighborAdvertizementEntry 14 }
                                        
wmanIf2BsNeighborAdvertizementRowStatus OBJECT-TYPE
        SYNTAX      RowStatus
        MAX-ACCESS  read-create
        STATUS      current
        DESCRIPTION
            "This object is used to create a new row or modify or delete
             an existing row in this table. If the implementator of this
             MIB has choosen not to implement 'dynamic assignment' of
             profiles, this object is not useful and should return
             noSuchName upon SNMP request."
        ::= { wmanIf2mBsNeighborAdvertizementEntry 15 }
                                 
wmanIf2mBsNeighborBsOfdmaUcdTable OBJECT-TYPE
        SYNTAX      SEQUENCE OF WmanIf2mBsNeighborBsOfdmaUcdEntry
        MAX-ACCESS  not-accessible
        STATUS      current
        DESCRIPTION
            "This table contains the attributes of the UCD message for
             the neighboring BSs."
        REFERENCE
            "Table 349 and Table 353, in IEEE Std 802.16-2004"
        ::= { wmanIf2mBsNeighborAdv 3 }

wmanIf2mBsNeighborBsOfdmaUcdEntry OBJECT-TYPE
        SYNTAX      WmanIf2mBsNeighborBsOfdmaUcdEntry
        MAX-ACCESS  not-accessible
        STATUS      current
        DESCRIPTION
            "This table provides one row for each neighboring BS."
        INDEX     { wmanIf2mBsNeighborBsId }
        ::= { wmanIf2mBsNeighborBsOfdmaUcdTable 1 }

WmanIf2mBsNeighborBsOfdmaUcdEntry ::= SEQUENCE {
        wmanIf2mBsOfdmaCtBasedResvTimeout       INTEGER,
        wmanIf2mBsOfdmaUplinkCenterFreq         Unsigned32,       
        wmanIf2mBsOfdmaStartOfRngCodes          INTEGER,
        wmanIf2mBsOfdmaPermutationBase          INTEGER,
        wmanIf2mBsOfdmaULAllocSubchBitmap       OCTET STRING,
        wmanIf2mBsOfdmaOptPermULAlloSubchBitmap OCTET STRING,
        wmanIf2mBsOfdmaBandAMCAllocThreshold    INTEGER,
        wmanIf2mBsOfdmaBandAMCReleaseThreshold  INTEGER,
        wmanIf2mBsOfdmaBandAMCAllocTimer        INTEGER,
        wmanIf2mBsOfdmaBandAMCReleaseTimer      INTEGER,
        wmanIf2mBsOfdmaBandStatRepMAXPeriod     INTEGER,
        wmanIf2mBsOfdmaBandAMCRetryTimer        INTEGER,
        wmanIf2mBsOfdmaHandoverRangingStart     INTEGER,
        wmanIf2mBsOfdmaHandoverRangingEnd       INTEGER,
        wmanIf2mBsOfdmaHARQAackDelayDLBurst     WmanIf2mHarqAckDelay,
        wmanIf2mBsOfdmaUlAmcAlloPhyBandsBitmap  OCTET STRING,
        wmanIf2mBsOfdmaMaxRetransmission        INTEGER,
        wmanIf2mBsOfdmaNormalizedCnOverride     OCTET STRING,
        wmanIf2mBsOfdmaSizeOfCqichId            INTEGER,
        wmanIf2mBsOfdmaNormalizedCnValue        INTEGER,
        wmanIf2mBsOfdmaNormalizedCnOverride2    OCTET STRING,
        wmanIf2mBsOfdmaBandAmcEntryAvgCinr      INTEGER,
        wmanIf2mBsOfdmaAasPreambleUpperBond     INTEGER,
        wmanIf2mBsOfdmaAasPreambleLowerBond     INTEGER,
        wmanIf2mBsOfdmaAasBeamSelectAllowed     INTEGER,
        wmanIf2mBsOfdmaCqichIndicationFlag      OCTET STRING,
        wmanIf2mBsOfdmaUpPowerAdjStep           Unsigned32,
        wmanIf2mBsOfdmaDownPowerAdjStep         Unsigned32,
        wmanIf2mBsOfdmaMinPowerOffsetAdj        INTEGER,
        wmanIf2mBsOfdmaMaxPowerOffsetAdj        INTEGER,
        wmanIf2mBsOfdmaHandoverRngCodes         INTEGER,
        wmanIf2mBsOfdmaInitialRngInterval       INTEGER,
        wmanIf2mBsOfdmaTxPwrRepThreshold        INTEGER,
        wmanIf2mBsOfdmaTprPower                 INTEGER,
        wmanIf2mBsOfdmaAlphaPavg                INTEGER,
        wmanIf2mBsOfdmaCqichTxPwrRepThreshold   INTEGER,
        wmanIf2mBsOfdmaCqichTprPower            INTEGER,
        wmanIf2mBsOfdmaCqichAlphaPavg           INTEGER,
        wmanIf2mBsOfdmaNormalizedCnChSounding   INTEGER,
        wmanIf2mBsOfdmaInitialRngBackoffStart   INTEGER,
        wmanIf2mBsOfdmaInitialRngBackoffEnd     INTEGER,
        wmanIf2mBsOfdmaBwRequestBackoffStart    INTEGER,
        wmanIf2mBsOfdmaBwRequestBackoffEnd      INTEGER}

wmanIf2mBsOfdmaCtBasedResvTimeout OBJECT-TYPE
        SYNTAX      INTEGER (1..255)
        MAX-ACCESS  read-write
        STATUS      current
        DESCRIPTION
            "The number of UL-MAPs to receive before contention-based
             reservation is attempted again for the same connection."
        REFERENCE
            "Table 349, in IEEE Std 802.16-2004"
        ::= { wmanIf2mBsNeighborBsOfdmaUcdEntry 1 }

wmanIf2mBsOfdmaUplinkCenterFreq OBJECT-TYPE
        SYNTAX      Unsigned32 
        UNITS       "kHz"
        MAX-ACCESS  read-write
        STATUS      current
        DESCRIPTION
            " Uplink center frequency (kHz)"
        REFERENCE
            "Table 349, in IEEE Std 802.16-2004"
        ::= { wmanIf2mBsNeighborBsOfdmaUcdEntry 2 }

wmanIf2mBsOfdmaStartOfRngCodes OBJECT-TYPE
        SYNTAX      INTEGER (0..255)
        MAX-ACCESS  read-write
        STATUS      current
        DESCRIPTION
            "Indicates the starting number, S, of the group of codes
             used for this uplink.All the ranging codes used on this
             uplink will be between S and ((S+N+M+L) mod 256). Where,
               N: the number of initial-ranging codes
               M: the number of periodic-ranging codes
               L: the number of bandwidth-request codes
               O: the number of handover-ranging codes"
        REFERENCE
            "Subclause 11.3.1, Table 353, in IEEE Std 802.16e-2005"
        DEFVAL 	    { 0 }
        ::= { wmanIf2mBsNeighborBsOfdmaUcdEntry 3 }

wmanIf2mBsOfdmaPermutationBase OBJECT-TYPE
        SYNTAX      INTEGER (0..255)
        MAX-ACCESS  read-write
        STATUS      current
        DESCRIPTION
            "Determines the UL_PermBase parameter for the subcarrier
             permutation to be used on this uplink channel.
                 UL_PermBase = 7 LSBs of Permutation base."
        REFERENCE
            "Subclause 11.3.1, Table 353, in IEEE Std 802.16-2004"
        DEFVAL 	    { 0 }
        ::= { wmanIf2mBsNeighborBsOfdmaUcdEntry 4 }

wmanIf2mBsOfdmaULAllocSubchBitmap OBJECT-TYPE
        SYNTAX      OCTET STRING (SIZE (9))
        MAX-ACCESS  read-write
        STATUS      current
        DESCRIPTION
            "This is a bitmap describing the physical sub-channels
             allocated to the segment in the UL, when using the uplink
             PUSC permutation. The LSB of the first byte shall corrspond
             to subchannel 0. For any bit that is not set, the
             corresponding subchannel shall not be used by the SS on
             that segment"
        REFERENCE
            "Subclause 11.3.1, Table 353, in IEEE Std 802.16e-2005"
        ::= { wmanIf2mBsNeighborBsOfdmaUcdEntry 5 }

wmanIf2mBsOfdmaOptPermULAlloSubchBitmap OBJECT-TYPE
        SYNTAX      OCTET STRING (SIZE (13))
        MAX-ACCESS  read-write
        STATUS      current
        DESCRIPTION
            "This is a bitmap describing the sub-channels allocated to
             the segment in the UL, when using the uplink optional PUSC
             permutation (see 8.4.6.2.5 in IEEE Std 802.16-2004). The
             LSB of the first byte shall correspond to subchannel 0.
             For any bit that is not set, the corresponding subchannel
             shall not be used by the SS on that segment. When this TLV
             is not present, BS may allocate any subchannels to an SS."
        REFERENCE
            "Subclause 11.3.1, Table 353, in IEEE Std 802.16-2004"
        ::= { wmanIf2mBsNeighborBsOfdmaUcdEntry 6 }

wmanIf2mBsOfdmaBandAMCAllocThreshold OBJECT-TYPE
        SYNTAX      INTEGER (0 .. 255)
        UNITS       "dB"
        MAX-ACCESS  read-write
        STATUS      current
        DESCRIPTION
            "Threshold of the maximum of the standard deviations of the
             individual bands CINR measurements over time to trigger
             mode transition from normal subchannel to Band AMC"
        REFERENCE
            "Subclause 11.3.1, Table 353, in IEEE Std 802.16e-2005"
        ::= { wmanIf2mBsNeighborBsOfdmaUcdEntry 7 }

wmanIf2mBsOfdmaBandAMCReleaseThreshold OBJECT-TYPE
        SYNTAX      INTEGER (0 .. 255)
        UNITS       "dB"
        MAX-ACCESS  read-write
        STATUS      current
        DESCRIPTION
            "Threshold of the maximum of the standard deviations of the
             individual bands CINR measurements over time to trigger
             mode transition from Band AMC to normal subchannel"
        REFERENCE
            "Subclause 11.3.1, Table 353, in IEEE Std 802.16e-2005"
        ::= { wmanIf2mBsNeighborBsOfdmaUcdEntry 8 }

wmanIf2mBsOfdmaBandAMCAllocTimer OBJECT-TYPE
        SYNTAX      INTEGER (0 .. 255)
        UNITS       "Frame"
        MAX-ACCESS  read-write
        STATUS      current
        DESCRIPTION
            "Minimum required number of frames to measure the average
             and standard deviation for the event of Band AMC triggering"
        REFERENCE
            "Subclause 11.3.1, Table 353, in IEEE Std 802.16e-2005"
        ::= { wmanIf2mBsNeighborBsOfdmaUcdEntry 9 }

wmanIf2mBsOfdmaBandAMCReleaseTimer OBJECT-TYPE
        SYNTAX      INTEGER (0 .. 255)
        UNITS       "Frame"
        MAX-ACCESS  read-write
        STATUS      current
        DESCRIPTION
            "Minimum required number of frames to measure the average
             and standard deviation for the event triggering from Band
             AMC to normal subchannel"
        REFERENCE
            "Subclause 11.3.1, Table 353, in IEEE Std 802.16e-2005"
        ::= { wmanIf2mBsNeighborBsOfdmaUcdEntry 10 }

wmanIf2mBsOfdmaBandStatRepMAXPeriod OBJECT-TYPE
        SYNTAX      INTEGER (0 .. 255)
        UNITS       "Frame"
        MAX-ACCESS  read-write
        STATUS      current
        DESCRIPTION
            "Maximum period between refreshing the Band CINR
             measurement by the unsolicited REP-RSP"
        REFERENCE
            "Subclause 11.3.1, Table 353, in IEEE Std 802.16e-2005"
        ::= { wmanIf2mBsNeighborBsOfdmaUcdEntry 11 }

wmanIf2mBsOfdmaBandAMCRetryTimer OBJECT-TYPE
        SYNTAX      INTEGER (0 .. 255)
        UNITS       "Frame"
        MAX-ACCESS  read-write
        STATUS      current
        DESCRIPTION
            "Backoff timer between consecutive mode transitions from
             normal subchannel to Band AMC when the previous request
             is failed"
        REFERENCE
            "Subclause 11.3.1, Table 353, in IEEE Std 802.16e-2005"
        ::= { wmanIf2mBsNeighborBsOfdmaUcdEntry 12 }
        
wmanIf2mBsOfdmaHandoverRangingStart OBJECT-TYPE
        SYNTAX      INTEGER (0..15)
        MAX-ACCESS  read-write
        STATUS      current
        DESCRIPTION
            "Initial backoff window size for MS performing initial
             ranging during handover process, expressed as a power of 2."
        REFERENCE
            "Table 349, in IEEE Std 802.16e-2005"
        ::= { wmanIf2mBsNeighborBsOfdmaUcdEntry 13 }

wmanIf2mBsOfdmaHandoverRangingEnd OBJECT-TYPE
        SYNTAX      INTEGER (0..15)
        MAX-ACCESS  read-write
        STATUS      current
        DESCRIPTION
            "Final backoff window size for MS performing initial
             ranging during handover process, expressed as a power
             of 2."
        REFERENCE
            "Table 349, in IEEE Std 802.16e-2005"
        ::= { wmanIf2mBsNeighborBsOfdmaUcdEntry 14 }
        
wmanIf2mBsOfdmaHARQAackDelayDLBurst OBJECT-TYPE
        SYNTAX      WmanIf2mHarqAckDelay
        MAX-ACCESS  read-write
        STATUS      current
        DESCRIPTION
            "This object defines the OFDMA H-ARQ ACK delay for DL
             burst."
        REFERENCE 
            "Subclause 11.3.1, Table 540"
	    ::= { wmanIf2mBsNeighborBsOfdmaUcdEntry 15 }        

wmanIf2mBsOfdmaUlAmcAlloPhyBandsBitmap OBJECT-TYPE
        SYNTAX      OCTET STRING (SIZE (6))
        MAX-ACCESS  read-write
        STATUS      current
        DESCRIPTION
            "A bitmap describing the physical bands allocated to the
             segment in the UL, when using the optional AMC permutation
             with regular MAPs (see 8.4.6.3). The LSB of the first byte
             shall correspond to the physical band 0. For any bit that
             is not set, the corresponding physical bands shall not be
             used by the SS on that segment. When this TLV is not
             present, BS may allocate any physical bands to an SS."
        REFERENCE
            "Subclause 11.3.1, Table 353, in IEEE Std 802.16e-2005"
        ::= { wmanIf2mBsNeighborBsOfdmaUcdEntry 16 }

wmanIf2mBsOfdmaMaxRetransmission OBJECT-TYPE
        SYNTAX      INTEGER (1..255)
        MAX-ACCESS  read-write
        STATUS      current
        DESCRIPTION
            "Maximum number of retransmission in UL HARQ."
        REFERENCE
            "Table 353, in IEEE Std 802.16e-2005"
        DEFVAL      { 4 }
        ::= { wmanIf2mBsNeighborBsOfdmaUcdEntry 17 }
        
wmanIf2mBsOfdmaNormalizedCnOverride OBJECT-TYPE
        SYNTAX      OCTET STRING (SIZE (8))
        MAX-ACCESS  read-write
        STATUS      current
        DESCRIPTION
            "This is a list of numbers, where each number is encoded by
             one nibble, and interpreted as a signed integer. The
             nibbles correspond in order to the list define by Table
             334, starting from the second line, such that the LS
             nibble of the first byte corresponds to the second line in
             the table. The number encoded by each nibble represents
             the difference in normalized C/N relative to the previous
             line in the table."
        REFERENCE
            "Subclause 11.3.1, Table 353, in IEEE Std 802.16e-2005"
        ::= { wmanIf2mBsNeighborBsOfdmaUcdEntry 18 }        

wmanIf2mBsOfdmaSizeOfCqichId OBJECT-TYPE
        SYNTAX      INTEGER (0..7)
        MAX-ACCESS  read-write
        STATUS      current
        DESCRIPTION
            "Size of CQICH ID field.
                 0 = 0 bits
                 1 = 3 bits
                 2 = 4 bits
                 3 = 5 bits
                 4 = 6 bits
                 5 = 7 bits
                 6 = 8 bits
                 7 = 9 bits"
        REFERENCE 
            "Subclause 11.3.1, Table 353, in IEEE Std 802.16e-2005"
        DEFVAL      { 0 }
        ::= { wmanIf2mBsNeighborBsOfdmaUcdEntry 19 }
        
wmanIf2mBsOfdmaNormalizedCnValue OBJECT-TYPE
        SYNTAX      INTEGER (-128..128)
        UNITS       "dB"
        MAX-ACCESS  read-write
        STATUS      current
        DESCRIPTION
            "It shall be interpreted as signed integer in dB. It
             corresponds to the normalized C/N value in the first line
             (counting except for header cell of table)"
        REFERENCE
            "Subclause 11.3.1, Table 353, in IEEE Std 802.16e-2005"
        ::= { wmanIf2mBsNeighborBsOfdmaUcdEntry 20 }

wmanIf2mBsOfdmaNormalizedCnOverride2 OBJECT-TYPE
        SYNTAX      OCTET STRING (SIZE (7))
        MAX-ACCESS  read-write
        STATUS      current
        DESCRIPTION
            "This is a list of numbers, where each number is encoded by
             one nibble, and interpreted as a signed integer. The
             nibbles correspond in order to the list define by Table 334
             , starting from the second line (counting except for the
             header cell of table), such that the LS nibble of the first
             byte corresponds to the second line in the table. The
             number encoded by each nibble represents the difference in
             normalized C/N relative to the previous line in the table."
        REFERENCE
            "Subclause 11.3.1, Table 353, in IEEE Std 802.16e-2005"
        ::= { wmanIf2mBsNeighborBsOfdmaUcdEntry 21 }

wmanIf2mBsOfdmaBandAmcEntryAvgCinr OBJECT-TYPE
        SYNTAX      INTEGER (-128..128)
        UNITS       "dB"
        MAX-ACCESS  read-write
        STATUS      current
        DESCRIPTION
            "Threshold of the average CINR of the whole bandwidth to
             trigger mode transition from normal subchannel to AMC"
        REFERENCE
            "Subclause 11.3.1, Table 353, in IEEE Std 802.16e-2005"
        ::= { wmanIf2mBsNeighborBsOfdmaUcdEntry 22 }

wmanIf2mBsOfdmaAasPreambleUpperBond OBJECT-TYPE
        SYNTAX      INTEGER (-128..128)
        UNITS       "0.25 dB"
        MAX-ACCESS  read-write
        STATUS      current
        DESCRIPTION
            "Upper bound of AAS preamble."
        REFERENCE
            "Subclause 11.3.1, Table 353, in IEEE Std 802.16e-2005"
        ::= { wmanIf2mBsNeighborBsOfdmaUcdEntry 23 }

wmanIf2mBsOfdmaAasPreambleLowerBond OBJECT-TYPE
        SYNTAX      INTEGER (-128..128)
        UNITS       "0.25 dB"
        MAX-ACCESS  read-write
        STATUS      current
        DESCRIPTION
            "Lower bound of AAS preamble."
        REFERENCE
            "Subclause 11.3.1, Table 353, in IEEE Std 802.16e-2005"
        ::= { wmanIf2mBsNeighborBsOfdmaUcdEntry 24 }

wmanIf2mBsOfdmaAasBeamSelectAllowed OBJECT-TYPE
        SYNTAX      INTEGER {notAllowed(0),
                             allowed(1)}
        UNITS       "0.25 dB"
        MAX-ACCESS  read-write
        STATUS      current
        DESCRIPTION
            "Indicate whether unsolicited AAS Beam Select messages (see
             6.3.2.3.41 in IEEE 802.16e-2005) should be sent by the MS."
        REFERENCE
            "Subclause 11.3.1, Table 353, in IEEE Std 802.16e-2005"
        DEFVAL      { allowed }
        ::= { wmanIf2mBsNeighborBsOfdmaUcdEntry 25 }

wmanIf2mBsOfdmaCqichIndicationFlag OBJECT-TYPE
        SYNTAX      OCTET STRING (SIZE (1))
        MAX-ACCESS  read-write
        STATUS      current
        DESCRIPTION
            "The N MSB values of this field represents the N-bit payload
             value on the Fast-Feedback channel reserved as indication
             flag for MS to initiate feedback on the Feedback header,
             where N is the number of payload bits used for S/N
             measurement feedback on the Fast-Feedback channel. The
             value shall not be set to all zeros."
        REFERENCE
            "Subclause 11.3.1, Table 353, in IEEE Std 802.16e-2005"
        ::= { wmanIf2mBsNeighborBsOfdmaUcdEntry 26 }

wmanIf2mBsOfdmaUpPowerAdjStep OBJECT-TYPE
        SYNTAX      Unsigned32
        UNITS       "0.01 dB"
        MAX-ACCESS  read-write
        STATUS      current
        DESCRIPTION
            "MS-specific up power offset adjustment step"
        REFERENCE
            "Subclause 11.3.1, Table 353, in IEEE Std 802.16e-2005"   
        ::= { wmanIf2mBsNeighborBsOfdmaUcdEntry 27 }

wmanIf2mBsOfdmaDownPowerAdjStep OBJECT-TYPE
        SYNTAX      Unsigned32
        UNITS       "0.01 dB"
        MAX-ACCESS  read-write
        STATUS      current
        DESCRIPTION
            "MS-specific down power offset adjustment step"
        REFERENCE
            "Subclause 11.3.1, Table 353, in IEEE Std 802.16e-2005"   
        ::= { wmanIf2mBsNeighborBsOfdmaUcdEntry 28 }        

wmanIf2mBsOfdmaMinPowerOffsetAdj OBJECT-TYPE
        SYNTAX      INTEGER
        UNITS       "0.1 dB"
        MAX-ACCESS  read-write
        STATUS      current
        DESCRIPTION
            "Minimum level of power offset adjustment"
        REFERENCE
            "Subclause 11.3.1, Table 353, in IEEE Std 802.16e-2005"   
        ::= { wmanIf2mBsNeighborBsOfdmaUcdEntry 29 }

wmanIf2mBsOfdmaMaxPowerOffsetAdj OBJECT-TYPE
        SYNTAX      INTEGER
        UNITS       "0.1 dB"
        MAX-ACCESS  read-write
        STATUS      current
        DESCRIPTION
            "Maximum level of power offset adjustment"
        REFERENCE
            "Subclause 11.3.1, Table 353, in IEEE Std 802.16e-2005"   
        ::= { wmanIf2mBsNeighborBsOfdmaUcdEntry 30 }

wmanIf2mBsOfdmaHandoverRngCodes OBJECT-TYPE
        SYNTAX      INTEGER (0..255)
        MAX-ACCESS  read-write
        STATUS      current
        DESCRIPTION
            "Number of handover ranging CDMA codes"
        REFERENCE
            "Subclause 11.3.1, Table 353, in IEEE Std 802.16e-2005"   
        ::= { wmanIf2mBsNeighborBsOfdmaUcdEntry 31 }

wmanIf2mBsOfdmaInitialRngInterval OBJECT-TYPE
        SYNTAX      INTEGER
        MAX-ACCESS  read-write
        STATUS      current
        DESCRIPTION
            "Number of frames between initial ranging interval allocation
             ."
        REFERENCE
            "Subclause 11.3.1, Table 353, in IEEE Std 802.16e-2005"   
        ::= { wmanIf2mBsNeighborBsOfdmaUcdEntry 32 }

wmanIf2mBsOfdmaTxPwrRepThreshold OBJECT-TYPE
        SYNTAX      INTEGER (0..15)
        UNITS       "dB"
        MAX-ACCESS  read-write
        STATUS      current
        DESCRIPTION
            "Tx power report threshold.
             wmanIf2mBsOfdmaTxPwrRepThreshold = 0b1111 means infinite."
        REFERENCE
            "Subclause 11.3.1, Table 353, and 8.4.10.3.2.1 in IEEE
             Std 802.16e-2005"   
        ::= { wmanIf2mBsNeighborBsOfdmaUcdEntry 33 }

wmanIf2mBsOfdmaTprPower OBJECT-TYPE
        SYNTAX      INTEGER (0..15)
        UNITS       "dB"
        MAX-ACCESS  read-write
        STATUS      current
        DESCRIPTION
            "Tx power report interval = 2 ^ wmanIf2mBsOfdmaTprPower.
             The unit of Tx power report interval is frame. 
             wmanIf2mBsOfdmaTprPower = 0b1111 means infinite."
        REFERENCE
            "Subclause 11.3.1, Table 353, and 8.4.10.3.2.1 in IEEE
             Std 802.16e-2005"   
        ::= { wmanIf2mBsNeighborBsOfdmaUcdEntry 34 }
        
wmanIf2mBsOfdmaAlphaPavg OBJECT-TYPE
        SYNTAX      INTEGER (0..15)
        UNITS       "dB"
        MAX-ACCESS  read-write
        STATUS      current
        DESCRIPTION
            "Aplha p_avg parameter as shown in equation 138d in IEEE
             802.16e-2005 indicates the multiple of 1/16. For example
             '0' means 1/16, 15 means 16/16. "
        REFERENCE
            "Subclause 11.3.1, Table 353, and 8.4.10.3.2.1 in IEEE
             Std 802.16e-2005"   
        ::= { wmanIf2mBsNeighborBsOfdmaUcdEntry 35 }

wmanIf2mBsOfdmaCqichTxPwrRepThreshold OBJECT-TYPE
        SYNTAX      INTEGER (0..15)
        UNITS       "dB"
        MAX-ACCESS  read-write
        STATUS      current
        DESCRIPTION
            "Tx power report threshold.
             wmanIf2mBsOfdmaTxPwrRepThreshold = 0b1111 means infinite.
             It shall be used when CQICH is allocated to the SS."
        REFERENCE
            "Subclause 11.3.1, Table 353, and 8.4.10.3.2.1 in IEEE
             Std 802.16e-2005"   
        ::= { wmanIf2mBsNeighborBsOfdmaUcdEntry 36 }

wmanIf2mBsOfdmaCqichTprPower OBJECT-TYPE
        SYNTAX      INTEGER (0..15)
        UNITS       "dB"
        MAX-ACCESS  read-write
        STATUS      current
        DESCRIPTION
            "Tx power report interval = 2 ^ wmanIf2mBsOfdmaTprPower.
             The unit of Tx power report interval is frame. 
             wmanIf2mBsOfdmaTprPower = 0b1111 means infinite.
             It shall be used when CQICH is allocated to the SS."
        REFERENCE
            "Subclause 11.3.1, Table 353, and 8.4.10.3.2.1 in IEEE
             Std 802.16e-2005"   
        ::= { wmanIf2mBsNeighborBsOfdmaUcdEntry 37 }
        
wmanIf2mBsOfdmaCqichAlphaPavg OBJECT-TYPE
        SYNTAX      INTEGER (0..15)
        UNITS       "dB"
        MAX-ACCESS  read-write
        STATUS      current
        DESCRIPTION
            "Aplha p_avg parameter as shown in equation 138d in
             IEEE 802.16e-2005 indicates the multiple of 1/16. For
             example '0' means 1/16, 15 means 16/16. It shall be
             used when CQICH is allocated to the SS."
        REFERENCE
            "Subclause 11.3.1, Table 353, and 8.4.10.3.2.1 in IEEE
             Std 802.16e-2005"   
        ::= { wmanIf2mBsNeighborBsOfdmaUcdEntry 38 }
        
wmanIf2mBsOfdmaNormalizedCnChSounding OBJECT-TYPE
        SYNTAX      INTEGER
        MAX-ACCESS  read-write
        STATUS      current
        DESCRIPTION
            "Signed integer for the required C/N (dB) for Channel
             Sounding."
        REFERENCE
            "Subclause 11.3.1, Table 353, in IEEE Std 802.16e-2005"   
        ::= { wmanIf2mBsNeighborBsOfdmaUcdEntry 39 }

wmanIf2mBsOfdmaInitialRngBackoffStart OBJECT-TYPE
        SYNTAX      INTEGER (0..15)
        MAX-ACCESS  read-write
        STATUS      current
        DESCRIPTION
            "Initial backoff window size for initial ranging
             contention, expressed as a power of 2."
        REFERENCE
            "Subclause 11.3.1, Table 353, in IEEE Std 802.16e-2005"   
        ::= { wmanIf2mBsNeighborBsOfdmaUcdEntry 40 }
                
wmanIf2mBsOfdmaInitialRngBackoffEnd OBJECT-TYPE
        SYNTAX      INTEGER (0..15)
        MAX-ACCESS  read-write
        STATUS      current
        DESCRIPTION
            "Final backoff window size for initial ranging
             contention, expressed as a power of 2."
        REFERENCE
            "Subclause 11.3.1, Table 353, in IEEE Std 802.16e-2005"   
        ::= { wmanIf2mBsNeighborBsOfdmaUcdEntry 41 }
        
wmanIf2mBsOfdmaBwRequestBackoffStart OBJECT-TYPE
        SYNTAX      INTEGER (0..15)
        MAX-ACCESS  read-write
        STATUS      current
        DESCRIPTION
            "Initial backoff window size for contention BW requests,
             expressed as a power of 2."
        REFERENCE
            "Subclause 11.3.1, Table 353, in IEEE Std 802.16e-2005"   
        ::= { wmanIf2mBsNeighborBsOfdmaUcdEntry 42 }

wmanIf2mBsOfdmaBwRequestBackoffEnd OBJECT-TYPE
        SYNTAX      INTEGER (0..15)
        MAX-ACCESS  read-write
        STATUS      current
        DESCRIPTION
            "Final backoff window size for contention BW requests,
             expressed as a power of 2."
        REFERENCE
            "Subclause 11.3.1, Table 353, in IEEE Std 802.16e-2005"   
        ::= { wmanIf2mBsNeighborBsOfdmaUcdEntry 43 }
                         
wmanIf2mBsNeighborBsOfdmaDcdTable OBJECT-TYPE
        SYNTAX      SEQUENCE OF WmanIf2mBsNeighborBsOfdmaDcdEntry
        MAX-ACCESS  not-accessible
        STATUS      current
        DESCRIPTION
            "This table contains the attributes of the DCD message for
             the neighboring BSs."
        ::= { wmanIf2mBsNeighborAdv 4 }

wmanIf2mBsNeighborBsOfdmaDcdEntry OBJECT-TYPE
        SYNTAX      WmanIf2mBsNeighborBsOfdmaDcdEntry
        MAX-ACCESS  not-accessible
        STATUS      current
        DESCRIPTION
            "This table provides one row for each neighboring BS."
        INDEX     { wmanIf2mBsNeighborBsId }
        ::= { wmanIf2mBsNeighborBsOfdmaDcdTable 1 }

WmanIf2mBsNeighborBsOfdmaDcdEntry ::= SEQUENCE {
        wmanIf2mBsOfdmaBsEIRP                   INTEGER,
        wmanIf2mBsOfdmaChannelNumber            INTEGER,
        wmanIf2mBsOfdmaTTG                      INTEGER,
        wmanIf2mBsOfdmaRTG                      INTEGER,
        wmanIf2mBsOfdmaInitRngMaxRSS            INTEGER,
        wmanIf2mBsOfdmaDownlinkCenterFreq       Unsigned32,
        wmanIf2mBsOfdmaBsId                     OCTET STRING,
        wmanIf2mBsOfdmaMacVersion               WmanIf2mMacVersion,
        wmanIf2mBsOfdmaFrameDurationCode        INTEGER,
        wmanIf2mBsOfdmaHARQAackDelayULBurst     WmanIf2mHarqAckDelay,
        wmanIf2mBsOfdmaHarqZonePermutation      INTEGER,
        wmanIf2mBsOfdmaHMaxRetransmission       INTEGER,
        wmanIf2mBsOfdmaCinrAlphaAvg             INTEGER,
        wmanIf2mBsOfdmaRssiAlphaAvg             INTEGER,
        wmanIf2mBsOfdmaDlAmcAlloPhyBandsBitmap  OCTET STRING,
        wmanIf2mBsOfdmaHandoverSupported        BITS,
        wmanIf2mBsOfdmaThresholdAddBsDivSet     INTEGER,
        wmanIf2mBsOfdmaThresholdDelBsDivSet     INTEGER,
        wmanIf2mBsOfdmaAsrSlotLength            INTEGER,
        wmanIf2mBsOfdmaAsrSwitchingPeriod       INTEGER,
        wmanIf2mBsOfdmaHysteresisMargin         INTEGER,
        wmanIf2mBsOfdmaTimeToTrigger            INTEGER,
        wmanIf2mBsOfdmaRestartCount             INTEGER}

wmanIf2mBsOfdmaBsEIRP OBJECT-TYPE
        SYNTAX      INTEGER (-32768..32767)
        UNITS       "dBm"
        MAX-ACCESS  read-write
        STATUS      current
        DESCRIPTION
            "The EIRP is the equivalent isotropic radiated power of the
             base station, which is computed for a simple
             single-antenna transmitter."
        REFERENCE
            "Subclause 11.4.1, Table 358, in IEEE Std 802.16-2004"
        ::= { wmanIf2mBsNeighborBsOfdmaDcdEntry 1 }

wmanIf2mBsOfdmaChannelNumber OBJECT-TYPE
        SYNTAX      INTEGER (0 .. 199)
        MAX-ACCESS  read-write
        STATUS      current
        DESCRIPTION
            "Downlink channel number as defined in 8.5. Used for
             license-exempt operation only."
        REFERENCE
            "Subclause 11.4.1, Table 358, in IEEE Std 802.16-2004"
        ::= { wmanIf2mBsNeighborBsOfdmaDcdEntry 2 }

wmanIf2mBsOfdmaTTG OBJECT-TYPE
        SYNTAX      INTEGER (0..255)
        UNITS       "PS" 
        MAX-ACCESS  read-write
        STATUS      current
        DESCRIPTION
            "Transmit / Receive Transition Gap. Used on TDD system only."
        REFERENCE
            "Subclause 11.4.1, Table 358, in IEEE Std 802.16e-2005"
        ::= { wmanIf2mBsNeighborBsOfdmaDcdEntry 3 }

wmanIf2mBsOfdmaRTG OBJECT-TYPE
        SYNTAX      INTEGER (0..255)
        UNITS       "PS"
        MAX-ACCESS  read-write
        STATUS      current
        DESCRIPTION
            "Receive / Transmit Transition Gap. Used on TDD system only."
        REFERENCE
            "Subclause 11.4.1, Table 358, in IEEE Std 802.16e-2005"
        ::= { wmanIf2mBsNeighborBsOfdmaDcdEntry 4 }

wmanIf2mBsOfdmaInitRngMaxRSS OBJECT-TYPE
        SYNTAX      INTEGER (-32768..32767)
        UNITS       "dBm"
        MAX-ACCESS  read-write
        STATUS      current
        DESCRIPTION
            "Initial Ranging Max. equivalent isotropic received power
             at BS Signed in units of 1 dBm."
        REFERENCE
            "Subclause 11.4.1, Table 358, in IEEE Std 802.16-2004"
        ::= { wmanIf2mBsNeighborBsOfdmaDcdEntry 5 }

wmanIf2mBsOfdmaDownlinkCenterFreq OBJECT-TYPE
        SYNTAX      Unsigned32
        UNITS       "kHz"
        MAX-ACCESS  read-write
        STATUS      current
        DESCRIPTION
            "Downlink center frequency (kHz)."
        REFERENCE
            "Subclause 11.4.1, Table 358, in IEEE Std 802.16-2004"
        ::= { wmanIf2mBsNeighborBsOfdmaDcdEntry 6 }

wmanIf2mBsOfdmaBsId OBJECT-TYPE
        SYNTAX      OCTET STRING (SIZE(6))
        MAX-ACCESS  read-write
        STATUS      current
        DESCRIPTION
            "Defines the encoding of BSID. The BSID is a 6 byte number
             and follows the encoding rules of MacAddress textual
             convention, i.e. as if it were transmitted
             least-significant bit first. The value should be displayed
             with 2 parts clearly separated by a colon e.g:
             001DFF:00003A. The most significant part is representing
             the Operator ID."
        REFERENCE
            "Subclause 11.4.1, Table 358, in IEEE Std 802.16-2004"
        ::= { wmanIf2mBsNeighborBsOfdmaDcdEntry 7 }

wmanIf2mBsOfdmaMacVersion OBJECT-TYPE
        SYNTAX      WmanIf2mMacVersion
        MAX-ACCESS  read-write
        STATUS      current
        DESCRIPTION
            "This parameter specifies the version of 802.16 to which
             the message originator conforms."
        REFERENCE
            "Subclause 11.4.1, Table 358, in IEEE Std 802.16-2004"
        ::= { wmanIf2mBsNeighborBsOfdmaDcdEntry 8 }

wmanIf2mBsOfdmaFrameDurationCode OBJECT-TYPE
        SYNTAX      INTEGER {aasGap(0),
                             duration2ms(1),
                             duration2dot5ms(2),
                             duration4ms(3),
                             duration5ms(4),
                             duration8ms(5),
                             duration10ms(6),
                             duration12dot5ms(7),
                             duration20ms(8)}
        MAX-ACCESS  read-write
        STATUS      current
        DESCRIPTION
            "The duration of the frame. The frame duration code values
             are specified in Table 274."
        REFERENCE
            "Table 274, in IEEE Std 802.16-2004"
        ::= { wmanIf2mBsNeighborBsOfdmaDcdEntry 9 }        

wmanIf2mBsOfdmaHARQAackDelayULBurst OBJECT-TYPE
        SYNTAX      WmanIf2mHarqAckDelay
        MAX-ACCESS  read-write
        STATUS      current
        DESCRIPTION
            "This object defines the OFDMA H-ARQ ACK delay for UL
             burst."
        REFERENCE 
            "Table 358, in IEEE Std 802.16e-2005"
        ::= { wmanIf2mBsNeighborBsOfdmaDcdEntry 10 }

wmanIf2mBsOfdmaHarqZonePermutation OBJECT-TYPE
        SYNTAX      INTEGER {pusc(1),
                             fusc(2),
                             optionalFusc(3),
                             amc(4)}
        MAX-ACCESS  read-write
        STATUS      current
        DESCRIPTION
            "Permutation type for broadcast region in HARQ zone"
        REFERENCE
            "Table 358, in IEEE Std 802.16e-2005"
        ::= { wmanIf2mBsNeighborBsOfdmaDcdEntry 11 }

wmanIf2mBsOfdmaHMaxRetransmission OBJECT-TYPE
        SYNTAX      INTEGER (0..255)
        MAX-ACCESS  read-write
        STATUS      current
        DESCRIPTION
            "Maximum number of retransmission in DL HARQ."
        REFERENCE
            "Table 358, in IEEE Std 802.16e-2005"
        DEFVAL      { 4 }
        ::= { wmanIf2mBsNeighborBsOfdmaDcdEntry 12 }
        
wmanIf2mBsOfdmaCinrAlphaAvg OBJECT-TYPE
        SYNTAX      INTEGER (0..15)
        MAX-ACCESS  read-write
        STATUS      current
        DESCRIPTION
            "Bit 0..3 of Default RSSI and CINR averaging parameter TLV.
             
             Default averaging parameter Alpha Avg for physical CINR
             measurements, in multiples of 1/16. For example
             '0' means 1/16, 15 means 16/16."
        REFERENCE
            "Table 358, in IEEE Std 802.16e-2005"   
        DEFVAL      { 3 }
        ::= { wmanIf2mBsNeighborBsOfdmaDcdEntry 13 }
       
wmanIf2mBsOfdmaRssiAlphaAvg OBJECT-TYPE
        SYNTAX      INTEGER (0..15)
        MAX-ACCESS  read-write
        STATUS      current
        DESCRIPTION
            "Bit 0..3 of Default RSSI and CINR averaging parameter TLV.
             
             Default averaging parameter Alpha Avg for physical RSSI
             measurements, in multiples of 1/16. For example
             '0' means 1/16, 15 means 16/16."
        REFERENCE
            "Table 358, in IEEE Std 802.16e-2005"   
        DEFVAL      { 3 }
        ::= { wmanIf2mBsNeighborBsOfdmaDcdEntry 14 }        

wmanIf2mBsOfdmaDlAmcAlloPhyBandsBitmap OBJECT-TYPE
        SYNTAX      OCTET STRING (SIZE (6))
        MAX-ACCESS  read-write
        STATUS      current
        DESCRIPTION
            "A bitmap describing the physical bands allocated to the
             segment in the DL, when allocating AMC subchannels
             through the HARQ MAP, or through the Normal MAP, or for
             Band-AMC CINR reports, or using the optional AMC
             permutation (see 8.4.6.3). The LSB of the first byte
             shall correspond to band 0. For any bit that is not set,
             the corresponding band shall not be used by the SS on
             that segment. When this TLV is not present, BS may
             allocate any physical bands to an SS."
        REFERENCE
            "Table 358, in IEEE Std 802.16e-2005"
        ::= { wmanIf2mBsNeighborBsOfdmaDcdEntry 15 }

wmanIf2mBsOfdmaHandoverSupported OBJECT-TYPE
        SYNTAX      BITS {handover(0),
                          mdHandover(1),
                          fbssHandover(2)}
        MAX-ACCESS  read-write
        STATUS      current
        DESCRIPTION
            "Indicates the types of handover supported.
             Bit #0 = HO
             Bit #1 = MDHO
             Bit #2 = FBSS HO."
        REFERENCE
            "Table 358, in IEEE Std 802.16e-2005"   
        ::= { wmanIf2mBsNeighborBsOfdmaDcdEntry 16 }
       
wmanIf2mBsOfdmaThresholdAddBsDivSet OBJECT-TYPE
        SYNTAX      INTEGER (0..255)
        UNITS       "dB"
        MAX-ACCESS  read-write
        STATUS      current
        DESCRIPTION
            "Threshold used by the MS to add a neighbor BS to the
             diversity set. When the CINR of a neighbor BS is higher
             than H_Add_Threshold, the MS should send MOB_MSHO-REQ to
             request adding this neighbor BS to the diversity set.
             This threshold is used for the MS that is performing 
             MDHO/FBSS HO. If the BS does not support FBSS HO/MDHO,
             this value is not set."
        REFERENCE
            "Table 358, in IEEE Std 802.16e-2005"   
        ::= { wmanIf2mBsNeighborBsOfdmaDcdEntry 17 }
       
wmanIf2mBsOfdmaThresholdDelBsDivSet OBJECT-TYPE
        SYNTAX      INTEGER (0..255)
        UNITS       "dB"
        MAX-ACCESS  read-write
        STATUS      current
        DESCRIPTION
            "Threshold used by the MS to delete a neighbor BS to the
             diversity set. When the CINR of a neighbor BS is lower
             than H_Add_Threshold, the MS should send MOB_MSHO-REQ to
             request dropping this neighbor BS to the diversity set.
             This threshold is used for the MS that is performing 
             MDHO/FBSS HO. If the BS does not support FBSS HO/MDHO,
             this value is not set."
        REFERENCE
            "Table 358, in IEEE Std 802.16e-2005"   
        ::= { wmanIf2mBsNeighborBsOfdmaDcdEntry 18 }
       
wmanIf2mBsOfdmaAsrSlotLength OBJECT-TYPE
        SYNTAX      INTEGER (0..15)
        UNITS       "Frames"
        MAX-ACCESS  read-write
        STATUS      current
        DESCRIPTION
            "Bit 0..3 of ASR Slot Length and Switching Period. For FBSS
             operation, the time axis is slotted by an ASR (Anchor
             Switch Reporting) slot that is
             wmanIf2mBsOfdmaAsrSlotLength frame long."
        REFERENCE
            "Table 358, in IEEE Std 802.16e-2005"   
        ::= { wmanIf2mBsNeighborBsOfdmaDcdEntry 19 }	                            
       
wmanIf2mBsOfdmaAsrSwitchingPeriod OBJECT-TYPE
        SYNTAX      INTEGER (0..15)
        UNITS       "ASR slots"
        MAX-ACCESS  read-write
        STATUS      current
        DESCRIPTION
            "Bit 0..3 of ASR Slot Length and Switching Period.
             A switching period is introduced whose duration is equals
             to wmanIf2mBsOfdmaAsrSwitchingPeriod ASR slots that should
             be long enough such that certain process (e.g., HARQ
             transmission, backhaul context transfer) can be completed
             at the current anchor BS before the MS switches to the new
             anchor BS."
        REFERENCE
            "Table 358, in IEEE Std 802.16e-2005"   
        ::= { wmanIf2mBsNeighborBsOfdmaDcdEntry 20 }

wmanIf2mBsOfdmaHysteresisMargin OBJECT-TYPE
        SYNTAX      INTEGER (0..57)
        UNITS       "dB"
        MAX-ACCESS  read-write
        STATUS      current
        DESCRIPTION
            "When the CINR of a neighbor BS is larger than the sum of
             the CINR of the current serving BS and 
             wmanIf2mBsOfdmaHysteresisMargin for the time-to-trigger
             duration, then the neighbor BS is included in the list
             of possible target BSs in MOB_MSHO-REQ."
        REFERENCE
            "Table 358, in IEEE Std 802.16e-2005"   
        ::= { wmanIf2mBsNeighborBsOfdmaDcdEntry 21 }

wmanIf2mBsOfdmaTimeToTrigger OBJECT-TYPE
        SYNTAX      INTEGER
        UNITS       "milliseconds"
        MAX-ACCESS  read-write
        STATUS      current
        DESCRIPTION
            "Indicates the time duration for MS decides to select a
             neighbor BS as a possible target BS. It is  applicable only
             for HHO."
        REFERENCE
            "Table 358, in IEEE Std 802.16e-2005"   
        ::= { wmanIf2mBsNeighborBsOfdmaDcdEntry 22 }

wmanIf2mBsOfdmaRestartCount OBJECT-TYPE
        SYNTAX      INTEGER (0..255)
        MAX-ACCESS  read-only
        STATUS      current
        DESCRIPTION
            "The value is incremented by one whenever BS restarts (see
             6.3.9.11). The value rolls over from 0 to 255."
        REFERENCE
            "Table 358, in IEEE Std 802.16e-2005"   
        ::= { wmanIf2mBsNeighborBsOfdmaDcdEntry  23 }

wmanIf2mBsPaging OBJECT IDENTIFIER ::= { wmanIf2mBsCm 4 }

--
-- wmanIf2mBsPagingAdvertizementTable       
--             
wmanIf2mBsPagingAdvertizementTable OBJECT-TYPE
        SYNTAX      SEQUENCE OF WmanIf2mBsPagingAdvertizementEntry
        MAX-ACCESS  not-accessible
        STATUS      current
        DESCRIPTION
            "This table contains the attributes that BS broadcasts in 
             the MOB_PAG-ADV message."
        REFERENCE
            "Subclause 6.3.2.3.56, Table 109p in IEEE Std 802.16e-2005"
        ::= { wmanIf2mBsPaging 1 }

wmanIf2mBsPagingAdvertizementEntry OBJECT-TYPE
        SYNTAX      WmanIf2mBsPagingAdvertizementEntry
        MAX-ACCESS  not-accessible
        STATUS      current
        DESCRIPTION
            ""
        INDEX     { ifIndex }
        ::= { wmanIf2mBsPagingAdvertizementTable 1 }
                                                              
WmanIf2mBsPagingAdvertizementEntry ::= SEQUENCE {
        wmanIf2mBsPagingGroupListIndex          INTEGER,
        wmanIf2mBsPagingRspWindow               INTEGER,
        wmanIf2mBsPagingAdvRowStatus            RowStatus}
                    
wmanIf2mBsPagingGroupListIndex OBJECT-TYPE
        SYNTAX      INTEGER (0 .. 65535)
        MAX-ACCESS  read-create
        STATUS      current
        DESCRIPTION
            "wmanIf2mBsPagingGroupListIndex maps to 
             wmanIf2mBsPagingGroupListId in wmanIf2mBsPagingGroupsTable
             , and is used to identify the list of paging group IDs."
        ::= { wmanIf2mBsPagingAdvertizementEntry 1 }

wmanIf2mBsPagingRspWindow OBJECT-TYPE
        SYNTAX      INTEGER (0 .. 255)
        UNITS       "Frames"
        MAX-ACCESS  read-create
        STATUS      current
        DESCRIPTION
            "OFDMA-PHY specific parameter used to indicate the time
             window during which the MS shall transmit the CDMA code at
             the transmission opportunity assigned in the CDMA code and
             transmission opportunity assignment TLV. The start of the
             window is the next frame after receiving the MOB_PAG-ADV."
        REFERENCE
            "Subclause 11.17.2 in IEEE Std 802.16e-2005"
        ::= { wmanIf2mBsPagingAdvertizementEntry 2 }
        
wmanIf2mBsPagingAdvRowStatus OBJECT-TYPE
        SYNTAX          RowStatus
        MAX-ACCESS      read-create
        STATUS          current
        DESCRIPTION
            "This object is used to ensure that the write, create,
             delete operation to multiple columns is guaranteed to be
             treated as atomic operation by agent."
        ::= { wmanIf2mBsPagingAdvertizementEntry 3 }

wmanIf2mBsMsPagedTable OBJECT-TYPE
        SYNTAX      SEQUENCE OF WmanIf2mBsMsPagedEntry
        MAX-ACCESS  not-accessible
        STATUS      current
        DESCRIPTION
            "This table contains the MSs that are paged in the
             MOB_PAG-ADV message."
        REFERENCE
            "Subclause 6.3.2.3.56, Table 109p in IEEE Std 802.16e-2005"
        ::= { wmanIf2mBsPaging 2 }

wmanIf2mBsMsPagedEntry OBJECT-TYPE
        SYNTAX      WmanIf2mBsMsPagedEntry
        MAX-ACCESS  not-accessible
        STATUS      current
        DESCRIPTION
            ""
        INDEX     { wmanIf2mBsSsMacAddress }
        ::= { wmanIf2mBsMsPagedTable 1 }
                                                              
WmanIf2mBsMsPagedEntry ::= SEQUENCE {
        wmanIf2mBsSsMacAddrHash                 WmanIf2mSsMacAddrHash,
        wmanIf2mBsPagingActionCode              WmanIf2mPagingAction,
        wmanIf2mBsCdmaCode                      INTEGER,
        wmanIf2mBsTransmitOpportunity           INTEGER}
               
wmanIf2mBsSsMacAddrHash OBJECT-TYPE
        SYNTAX      WmanIf2mSsMacAddrHash
        MAX-ACCESS  read-only
        STATUS      current
        DESCRIPTION
        	"The hash is obtained by computing a CRC24 on the MS 48-bit
             MAC address. The polynomial for the calculation is
             0x1864CFB"
        REFERENCE
            "Subclause 6.3.2.3.52, Table 152"
        ::= { wmanIf2mBsMsPagedEntry 1 }

wmanIf2mBsPagingActionCode OBJECT-TYPE
        SYNTAX      WmanIf2mPagingAction
        MAX-ACCESS  read-only
        STATUS      current
        DESCRIPTION
        	"Paging action instruction to MS."
        REFERENCE
            "Subclause 6.3.2.3.52, Table 152"
        ::= { wmanIf2mBsMsPagedEntry 2 }

wmanIf2mBsCdmaCode OBJECT-TYPE
        SYNTAX      INTEGER (0 .. 255)
        MAX-ACCESS  read-only
        STATUS      current
        DESCRIPTION
            "OFDMA-PHY specific parameter used to indicate CDMA code
             and assigned to one or more MSs being paged in this
             message. One CDMA code assignment in the TLV corresponds
             to one MS paged. If wmanIf2mBsPagingActionCode is 'No
             Action Required', then it should return 0."
        REFERENCE
            "Subclause 11.17.1 in IEEE Std 802.16e-2005"
        ::= { wmanIf2mBsMsPagedEntry 3 }

wmanIf2mBsTransmitOpportunity OBJECT-TYPE
        SYNTAX      INTEGER (0 .. 65535)
        MAX-ACCESS  read-only
        STATUS      current
        DESCRIPTION
            "OFDMA-PHY specific parameter used to indicate transmission
             opportunity assigned to one or more MSs being paged in this
             message. One transmission opportunity assignment in the TLV
             corresponds to one MS paged. If wmanIf2mBsPagingActionCode
             is 'No Action Required', then it should return 0."
        REFERENCE
            "Subclause 11.17.1 in IEEE Std 802.16e-2005"
        ::= { wmanIf2mBsMsPagedEntry 4 }
                
wmanIf2mBsPagingGroupsTable OBJECT-TYPE
        SYNTAX      SEQUENCE OF WmanIf2mBsPagingGroupsEntry
        MAX-ACCESS  not-accessible
        STATUS      current
        DESCRIPTION
            "This table contains paging group IDs that BS can broadcast
             in the MOB_PAG-ADV message."
        REFERENCE            
            "Table 109f and Table 358 in IEEE Std 802.16e-2005"
        ::= { wmanIf2mBsPaging 3 }

wmanIf2mBsPagingGroupsEntry OBJECT-TYPE
        SYNTAX      WmanIf2mBsPagingGroupsEntry
        MAX-ACCESS  not-accessible
        STATUS      current
        DESCRIPTION
            "Each entry contains a paging group ID. If multiple paging
             group IDs are to be formed in a list that will be
             broadcast by a BS, these paging group IDs should be
             identified by the same wmanIf2mBsPagingGroupListId value."
        INDEX     { wmanIf2mBsPagingGroupListId,
                    wmanIf2mBsPagingGroupId }
        ::= { wmanIf2mBsPagingGroupsTable 1 }

WmanIf2mBsPagingGroupsEntry ::= SEQUENCE {
        wmanIf2mBsPagingGroupListId             INTEGER,
        wmanIf2mBsPagingGroupId                 INTEGER,
        wmanIf2BsPagingGroupsRowStatus          RowStatus}

wmanIf2mBsPagingGroupListId OBJECT-TYPE
        SYNTAX      INTEGER (0 .. 65535)
        MAX-ACCESS  not-accessible
        STATUS      current
        DESCRIPTION
            "The index to the wmanIf2mBsPagingGroupsTable."
        REFERENCE            
            "Table 109f in IEEE Std 802.16e-2005"
        ::= { wmanIf2mBsPagingGroupsEntry 1 }

wmanIf2mBsPagingGroupId OBJECT-TYPE
        SYNTAX      INTEGER (0 .. 65535)
        MAX-ACCESS  not-accessible
        STATUS      current
        DESCRIPTION
            "This field indicates the ID of the paging group."
        REFERENCE
            "Subclause 6.3.2.3.47, Table 109f in IEEE Std 802.16e-2005"
        ::= { wmanIf2mBsPagingGroupsEntry 2 }

wmanIf2BsPagingGroupsRowStatus OBJECT-TYPE
        SYNTAX          RowStatus
        MAX-ACCESS      read-create
        STATUS          current
        DESCRIPTION
            "This object is used to ensure that the write, create,
             delete operation to multiple columns is guaranteed to be
             treated as atomic operation by agent."
        ::= { wmanIf2mBsPagingGroupsEntry 3 }


wmanIf2mBsServiceFlow OBJECT IDENTIFIER ::= { wmanIf2mBsCm 5 }

wmanIf2mBsServiceFlowTable OBJECT-TYPE
        SYNTAX      SEQUENCE OF WmanIf2mBsServiceFlowEntry
        MAX-ACCESS  not-accessible
        STATUS      current
        DESCRIPTION
            "This table contains the service flow database. When an SS
             first registers at the BS, the BS should download the
             SS' service flow profile (e.g. QoS parameter set and
             classification rules) from the home AAA server.
             
             For fixed or normadic SS, its service flow profile will
             not be changed in the entire duration of the session.    
             
             For portable or mobile SS, when the SS handoffs to another
             BS, as part of the context transfer, the serving BS should
             transfer service flow profile to the target BS. After the
             handoff, the old serving BS shall change the
             wmanIf2mBsServiceFlowState of the service flows, previously
             used by the SS to 'inactive'.
             
             The BS may cleanup wmanIf2mBsServiceFlowTable periodically,
             by removing those entries with wmanIf2mBsServiceFlowState
             = 'inactive'."
        REFERENCE            
            "Subclause 6.3.14 in IEEE Std 802.16e-2005"
        ::= { wmanIf2mBsServiceFlow 1 }

wmanIf2mBsServiceFlowEntry OBJECT-TYPE
        SYNTAX      WmanIf2mBsServiceFlowEntry
        MAX-ACCESS  not-accessible
        STATUS      current
        DESCRIPTION
            "This table provides one row for each service flow. It
             supports both unicast and multicast service flows:
             Unicast - a SS (wmanIf2mBsSsMacAddress) may contain
                       multiple service flows (wmanIf2mBsSsSfId)
             Multicast - a service flow (wmanIf2mBsSsSfId) may be
                         multicast to multiple SS
                         (wmanIf2mBsSsMacAddress)"
        INDEX     { ifIndex,
                    wmanIf2mBsSsMacAddress,
                    wmanIf2mBsSsSfId }
        ::= { wmanIf2mBsServiceFlowTable 1 }

WmanIf2mBsServiceFlowEntry ::= SEQUENCE {
        wmanIf2mBsSsMacAddress                  MacAddress,
        wmanIf2mBsServiceFlowDirection          WmanIf2mSfDirection,
        wmanIf2mBsProvisionedGlobalServiceClass WmanIf2mGlobalSrvClass,
        wmanIf2mBsAdmittedGlobalServiceClass    WmanIf2mGlobalSrvClass,
        wmanIf2mBsActiveGlobalServiceClass      WmanIf2mGlobalSrvClass,
        wmanIf2mBsProvisionedQoSProfileIndex    INTEGER,
        wmanIf2mBsAdmittedQoSProfileIndex       INTEGER,
        wmanIf2mBsActiveQoSProfileIndex         INTEGER,        
        wmanIf2mBsArqAttributeIndex             INTEGER,
        wmanIf2mBsServiceFlowState              WmanIf2mSfState,
        wmanIf2mBsCid                           INTEGER,
        wmanIf2mBsSfCsSpecification             WmanIf2mCsSpecification,
        wmanIf2mBsSfMinTolerableTrafficRate     Unsigned32,
        wmanIf2mBsSfReqTxPolicy                 WmanIf2mReqTxPolicy, 
        wmanIf2mBsSfTargetSaid                  INTEGER,
        wmanIf2mBsSfEstablishTime               TimeStamp,
        wmanIf2mBsSfTerminateTime               TimeStamp}

wmanIf2mBsSsMacAddress OBJECT-TYPE
        SYNTAX      MacAddress
        MAX-ACCESS  not-accessible
        STATUS      current
        DESCRIPTION
            "The MAC address of the SS that the service flow is
             associated with."
        ::= { wmanIf2mBsServiceFlowEntry 1 }
                
wmanIf2mBsServiceFlowDirection OBJECT-TYPE
        SYNTAX      WmanIf2mSfDirection
        MAX-ACCESS  read-only
        STATUS      current
        DESCRIPTION
            "An attribute indicating the direction of a service flow."
        ::= { wmanIf2mBsServiceFlowEntry 2 }                        

wmanIf2mBsProvisionedGlobalServiceClass OBJECT-TYPE
        SYNTAX      WmanIf2mGlobalSrvClass
        MAX-ACCESS  read-only
        STATUS      current
        DESCRIPTION
            "This object defines the ProvisionedQoSParamSet for this
             service flow. When '0' is returned from reading this object
             , it means either no global service class is defined, or
             its Qos profile may be defined in
             wmanIf2mBsProvisionedQoSProfileIndex."
        REFERENCE
            "Subclause 6.3.14.4.1 Table 124a in IEEE Std 802.16e-2005"
        ::= { wmanIf2mBsServiceFlowEntry 3 }

wmanIf2mBsAdmittedGlobalServiceClass OBJECT-TYPE
        SYNTAX      WmanIf2mGlobalSrvClass
        MAX-ACCESS  read-only
        STATUS      current
        DESCRIPTION
            "This object defines the AdmittededQoSParamSet for this
             service flow. When '0' is returned from reading this object
             , it means either no global service class is defined, or
             its Qos profile may be defined in
             wmanIf2mBsAdmittedQoSProfileIndex. AdmittededQoSParamSet is
             a subset of ProvisionedQoSParamSet."
        REFERENCE
            "Subclause 6.3.14.4.1 Table 124a in IEEE Std 802.16e-2005"
        ::= { wmanIf2mBsServiceFlowEntry 4 }

wmanIf2mBsActiveGlobalServiceClass OBJECT-TYPE
        SYNTAX      WmanIf2mGlobalSrvClass
        MAX-ACCESS  read-only
        STATUS      current
        DESCRIPTION
            "This object defines the ActiveQoSParamSet for this service
             flow. When '0' is returned from reading this object, it
             means either no global service class is defined, or its Qos
             profile may be defined in wmanIf2mBsActiveQoSProfileIndex.
             ActiveQoSParamSet is a subset of AdmittededQoSParamSet."
        REFERENCE
            "Subclause 6.3.14.4.1 Table 124a in IEEE Std 802.16e-2005"
        ::= { wmanIf2mBsServiceFlowEntry 5 }

wmanIf2mBsProvisionedQoSProfileIndex OBJECT-TYPE
        SYNTAX      INTEGER (1 .. 65535)
        MAX-ACCESS  read-only
        STATUS      current
        DESCRIPTION
            "This index points to an entry in wmanIf2mBsQoSProfileTable
             that defines the ProvisionedQoSParamSet of a service flow.
             If WmanIf2mSfState = 'provisioned', then
             ProvisionedQoSParamSet is the QoS profile for this service
             flow. When '0' is returned from reading this object, it
             means the QoS profile either is not defined, or is defined
             in wmanIf2mBsProvisionedQoSProfileIndex."
        REFERENCE            
            "Subclause 6.3.13 and 6.3.14 in IEEE Std 802.16-2004"
        ::= { wmanIf2mBsServiceFlowEntry 6 }

wmanIf2mBsAdmittedQoSProfileIndex OBJECT-TYPE
        SYNTAX      INTEGER (1 .. 65535)
        MAX-ACCESS  read-only
        STATUS      current
        DESCRIPTION
            "This index points to an entry in wmanIf2mBsQoSProfileTable
             that defines the AdmittedQoSParamSet of a service flow. If
             WmanIf2mSfState = 'admitted', then AdmittedQoSParamSet is
             the QoS profile for this service flow. When '0' is returned
             from reading this object, it means the QoS profile either
             is not defined, or is defined in
             wmanIf2mBsAdmittedQoSProfileIndex. AdmittededQoSParamSet is
             a subset of ProvisionedQoSParamSet."
        REFERENCE            
            "Subclause 6.3.13 and 6.3.14 in IEEE Std 802.16-2004"
        ::= { wmanIf2mBsServiceFlowEntry 7 }

wmanIf2mBsActiveQoSProfileIndex OBJECT-TYPE
        SYNTAX      INTEGER (1 .. 65535)
        MAX-ACCESS  read-only
        STATUS      current
        DESCRIPTION
            "This index points to an entry in wmanIf2mBsQoSProfileTable
             that defines the ActiveQoSParamSet of a service flow. If
             WmanIf2mSfState = 'active', then ActiveQoSParamSet is the
             QoS profile for this service flow. When '0' is returned
             from reading this object, it means the QoS profile either
             is not defined, or is defined in
             wmanIf2mBsActiveQoSProfileIndex. ActiveQoSParamSet is a
             subset of AdmittedQoSParamSet."
        REFERENCE            
            "Subclause 6.3.13 and 6.3.14 in IEEE Std 802.16-2004"
        ::= { wmanIf2mBsServiceFlowEntry 8 }

wmanIf2mBsArqAttributeIndex OBJECT-TYPE
        SYNTAX      INTEGER (1 .. 65535)
        MAX-ACCESS  read-only
        STATUS      current
        DESCRIPTION
            "This index points to an entry in
             wmanIf2mBsArqAttributeTable that defines the ARQ
             attributes for a service flow. When '0' is returned from
             reading this object, it means the ARQ attributes are not
             defined for this service flow."
        REFERENCE            
            "Subclause 11.13.19.3.5 in IEEE Std 802.16-2004"
        ::= { wmanIf2mBsServiceFlowEntry 9 }
                                        
wmanIf2mBsServiceFlowState OBJECT-TYPE
        SYNTAX      WmanIf2mSfState
        MAX-ACCESS  read-only
        STATUS      current
        DESCRIPTION
            "wmanIf2SsServiceFlowState determines the state of a service
             flow."
        REFERENCE
            "Subclause 6.3.14.2"
        ::= { wmanIf2mBsServiceFlowEntry 10 }
        
wmanIf2mBsCid OBJECT-TYPE
        SYNTAX      INTEGER (0 .. 65535)
        MAX-ACCESS  read-only
        STATUS      current
        DESCRIPTION
            "A 16 bit channel identifier points to the connection being
             created by DSA for this service flow. When '0' is returned
             from reading this object, it means no CID has been assigned
             to this service flow yet."
        ::= { wmanIf2mBsServiceFlowEntry 11 }                

wmanIf2mBsSfCsSpecification OBJECT-TYPE
        SYNTAX      WmanIf2mCsSpecification
        MAX-ACCESS  read-only
        STATUS      current
        DESCRIPTION
            "This parameter specifies the convergence sublayer
             encapsulation mode."
        REFERENCE
            "Subclause 11.13.19.1 in IEEE Std 802.16-2004"
        ::= { wmanIf2mBsServiceFlowEntry 12 }

wmanIf2mBsSfMinTolerableTrafficRate OBJECT-TYPE
        SYNTAX      Unsigned32
        UNITS       "bps"
        MAX-ACCESS  read-only
        STATUS      current
        DESCRIPTION
            "Minimum Tolerable Traffic Rate = R (bits/sec) with time
             base T(sec) means the following. Let S denote additional
             demand accumulated at the MAC SAP of the transmitter
             during an arbitrary time interval of the length T. Then the
             amount of data forwarded at the receiver to CS (in bits)
             during this interval should be not less than min {S, R * T}
             ."
        REFERENCE
            "Subclause 11.13.9 in IEEE Std 802.16-2004"
        ::= { wmanIf2mBsServiceFlowEntry 13 }

wmanIf2mBsSfReqTxPolicy OBJECT-TYPE
        SYNTAX      WmanIf2mReqTxPolicy 
        MAX-ACCESS  read-only
        STATUS      current
        DESCRIPTION
            "The value of this parameter provides the capability to
             specify certain attributes for the associated service flow.
             An attribute is enabled by setting the corresponding bit
             position to 1."
        REFERENCE
            "Subclause 11.13.12"
        ::= { wmanIf2mBsServiceFlowEntry 14 }

wmanIf2mBsSfTargetSaid OBJECT-TYPE
        SYNTAX      INTEGER (0 .. 65535)
        MAX-ACCESS  read-only
        STATUS      current
        DESCRIPTION
            "The target SAID parameter indicates the SAID onto which the
             service flow being set up shall be mapped."
        REFERENCE
            "Subclause 11.13.17 in IEEE Std 802.16e-2005"
        ::= { wmanIf2mBsServiceFlowEntry 15 }
        
wmanIf2mBsSfEstablishTime OBJECT-TYPE
        SYNTAX      TimeStamp
        MAX-ACCESS  read-only
        STATUS      current
        DESCRIPTION
            "Indicates the date and time when the service flow is
             established that means wmanIf2mBsServiceFlowState is
             either in 'provisioned', 'admitted', or 'active' state."
        ::= { wmanIf2mBsServiceFlowEntry 16 }

wmanIf2mBsSfTerminateTime OBJECT-TYPE
        SYNTAX      TimeStamp
        MAX-ACCESS  read-only
        STATUS      current
        DESCRIPTION
            "Indicates the date and time when the service flow is
             terminated that means wmanIf2mBsServiceFlowState is
             in 'inactive' state."
        ::= { wmanIf2mBsServiceFlowEntry 17 }

wmanIf2mBsClassifierRuleTable OBJECT-TYPE
        SYNTAX      SEQUENCE OF WmanIf2mBsClassifierRuleEntry
        MAX-ACCESS  not-accessible
        STATUS      current
        DESCRIPTION
            "This table contains packet classifier rules associated
             with service flows."
        ::= { wmanIf2mBsServiceFlow 2 }

wmanIf2mBsClassifierRuleEntry OBJECT-TYPE
        SYNTAX      WmanIf2mBsClassifierRuleEntry
        MAX-ACCESS  not-accessible
        STATUS      current
        DESCRIPTION 
            "This table provides one row for each packet classifier rule
             ."
        INDEX     { ifIndex,
                    wmanIf2mBsSsMacAddress,
                    wmanIf2mBsSsSfId,
                    wmanIf2mBsClassifierRuleId }
        ::= { wmanIf2mBsClassifierRuleTable 1 }

WmanIf2mBsClassifierRuleEntry::= SEQUENCE {
        wmanIf2mBsClassifierRuleId              Unsigned32,
        wmanIf2mBsClassifierRulePriority        INTEGER,
        wmanIf2mBsClassifierRuleIpTosLow        INTEGER,
        wmanIf2mBsClassifierRuleIpTosHigh       INTEGER,
        wmanIf2mBsClassifierRuleIpTosMask       INTEGER,
        wmanIf2mBsClassifierRuleIpProtocol      Integer32,
        wmanIf2mBsClassifierRuleIpSrcAddr       InetAddress,
        wmanIf2mBsClassifierRuleIpSrcMask       InetAddress,
        wmanIf2mBsClassifierRuleIpDestAddr      InetAddress,
        wmanIf2mBsClassifierRuleIpDestMask      InetAddress,
        wmanIf2mBsClassifierRuleSrcPortStart    Integer32,
        wmanIf2mBsClassifierRuleSrcPortEnd      Integer32,
        wmanIf2mBsClassifierRuleDestPortStart   Integer32,
        wmanIf2mBsClassifierRuleDestPortEnd     Integer32,
        wmanIf2mBsClassifierRuleDestMacAddr     MacAddress,
        wmanIf2mBsClassifierRuleDestMacMask     MacAddress,
        wmanIf2mBsClassifierRuleSrcMacAddr      MacAddress,
        wmanIf2mBsClassifierRuleSrcMacMask      MacAddress,
        wmanIf2mBsClassifierRuleEnetType        INTEGER,
        wmanIf2mBsClassifierRuleEnetProtocol    Integer32,
        wmanIf2mBsClassifierRuleUserPriLow      Integer32,
        wmanIf2mBsClassifierRuleUserPriHigh     Integer32,
        wmanIf2mBsClassifierRuleVlanId          Integer32,
        wmanIf2mBsClassifierRuleIpv6FlowLabel   WmanIf2mIpv6FlowLabel,
        wmanIf2mBsClassifierRulePkts            Counter64,
        wmanIf2mBsClassifierRuleBitMap          WmanIf2mClassifierBitMap,
        wmanIf2mBsClassifierRuleAssociatedPhsi  INTEGER
                                                }
        
wmanIf2mBsClassifierRuleId  OBJECT-TYPE
        SYNTAX      Unsigned32 (1..4294967295)
        MAX-ACCESS  not-accessible
        STATUS      current
        DESCRIPTION 
            "An index is assigned to each classifier in the classifiers
             table"
        REFERENCE
            "Subclause 11.13.19.3.4.14 in IEEE Std 802.16-2004"
        ::= { wmanIf2mBsClassifierRuleEntry 1 }

wmanIf2mBsClassifierRulePriority OBJECT-TYPE
        SYNTAX      INTEGER (0..255)
        MAX-ACCESS  read-only
        STATUS      current
        DESCRIPTION
            "The value specifies the order of evaluation of the
             classifiers. The higher the value the higher the priority.
             The value of 0 is used as default in provisioned service
             flows classifiers. The default value of 64 is used for
             dynamic service flow classifiers. If the referenced
             parameter is not present in a classifier, this object
             reports the default value as defined above"
        REFERENCE
            "Subclause 11.13.19.3.4.1 in IEEE Std 802.16-2004"
        DEFVAL      { 0 }
        ::= { wmanIf2mBsClassifierRuleEntry 2 }

wmanIf2mBsClassifierRuleIpTosLow OBJECT-TYPE
        SYNTAX      INTEGER (0 .. 255)
        MAX-ACCESS  read-only
        STATUS      current
        DESCRIPTION
            "The low value of a range of TOS byte values. If the
             referenced parameter is not present in a classifier, this
             object reports the value of 0."
        REFERENCE
            "Subclause 11.13.19.3.4.2 in IEEE Std 802.16-2004"
        ::= { wmanIf2mBsClassifierRuleEntry 3 }

wmanIf2mBsClassifierRuleIpTosHigh OBJECT-TYPE
        SYNTAX      INTEGER (0 .. 255)
        MAX-ACCESS  read-only
        STATUS      current
        DESCRIPTION
            "The 8-bit high value of a range of TOS byte values. If the
             referenced parameter is not present in a classifier, this
             object reports the value of 0."
        REFERENCE
            "Subclause 11.13.19.3.4.2 in IEEE Std 802.16-2004"
        ::= { wmanIf2mBsClassifierRuleEntry 4 }

wmanIf2mBsClassifierRuleIpTosMask OBJECT-TYPE
        SYNTAX      INTEGER (0 .. 255)
        MAX-ACCESS  read-only
        STATUS      current
        DESCRIPTION
            "The mask value is bitwise ANDed with TOS byte in an IP
             packet and this value is used for the range checking of
             TosLow and TosHigh. If the referenced parameter is not
             present in a classifier, this object reports the value of
             0."
        REFERENCE
            "Subclause 11.13.19.3.4.2 in IEEE Std 802.16-2004"
        ::= { wmanIf2mBsClassifierRuleEntry 5 }

wmanIf2mBsClassifierRuleIpProtocol OBJECT-TYPE
        SYNTAX      Integer32 (0..255)
        MAX-ACCESS  read-only
        STATUS      current
        DESCRIPTION
            "This object indicates the value of the IP Protocol field
             required for IP packets to match this rule. If the
             referenced parameter is not present in a classifier, this
             object reports the value of 0."
        REFERENCE
            "Subclause 11.13.19.3.4.3 in IEEE Std 802.16-2004"
        ::= { wmanIf2mBsClassifierRuleEntry 6 }

wmanIf2mBsClassifierRuleIpSrcAddr OBJECT-TYPE
        SYNTAX      InetAddress
        MAX-ACCESS  read-only
        STATUS      current
        DESCRIPTION
            "This object specifies the value of the IP Source Address
             required for packets to match this rule. An IP packet
             matches the rule when the packet ip source address bitwise
             ANDed with the wmanIf2mBsClassifierRuleIpSrcMask value
             equals the wmanIf2mBsClassifierRuleIpSrcAddr value.
             If the referenced parameter is not present in a classifier
             , this object reports the value of 0.0.0.0."
        REFERENCE
            "Subclause 11.13.19.3.4.4 in IEEE Std 802.16-2004"
        ::= { wmanIf2mBsClassifierRuleEntry 7 }

wmanIf2mBsClassifierRuleIpSrcMask OBJECT-TYPE
        SYNTAX      InetAddress
        MAX-ACCESS  read-only
        STATUS      current
        DESCRIPTION
            "This object specifies which bits of a packet's IP Source
             Address that are compared to match this rule. An IP packet
             matches the rule when the packet source address bitwise
             ANDed with the
             wmanIf2mBsClassifierRuleIpSrcMask value equals the
             wmanIf2mBsClassifierRuleIpSrcAddr value.
             If the referenced parameter is not present in a classifier
             , this object reports the value of 0.0.0.0."
        REFERENCE
            "Subclause 11.13.19.3.4.4 in IEEE Std 802.16-2004"
        ::= { wmanIf2mBsClassifierRuleEntry 8 }

wmanIf2mBsClassifierRuleIpDestAddr OBJECT-TYPE
        SYNTAX      InetAddress
        MAX-ACCESS  read-only
        STATUS      current
        DESCRIPTION
            "This object specifies the value of the IP Destination
             Address required for packets to match this rule. An IP
             packet matches the rule when the packet IP destination
             address bitwise ANDed with the
             wmanIf2mBsClassifierRuleIpDestMask value equals the
             wmanIf2mBsClassifierRuleIpDestAddr value.
             If the referenced parameter is not present in a 
             classifier, this object reports the value of 0.0.0.0."
        REFERENCE
            "Subclause 11.13.19.3.4.5 in IEEE Std 802.16-2004"
        ::= { wmanIf2mBsClassifierRuleEntry 9 }

wmanIf2mBsClassifierRuleIpDestMask OBJECT-TYPE
        SYNTAX      InetAddress
        MAX-ACCESS  read-only
        STATUS      current
        DESCRIPTION
            "This object specifies which bits of a packet's IP 
             Destination Address that are compared to match this rule.
             An IP packet matches the rule when the packet destination
             address bitwise ANDed with the
             wmanIf2mBsClassifierRuleIpDestMask value equals the
             wmanIf2mBsClassifierRuleIpDestAddr value.
             If the referenced parameter is not present in a classifier
             , this object reports the value of 0.0.0.0."
        REFERENCE
            "Subclause 11.13.19.3.4.5 in IEEE Std 802.16-2004"
        ::= { wmanIf2mBsClassifierRuleEntry 10 }

wmanIf2mBsClassifierRuleSrcPortStart OBJECT-TYPE
        SYNTAX      Integer32 (0..65535)
        MAX-ACCESS  read-only
        STATUS      current
        DESCRIPTION
             "This object specifies the low end inclusive range of
              TCP/UDP source port numbers to which a packet is compared
              . This object is irrelevant for non-TCP/UDP IP packets.
              If the referenced parameter is not present in a
              classifier, this object reports the value of 0."
        REFERENCE
            "Subclause 11.13.19.3.4.6 in IEEE Std 802.16-2004"
        ::= { wmanIf2mBsClassifierRuleEntry 11 }

wmanIf2mBsClassifierRuleSrcPortEnd OBJECT-TYPE
        SYNTAX      Integer32 (0..65535)
        MAX-ACCESS  read-only
        STATUS      current
        DESCRIPTION
            "This object specifies the high end inclusive range of
             TCP/UDP source port numbers to which a packet is compared.
             This object is irrelevant for non-TCP/UDP IP packets.
             If the referenced parameter is not present in a classifier,
             this object reports the value of 65535."
        REFERENCE
            "Subclause 11.13.19.3.4.6 in IEEE Std 802.16-2004"
        ::= { wmanIf2mBsClassifierRuleEntry 12 }

wmanIf2mBsClassifierRuleDestPortStart OBJECT-TYPE
        SYNTAX      Integer32 (0..65535)
        MAX-ACCESS  read-only
        STATUS      current
        DESCRIPTION
            "This object specifies the low end inclusive range of
             TCP/UDP destination port numbers to which a packet is
             compared. If the referenced parameter is not present in a
             classifier, this object reports the value of 0."
        REFERENCE
            "Subclause 11.13.19.3.4.7 in IEEE Std 802.16-2004"
        ::= { wmanIf2mBsClassifierRuleEntry 13 }

wmanIf2mBsClassifierRuleDestPortEnd OBJECT-TYPE
        SYNTAX      Integer32 (0..65535)
        MAX-ACCESS  read-only
        STATUS      current
        DESCRIPTION
            "This object specifies the high end inclusive range of
             TCP/UDP destination port numbers to which a packet is
             compared. If the referenced parameter is not present
             in a classifier, this object reports the value of
             65535."
        REFERENCE
            "Subclause 11.13.19.3.4.7 in IEEE Std 802.16-2004"
        ::= { wmanIf2mBsClassifierRuleEntry 14 }

wmanIf2mBsClassifierRuleDestMacAddr OBJECT-TYPE
        SYNTAX      MacAddress
        MAX-ACCESS  read-only
        STATUS      current
        DESCRIPTION
            "An Ethernet packet matches an entry when its destination
             MAC address bitwise ANDed with 
             wmanIf2mBsClassifierRuleDestMacMask equals the value of
             wmanIf2mBsClassifierRuleDestMacAddr. If the referenced
             parameter is not present in a classifier, this object
             reports the value of '000000000000'H."
        REFERENCE
            "Subclause 11.13.19.3.4.8 in IEEE Std 802.16-2004"
        ::= { wmanIf2mBsClassifierRuleEntry 15 }

wmanIf2mBsClassifierRuleDestMacMask OBJECT-TYPE
        SYNTAX      MacAddress
        MAX-ACCESS  read-only
        STATUS      current
        DESCRIPTION
            "An Ethernet packet matches an entry when its destination
             MAC address bitwise ANDed with
             wmanIf2mBsClassifierRuleDestMacMask equals the value of
             wmanIf2mBsClassifierRuleDestMacAddr. If the referenced
             parameter is not present in a classifier, this object
             reports the value of '000000000000'H."
        REFERENCE
            "Subclause 11.13.19.3.4.8 in IEEE Std 802.16-2004"
        ::= { wmanIf2mBsClassifierRuleEntry 16 }

wmanIf2mBsClassifierRuleSrcMacAddr OBJECT-TYPE
        SYNTAX      MacAddress
        MAX-ACCESS  read-only
        STATUS      current
        DESCRIPTION
            "An Ethernet packet matches this entry when its source MAC
             address  bitwise ANDed with
             wmanIf2mBsClassifierRuleSrcMacMask equals the value of
             wmanIf2mBsClassifierRuleSrcMacAddr. If the referenced
             parameter is not present in a classifier, this object
             reports the value of '000000000000'H."
        REFERENCE
            "Subclause 11.13.19.3.4.9 in IEEE Std 802.16-2004"
        ::= { wmanIf2mBsClassifierRuleEntry 17 }

wmanIf2mBsClassifierRuleSrcMacMask OBJECT-TYPE
        SYNTAX      MacAddress
        MAX-ACCESS  read-only
        STATUS      current
        DESCRIPTION
            "An Ethernet packet matches an entry when its destination
             MAC address bitwise ANDed with
             wmanIf2mBsClassifierRuleSrcMacMask equals the value of
             wmanIf2mBsClassifierRuleSrcMacAddr. If the referenced
             parameter is not present in a classifier, this object
             reports the value of '000000000000'H."
        REFERENCE
            "Subclause 11.13.19.3.4.9 in IEEE Std 802.16-2004"
        ::= { wmanIf2mBsClassifierRuleEntry 18 }

wmanIf2mBsClassifierRuleEnetType OBJECT-TYPE
        SYNTAX      INTEGER {none(0),
                             ethertype(1),
                             dsap(2)}
        MAX-ACCESS  read-only
        STATUS      current
        DESCRIPTION
            "This object indicates the format of the layer 3 protocol
             id in the Ethernet packet. A value of none(0) means that
             the rule does not use the layer 3 protocol type as a
             matching criteria. A value of ethertype(1) means that the
             rule applies only to frames which contains an EtherType
             value. Ethertype values are contained in packets using
             the Dec-Intel-Xerox (DIX) encapsulation or the RFC1042
             Sub-Network Access Protocol (SNAP) encapsulation formats.
             A value of dsap(2) means that the rule applies only to
             frames using the IEEE802.3 encapsulation format with a
             Destination Service Access Point (DSAP) other than 0xAA
             (which is reserved for SNAP). If the Ethernet frame
             contains an 802.1P/Q Tag header (i.e. EtherType 0x8100),
             this object applies to the embedded EtherType field within
             the 802.1P/Q header. If the referenced parameter is not
             present in a classifier, this object reports the value of
             0."
        REFERENCE
            "Subclause 11.13.19.3.4.10 in IEEE Std 802.16-2004"
        ::= { wmanIf2mBsClassifierRuleEntry 19 }

wmanIf2mBsClassifierRuleEnetProtocol OBJECT-TYPE
        SYNTAX      Integer32 (0..65535)
        MAX-ACCESS  read-only
        STATUS      current
        DESCRIPTION
            "If wmanIf2mBsClassifierRuleEnetType is none(0), this
             object is ignored when considering whether a packet matches
             the current rule. If wmanIf2mBsClassifierRuleEnetType is
             ethertype(1), this object gives the 16-bit value of the
             EtherType that the packet must match in order to match the
             rule. If wmanIf2mBsClassifierRuleEnetType is dsap(2), the
             lower 8 bits of this object's value must match the DSAP
             byte of the packet in order to match the rule. 
             If the Ethernet frame contains an 802.1P/Q Tag header
             (i.e. EtherType 0x8100), this object applies to the
             embedded EtherType field within the 802.1P/Q header.
             If the referenced parameter is not present in the
             classifier, the value of this object is reported as 0."
        REFERENCE
            "Subclause 11.13.19.3.4.10 in IEEE Std 802.16-2004"
        ::= { wmanIf2mBsClassifierRuleEntry 20 }

wmanIf2mBsClassifierRuleUserPriLow OBJECT-TYPE
        SYNTAX      Integer32 (0..7)
        MAX-ACCESS  read-only
        STATUS      current
        DESCRIPTION
            "This object applies only to Ethernet frames using the
             802.1P/Q tag header (indicated with EtherType 0x8100).
             Such frames include a 16-bit Tag that contains a 3 bit
             Priority field and a 12 bit VLAN number.
             Tagged Ethernet packets must have a 3-bit Priority field
             within the range of wmanIf2mBsClassifierRulePriLow and
             wmanIf2mBsClassifierRulePriHigh in order to match this
             rule.
             If the referenced parameter is not present in the
             classifier, the value of this object is reported as 0."
        REFERENCE
            "Subclause 11.13.19.3.4.11 in IEEE Std 802.16-2004"
        ::= { wmanIf2mBsClassifierRuleEntry 21 }

wmanIf2mBsClassifierRuleUserPriHigh OBJECT-TYPE
        SYNTAX      Integer32 (0..7)
        MAX-ACCESS  read-only
        STATUS      current
        DESCRIPTION
            "This object applies only to Ethernet frames using the
            802.1P/Q tag header (indicated with EtherType 0x8100).
            Such frames include a 16-bit Tag that contains a 3 bit
            Priority field and a 12 bit VLAN number.
            Tagged Ethernet packets must have a 3-bit Priority
            field within the range of wmanIf2mBsClassifierRulePriLow
            and wmanIf2mBsClassifierRulePriHigh in order to match
            this rule.
            If the referenced parameter is not present in the 
            classifier, the value of this object is reported as 7."
        REFERENCE
            "Subclause 11.13.19.3.4.11 in IEEE Std 802.16-2004"
        ::= { wmanIf2mBsClassifierRuleEntry 22 }

wmanIf2mBsClassifierRuleVlanId OBJECT-TYPE
        SYNTAX      Integer32 (0..4095)
        MAX-ACCESS  read-only
        STATUS      current
        DESCRIPTION
            "This object applies only to Ethernet frames using the
             802.1P/Q tag header.
             If this object's value is nonzero, tagged packets must
             have a VLAN Identifier that matches the value in order
             to match the rule.
             Only the least significant 12 bits of this object's
             value are valid.
             If the referenced parameter is not present in the
             classifier, the value of this object is reported as 0."
        REFERENCE
            "Subclause 11.13.19.3.4.12 in IEEE Std 802.16-2004"
        ::= { wmanIf2mBsClassifierRuleEntry 23 }

wmanIf2mBsClassifierRuleIpv6FlowLabel OBJECT-TYPE
        SYNTAX      WmanIf2mIpv6FlowLabel
        MAX-ACCESS  read-only
        STATUS      current
        DESCRIPTION
            "The value of this field specifies the matching values for
             the IPv6 Flow label field."
        ::= { wmanIf2mBsClassifierRuleEntry 24 }

wmanIf2mBsClassifierRulePkts OBJECT-TYPE
        SYNTAX      Counter64
        MAX-ACCESS  read-only
        STATUS      current
        DESCRIPTION
            "This object counts the number of packets that have
             been classified using this entry."
        ::= { wmanIf2mBsClassifierRuleEntry 25 }
                        
wmanIf2mBsClassifierRuleBitMap OBJECT-TYPE
        SYNTAX      WmanIf2mClassifierBitMap
        MAX-ACCESS  read-only
        STATUS      current
        DESCRIPTION
            "This object indicates which parameter encodings were
             actually present in the entry. A bit set to '1' indicates
             the corresponding classifier encoding is present, and '0'
             means otherwise"
        ::= { wmanIf2mBsClassifierRuleEntry 26 }

wmanIf2mBsClassifierRuleAssociatedPhsi OBJECT-TYPE
        SYNTAX      INTEGER (1..255)
        MAX-ACCESS  read-only
        STATUS      current
        DESCRIPTION 
            "The Associated PHSI has a value between 1 and 255, which
             shall mirror the PHSI value of a PHS rule. Packets matching
             the Packet Classification Rule containing the Associated
             PHSI parameter shall undergo PHS according to the
             corresponding PHS rule. A value '0' indicates that no PHS
             rule is associated with this classifier rule."
        REFERENCE
            "Subclause 11.13.19.3.4.13 in IEEE Std 802.16-2004"
        ::= { wmanIf2mBsClassifierRuleEntry 27 }

wmanIf2mBsPhsRuleTable OBJECT-TYPE
        SYNTAX      SEQUENCE OF WmanIf2mBsPhsRuleEntry
        MAX-ACCESS  not-accessible
        STATUS      current
        DESCRIPTION                                                   
            "This table contains PHS rule dictionary entries. Each
             entry contains the data of the header to be suppressed
             along with its identification - PHSI. The classifier
             uniquely maps packets to its associated PHS Rule. The
             receiving entity uses the CID and the PHSI to restore the
             PHSF. Once a PHSF has been assigned to a PHSI, it shall
             not be changed. To change the value of a PHSF on a
             service flow, a new PHS rule shall be defined, the old
             rule is removed from the service flow, and the new rule
             is added. When all classification rules associated with
             the PHS rule are deleted, then the PHS rule shall also be
             deleted."
        REFERENCE
            "Subclause 5.2.3 in IEEE Std 802.16-2004"
        ::= { wmanIf2mBsServiceFlow 3 }

wmanIf2mBsPhsRuleEntry OBJECT-TYPE
        SYNTAX      WmanIf2mBsPhsRuleEntry
        MAX-ACCESS  not-accessible
        STATUS      current
        DESCRIPTION                                                   
            "This table provides one row for each PHS rule created
             dynamically by the BS and SS on a given service flow. The
             PHS rule is defined by the pair (PHSS, PHSM) for each
             distinct header data."
        INDEX     { ifIndex,
                    wmanIf2mBsSsMacAddress,
                    wmanIf2mBsSsSfId,        
                    wmanIf2mBsPhsRuleId }
        ::= { wmanIf2mBsPhsRuleTable 1 }
        
WmanIf2mBsPhsRuleEntry::= SEQUENCE {             
        wmanIf2mBsPhsRuleId                     INTEGER,
        wmanIf2mBsPhsRulePhsField               OCTET STRING,
        wmanIf2mBsPhsRulePhsMask                OCTET STRING,
        wmanIf2mBsPhsRulePhsSize                Integer32,
        wmanIf2mBsPhsRulePhsVerify              WmanIf2mPhsRuleVerify}
        
wmanIf2mBsPhsRuleId OBJECT-TYPE
        SYNTAX      INTEGER (1 .. 255)
        MAX-ACCESS  not-accessible
        STATUS      current
        DESCRIPTION 
            "The PHSI (PHS Index) has a value between 1 and 255, which
             uniquely references the suppressed byte string. The index
             is unique per service flow. The uplink and downlink PHSI
             values are independent of each other."
        REFERENCE
            "Subclause 11.13.19.3.7.1 in IEEE Std 802.16-2004"
        ::= { wmanIf2mBsPhsRuleEntry 1 }
        
wmanIf2mBsPhsRulePhsField OBJECT-TYPE
        SYNTAX      OCTET STRING (SIZE(0..65535))
        MAX-ACCESS  read-only
        STATUS      current
        DESCRIPTION 
            "The PHSF (PHS Field) is a string of bytes containing the
             header information to be suppressed by the sending CS and
             reconstructed by the receiving CS. The most significant
             byte of the string corresponds to the first byte of the
             CS-SDU."
        REFERENCE
            "Subclause 11.13.19.3.7.2 in IEEE Std 802.16-2004"
        ::= { wmanIf2mBsPhsRuleEntry 2 }
        
wmanIf2mBsPhsRulePhsMask OBJECT-TYPE
        SYNTAX      OCTET STRING (SIZE(0..65535))
        MAX-ACCESS  read-only
        STATUS      current
        DESCRIPTION 
            "The PHSM An 8-bit mask that indicates which bytes in the
             PHS Field (PHSF) to suppress and which bytes to not
             suppress. The PHSM allows fields, such as sequence numbers
             or checksums (which vary in value), to be excluded from
             suppression with the constant bytes around them suppressed.
             It is encodded as follows:
             bit 0:
                0 = don't suppress the 1st byte of the suppression field
                1 = suppress first byte of the suppression field
             bit 1:
                0 = don't suppress the 2nd byte of the suppression field
                1 = suppress second byte of the suppression field
             bit x:
                0 = don't suppress the (x+1) byte of the suppression
                    field
                1 = suppress (x+1) byte of the suppression field
             where the length of the octet string is ceiling
             (wmanIf2mBsPhsRulePhsSize/8)."             
        REFERENCE
            "Subclause 11.13.19.3.7.3 in IEEE Std 802.16-2004"
        ::= { wmanIf2mBsPhsRuleEntry 3 }
        
wmanIf2mBsPhsRulePhsSize OBJECT-TYPE
        SYNTAX      Integer32 (0..255)
        UNITS       "byte"
        MAX-ACCESS  read-only
        STATUS      current
        DESCRIPTION
            "The value of this field - PHSS is the total number of bytes 
             in the header to be suppressed and then restored in a
             service flow that uses PHS."
        REFERENCE
            "Subclause 11.13.19.3.7.4 in IEEE Std 802.16-2004"
        DEFVAL      {0}
        ::= { wmanIf2mBsPhsRuleEntry 4 }

wmanIf2mBsPhsRulePhsVerify OBJECT-TYPE
        SYNTAX      WmanIf2mPhsRuleVerify
        MAX-ACCESS  read-only
        STATUS      current
        DESCRIPTION
            "The value of this field indicates to the sending entity 
             whether or not the packet header contents are to be
             verified prior to performing suppression."
        DEFVAL      { phsVerifyEnable }
        ::= { wmanIf2mBsPhsRuleEntry 5 }

wmanIf2mBsQoSProfileTable OBJECT-TYPE
        SYNTAX      SEQUENCE OF WmanIf2mBsQoSProfileEntry
        MAX-ACCESS  not-accessible
        STATUS      current
        DESCRIPTION
            "This table contains QoS profiles that are associated with
             service flows or CIDs via the wmanIf2mBsQoSProfileIndex.

             The following table shows the required parameters for
             different UL grant scheduling type.     
                 0   - not required
                 1   - required
                 0-1 - optional
                                                                      
             QoS Parameters                BE  ertPS  UGS  rtPS  nrtPS               
             ---------------------------------------------------------             
             Traffic priority              0-1  0-1    0    0-1   0-1 
             Max sustained traffic rate    0-1  0-1    1    0-1   0-1
             Min reserved traffic rate      0    1    0-1    1     1
             Minimum traffic burst          0   0-1    0    0-1   0-1
             Tolerated jitter               0   0-1    1     0     0
             Maximum latency                0    1     1     1     0
             Unsolicited Grant Interval     0    1     1     0     0
             SDU size                       0    0    0-1    0     0
             Unsolicited Polling Interval   0    0     0     1     0"
        REFERENCE
            "Subclause 6.3.14.4 in IEEE Std 802.16-2004"    
        ::= { wmanIf2mBsServiceFlow 4 }

wmanIf2mBsQoSProfileEntry OBJECT-TYPE
        SYNTAX      WmanIf2mBsQoSProfileEntry
        MAX-ACCESS  not-accessible
        STATUS      current
        DESCRIPTION
            "This table provides one row for each QoS parameter Set."
        INDEX     { ifIndex, wmanIf2mBsQoSProfileIndex }
        ::= { wmanIf2mBsQoSProfileTable 1 }

WmanIf2mBsQoSProfileEntry ::= SEQUENCE {
        wmanIf2mBsQoSProfileIndex               INTEGER,
        wmanIf2mBsQosServiceClassName           OCTET STRING,
        wmanIf2mBsQosUlGrantScheduleType        WmanIf2mSchedulingType,
        wmanIf2mBsQosTrafficPriority            INTEGER,
        wmanIf2mBsQosMaximumSustainedRate       Unsigned32,
        wmanIf2mBsQosMinimumReservedRate        Unsigned32,
        wmanIf2mBsQosMaximumTrafficBurst        Unsigned32,
        wmanIf2mBsQosToleratedJitter            Unsigned32,
        wmanIf2mBsQosMaxLatency                 Unsigned32,
        wmanIf2mBsQosUnsolicitedGrantInterval   Unsigned32,            
        wmanIf2mBsQosSduSize                    Unsigned32,
        wmanIf2mBsQosUnsolicitedPollInterval    Unsigned32}
        
wmanIf2mBsQoSProfileIndex OBJECT-TYPE
        SYNTAX      INTEGER (1 .. 65535)
        MAX-ACCESS  not-accessible
        STATUS      current
        DESCRIPTION
            "The index value which uniquely identifies an entry in the
             wmanIf2mBsQoSProfileTable"
        ::= { wmanIf2mBsQoSProfileEntry 1 }
        
wmanIf2mBsQosServiceClassName  OBJECT-TYPE
        SYNTAX      OCTET STRING (SIZE(2..128))
        MAX-ACCESS  read-only
        STATUS      current
        DESCRIPTION    
            "This object is the Null-terminated string of ASCII
             characters. It refers to a predefined BS service
             configuration to be used for a service flow."
        REFERENCE
            "Subclause 11.13.3 in IEEE Std 802.16-2004"
        ::= { wmanIf2mBsQoSProfileEntry 2 }
        
wmanIf2mBsQosUlGrantScheduleType OBJECT-TYPE
        SYNTAX      WmanIf2mSchedulingType
        MAX-ACCESS  read-only
        STATUS      current
        DESCRIPTION
            "This parameter specifies the Uplink grant scheduling type
             that shall be enabled for the associated uplink service
             flow upstream service flow. If the parameter is not
             present in the corresponding 802.16 QOS Parameter Set of
             an upstream service flow, the default value is assumed."
        REFERENCE      
            "Subclause 11.13.11 in IEEE Std 802.16e-2004"
        DEFVAL	    { bestEffort }
        ::= { wmanIf2mBsQoSProfileEntry 3 }
                    
wmanIf2mBsQosTrafficPriority OBJECT-TYPE
        SYNTAX      INTEGER (0..7)
        MAX-ACCESS  read-only
        STATUS      current
        DESCRIPTION
            "The value of this parameter specifies the priority assigned
             to a service flow. For uplink service flows, the BS should
             use this parameter when determining precedence in request
             service and grant generation, Higher numbers indicate
             higher priority"
        REFERENCE
            "Subclause 11.13.5 in IEEE Std 802.16e-2005"
        ::= { wmanIf2mBsQoSProfileEntry 4 }
        
wmanIf2mBsQosMaximumSustainedRate OBJECT-TYPE
        SYNTAX      Unsigned32
        UNITS       "bps"
        MAX-ACCESS  read-only
        STATUS      current
        DESCRIPTION
            "This parameter defines the peak information rate of the
             service. The rate is expressed in bits per second and
             pertains to the SDUs at the input to the Convergence
             Sublayer."
        REFERENCE
            "Subclause 11.13.6 in IEEE Std 802.16e-2005"
        ::= { wmanIf2mBsQoSProfileEntry 5 }        
                        
wmanIf2mBsQosMinimumReservedRate OBJECT-TYPE
        SYNTAX      Unsigned32
        UNITS       "bps"
        MAX-ACCESS  read-only
        STATUS      current
        DESCRIPTION
            "This parameter specifies the minimum rate reserved for this
             service flow. It specifies the minimum amount of data to be
             transported on behalf of the service flow when averaged
             over time."
        REFERENCE
            "Subclause 11.13.8 in IEEE Std 802.16e-2004"
        ::= { wmanIf2mBsQoSProfileEntry 6 }
                        
wmanIf2mBsQosMaximumTrafficBurst OBJECT-TYPE
        SYNTAX      Unsigned32
        UNITS       "byte"
        MAX-ACCESS  read-only
        STATUS      current
        DESCRIPTION
            "This parameter defines the maximum burst size that must be
             accommodated for the service. It defines the maximum
             continuous burst the system should accommodate for the
             service assuming the service is not currently using any of
             its available resources."
        REFERENCE
            "Subclause 11.13.7 in IEEE Std 802.16-2004"
        ::= { wmanIf2mBsQoSProfileEntry 7 }
                                
wmanIf2mBsQosToleratedJitter OBJECT-TYPE
        SYNTAX      Unsigned32
        UNITS       "millisecond"
        MAX-ACCESS  read-only
        STATUS      current
        DESCRIPTION
            "This parameter defines the Maximum delay variation (jitter)
             for the connection."
        REFERENCE
            "Subclause 11.13.13 in IEEE Std 802.16-2004"
        ::= { wmanIf2mBsQoSProfileEntry 8 }
                                
wmanIf2mBsQosMaxLatency OBJECT-TYPE
        SYNTAX      Unsigned32
        UNITS       "millisecond"
        MAX-ACCESS  read-only
        STATUS      current
        DESCRIPTION
            "This parameter specifies the maximum latency between the
             ingress of a packet to the Convergence Sublayer and the
             forwarding of the SDU to its Air Interface."
        REFERENCE
            "Subclause 11.13.14 in IEEE Std 802.16-2004"
        ::= { wmanIf2mBsQoSProfileEntry 9 }

wmanIf2mBsQosUnsolicitedGrantInterval OBJECT-TYPE
        SYNTAX      Unsigned32
        UNITS       "millisecond"
        MAX-ACCESS  read-only
        STATUS      current
        DESCRIPTION
            "This object specifies the nominal interval between
             successive data grant opportunities for a service flow."
        REFERENCE
            "Subclause 11.13.20 in IEEE Std 802.16e-2004"
        ::= { wmanIf2mBsQoSProfileEntry 10 }

wmanIf2mBsQosSduSize OBJECT-TYPE
        SYNTAX      Unsigned32
        UNITS       "byte"
        MAX-ACCESS  read-only
        STATUS      current
        DESCRIPTION
            "This parameter specifies the length of the SDU for a
             fixed-length SDU service flow. It is used only if packing
             is on and the service flow is indicated as carrying
             fixed-length SDUs. If this object is omitted in the QoS
             parameter set, it should return 0 that means the
             variable-length service flow."
        REFERENCE
            "Subclause 11.13.16 in IEEE Std 802.16-2004"
        ::= { wmanIf2mBsQoSProfileEntry 11 }

wmanIf2mBsQosUnsolicitedPollInterval OBJECT-TYPE
        SYNTAX      Unsigned32
        UNITS       "millisecond"
        MAX-ACCESS  read-only
        STATUS      current
        DESCRIPTION
            "This object specifies the maximal nominal interval between
             successive polling grants opportunities for this Service
             Flow."
        REFERENCE
            "Subclause 11.13.21 in IEEE Std 802.16e-2004"
        ::= { wmanIf2mBsQoSProfileEntry 12 }
        
wmanIf2mBsArqAttributeTable OBJECT-TYPE
        SYNTAX      SEQUENCE OF WmanIf2mBsArqAttributeEntry
        MAX-ACCESS  not-accessible
        STATUS      current
        DESCRIPTION
            "This table contains ARQ parameters that are associated
             with the Service Flows."
        ::= { wmanIf2mBsServiceFlow 5 }

wmanIf2mBsArqAttributeEntry OBJECT-TYPE
        SYNTAX      WmanIf2mBsArqAttributeEntry
        MAX-ACCESS  not-accessible
        STATUS      current
        DESCRIPTION
            "This table provides one row for each created service flow
             for a given MacAddress."
        INDEX     { ifIndex, wmanIf2mBsArqIndex  }
        ::= { wmanIf2mBsArqAttributeTable 1 }

WmanIf2mBsArqAttributeEntry::= SEQUENCE {
        wmanIf2mBsArqIndex                      INTEGER,
        wmanIf2mBsArqEnable                     TruthValue,
        wmanIf2mBsArqWindowSize                 INTEGER,
        wmanIf2mBsArqBlockLifetime              INTEGER,
        wmanIf2mBsArqSyncLossTimeout            INTEGER,
        wmanIf2mBsArqDeliverInOrder             TruthValue,
        wmanIf2mBsArqRxPurgeTimeout             INTEGER,
        wmanIf2mBsArqBlockSize                  INTEGER,
        wmanIf2mBsArqAckProcessingTime          INTEGER}
       
wmanIf2mBsArqIndex OBJECT-TYPE
        SYNTAX      INTEGER ( 1 .. 65535)
        MAX-ACCESS  not-accessible
        STATUS      current
        DESCRIPTION
            "The index value which uniquely identifies an entry in the
             in the wmanIf2mBsArqAttributeTable."
        ::= { wmanIf2mBsArqAttributeEntry 1 }

wmanIf2mBsArqEnable OBJECT-TYPE
        SYNTAX      TruthValue
        MAX-ACCESS  read-only
        STATUS      current
        DESCRIPTION
            "True(1) ARQ enabling is requested for the connection."
        ::= { wmanIf2mBsArqAttributeEntry 2 }

wmanIf2mBsArqWindowSize	 OBJECT-TYPE
        SYNTAX	    INTEGER (1..1024)
        MAX-ACCESS  read-only
        STATUS      current
        DESCRIPTION
            "Indicates the maximum number of unacknowledged fragments
             at any time."
        ::= { wmanIf2mBsArqAttributeEntry 3 }

wmanIf2mBsArqBlockLifetime OBJECT-TYPE
        SYNTAX	    INTEGER (0 .. 65535)
        UNITS	    "10 us"
        MAX-ACCESS  read-only
        STATUS      current
        DESCRIPTION
            "The maximum time interval an ARQ fragment will be managed
             by the transmitter ARQ machine, once initial transmission
             of the fragment has occured. If transmission or
             retransmission of the fragment is not acknowledged by the
             receiver before the time limit is reached, the fragment is
             discarded. A value of 0 means Infinite."
        ::= { wmanIf2mBsArqAttributeEntry 4 }

wmanIf2mBsArqSyncLossTimeout OBJECT-TYPE
        SYNTAX	    INTEGER (0 .. 65535 )
        UNITS	    "10 us"
        MAX-ACCESS  read-only
        STATUS      current
        DESCRIPTION
            "The maximum interval before declaring a loss of
             synchronization of the sender and receiver state machines.
             A value of 0 means Infinite."
        ::= { wmanIf2mBsArqAttributeEntry 5 }

wmanIf2mBsArqDeliverInOrder  OBJECT-TYPE
        SYNTAX      TruthValue
        MAX-ACCESS  read-only
        STATUS      current
        DESCRIPTION
            "Indicates whether or not data is to be delivered by the
             receiving MAC to its client application in the order in
             which data was handed off to the originating MAC."
        ::= { wmanIf2mBsArqAttributeEntry 6 }

wmanIf2mBsArqRxPurgeTimeout  OBJECT-TYPE
        SYNTAX	    INTEGER (0 .. 65535)
        UNITS	    "10 us"
        MAX-ACCESS  read-only
        STATUS      current
        DESCRIPTION
            "Indicates the time interval the ARQ window is advanced
             after a fragment is received. A value of 0 means
             Infinite."
        ::= { wmanIf2mBsArqAttributeEntry 7 }

wmanIf2mBsArqBlockSize OBJECT-TYPE
        SYNTAX	    INTEGER (1..2040)
        UNITS       "byte"
        MAX-ACCESS  read-only
        STATUS      current
        DESCRIPTION
            "This value of this parameter specifies the size of an ARQ
             block. This parameter shall be established by negotiation
             during the connection creation dialog."
        REFERENCE
            "Subclause 11.13.18.8 in IEEE Std 802.16-2004"             
        ::= { wmanIf2mBsArqAttributeEntry 8 }

wmanIf2mBsArqAckProcessingTime OBJECT-TYPE
        SYNTAX	    INTEGER (0 .. 255)
        UNITS       "millisecond"
        MAX-ACCESS  read-only
        STATUS      current
        DESCRIPTION
            "This parameter indicates the number of ms required by the
             ARQ receiver to process the received ARQ blocks and provide
             a valid ACK or NAK."
        REFERENCE
            "Subclause 11.13.18.9 in IEEE Std 802.16e-2005"             
        ::= { wmanIf2mBsArqAttributeEntry 9 }

--
-- Mobile Station Sleep Mode Statistics Table
--         
wmanIf2mBsSsSleepModeStatisticsTable OBJECT-TYPE
        SYNTAX      SEQUENCE OF   WmanIf2mBsSsSleepModeStatisticsEntry
        MAX-ACCESS  not-accessible
        STATUS      current
        DESCRIPTION
            "This table contains the sleep mode statistic for MS. This
             table shall be maintained as FIFO to store the sleep mode
             statistics over a period of time that is subject to
             implementation. This statistics information can be to
             monitor, fine tuning, or debugging the power saving
             performance of each MS. When the statistics entry for an
             MS reaches the limit, it wraps around to the beginning, and
             overwrites the oldest entry with the new entry. When the BS
             roams to a different BS, all entries associated with such
             MS will be deleted."
        REFERENCE
            "6.3.21 in IEEE Std 802.16e-2005"
        ::= { wmanIf2mBsPm 1 }

wmanIf2mBsSsSleepModeStatisticsEntry OBJECT-TYPE
        SYNTAX      WmanIf2mBsSsSleepModeStatisticsEntry
        MAX-ACCESS  not-accessible
        STATUS      current
        DESCRIPTION
            "Each entry in the table contains the event of an MS
             entering the sleep mode. wmanIf2mBsSsStatisticsIndex is the
             index to sleep mode event entry in the table, and should be
             increased monotonically, and wraps around when it reaches
             the implementation specific limit. A time stamp is provided
             in each entry to indicate when the sleep mode event took
             place."
        INDEX     { ifIndex,
                    wmanIf2mBsSsMacAddress,
                    wmanIf2mBsSsCid,
                    wmanIf2mBsSsStatisticsIndex }
        ::= { wmanIf2mBsSsSleepModeStatisticsTable  1 }

WmanIf2mBsSsSleepModeStatisticsEntry ::= SEQUENCE { 
        wmanIf2mBsSsStatisticsIndex             Unsigned32,
        wmanIf2mBsSsSleepWindowStarted          Unsigned32,
        wmanIf2mBsSsListeningWindowStarted      Unsigned32,
        wmanIf2mBsSsPendingMsdu                 INTEGER,
        wmanIf2mBsSsSleepWindowTimeStamp        DateAndTime}
               
wmanIf2mBsSsStatisticsIndex OBJECT-TYPE
        SYNTAX      Unsigned32 (1 .. 4294967295) 
        MAX-ACCESS  not-accessible
        STATUS      current
        DESCRIPTION
            "wmanIf2mBsSsStatisticsIndex identifies the entry in the
             table where the latest sleep mode event took place."
        ::= { wmanIf2mBsSsSleepModeStatisticsEntry 1 }

wmanIf2mBsSsSleepWindowStarted OBJECT-TYPE
        SYNTAX      Unsigned32 (1 .. 166777215) 
        UNITS       "frame"
        MAX-ACCESS  read-only
        STATUS      current
        DESCRIPTION
            "wmanIf2mBsSsSleepWindowStarted identifies when the sleep
             mode is activated.
               wmanIf2mBsSsSleepWindowStarted = current frame number +
                                                Start_frame_number.
             The frame number is provided in the DL-MAP, and is
             incremented by 1 MOD 2^24 each frame."
        ::= { wmanIf2mBsSsSleepModeStatisticsEntry 2 }

wmanIf2mBsSsListeningWindowStarted OBJECT-TYPE
        SYNTAX      Unsigned32 (1 .. 166777215) 
        UNITS       "frame"
        MAX-ACCESS  read-only
        STATUS      current
        DESCRIPTION
            "wmanIf2mBsSsListeningWindowStarted identifies when the sleep
             mode is deactivated.
               wmanIf2mBsSsListeningWindowStarted = 
               wmanIf2mBsSsListeningWindowStarted + sleep window
             The frame number is provided in the DL-MAP, and is
             incremented by 1 MOD 2^24 each frame."
        ::= { wmanIf2mBsSsSleepModeStatisticsEntry 3 }
                                 
wmanIf2mBsSsPendingMsdu OBJECT-TYPE
        SYNTAX      INTEGER 
        MAX-ACCESS  read-only
        STATUS      current
        DESCRIPTION
            "Indicate the number of MAC SDU that are received from the
             network during the sleep window."
        ::= { wmanIf2mBsSsSleepModeStatisticsEntry 4 }

wmanIf2mBsSsSleepWindowTimeStamp OBJECT-TYPE
        SYNTAX      DateAndTime
        MAX-ACCESS  read-only
        STATUS      current
        DESCRIPTION
            "This is the time when sleep window is started in seconds.
             The definition of time is as in IETF RFC 868."
        ::= { wmanIf2mBsSsSleepModeStatisticsEntry 5 }

--
-- wmanIf2mBsMobileScanRequestTable       
--             
wmanIf2mBsMobileScanRequestTable OBJECT-TYPE
        SYNTAX      SEQUENCE OF WmanIf2mBsMobileScanRequestEntry
        MAX-ACCESS  not-accessible
        STATUS      current
        DESCRIPTION
            "This table contains the attributes that are sent in the
             MOB_SCN-REQ message."
        REFERENCE
            "Subclause 6.3.2.3.48, Table 109h in IEEE Std 802.16e-2005"
        ::= { wmanIf2mBsPm 2 }

wmanIf2mBsMobileScanRequestEntry OBJECT-TYPE
        SYNTAX      WmanIf2mBsMobileScanRequestEntry
        MAX-ACCESS  not-accessible
        STATUS      current
        DESCRIPTION
            ""
        INDEX     { ifIndex, wmanIf2mBsSsMacAddress }
        ::= { wmanIf2mBsMobileScanRequestTable 1 }
                                                              
WmanIf2mBsMobileScanRequestEntry ::= SEQUENCE {
        wmanIf2mBsScanReqDuration               INTEGER,
        wmanIf2mBsScanReqInterleavingInterval   INTEGER,
        wmanIf2mBsScanReqIteration              INTEGER,
        wmanIf2mBsNumOfRecommendedBs            INTEGER,
        wmanIf2mBsScanConfigChangeCount         INTEGER}
                    
wmanIf2mBsScanReqDuration OBJECT-TYPE
        SYNTAX      INTEGER (0 .. 255)
        UNITS       "frames"
        MAX-ACCESS  read-only
        STATUS      current
        DESCRIPTION
            "Duration of the requested scanning period."
        ::= { wmanIf2mBsMobileScanRequestEntry 1 }

wmanIf2mBsScanReqInterleavingInterval OBJECT-TYPE
        SYNTAX      INTEGER (0 .. 255)
        UNITS       "frames"
        MAX-ACCESS  read-only
        STATUS      current
        DESCRIPTION
            "The period of MS's Normal Operation which is interleaved
             between Scanning Durations."
        ::= { wmanIf2mBsMobileScanRequestEntry 2 }

wmanIf2mBsScanReqIteration OBJECT-TYPE
        SYNTAX      INTEGER (0 .. 255)
        UNITS       "frames"
        MAX-ACCESS  read-only
        STATUS      current
        DESCRIPTION
            "The requested number of iterating scanning interval by an
             MS."
        ::= { wmanIf2mBsMobileScanRequestEntry 3 }

wmanIf2mBsNumOfRecommendedBs OBJECT-TYPE
        SYNTAX      INTEGER (0 .. 255)
        MAX-ACCESS  read-only
        STATUS      current
        DESCRIPTION
            "Number of neighboring BS to be scanned or associated, which
             are included in MOB_NBR-ADV message."
        ::= { wmanIf2mBsMobileScanRequestEntry 4 }

wmanIf2mBsScanConfigChangeCount OBJECT-TYPE
        SYNTAX      INTEGER (0 .. 255)
        MAX-ACCESS  read-only
        STATUS      current
        DESCRIPTION
            "The value of Configuration Change Count in MOB_NBR-ADV
             message referred in order to compress neighbor BSID."
        ::= { wmanIf2mBsMobileScanRequestEntry 5 }        
                
--
-- wmanIf2mBsMobileScanResponseTable       
--             
wmanIf2mBsMobileScanResponseTable OBJECT-TYPE
        SYNTAX      SEQUENCE OF WmanIf2mBsMobileScanResponseEntry
        MAX-ACCESS  not-accessible
        STATUS      current
        DESCRIPTION
            "This table contains the attributes that are sent in the
             MOB_SCN-RSP message."
        REFERENCE
            "Subclause 6.3.2.3.49, Table 109i in IEEE Std 802.16e-2005"
        ::= { wmanIf2mBsPm 3 }

wmanIf2mBsMobileScanResponseEntry OBJECT-TYPE
        SYNTAX      WmanIf2mBsMobileScanResponseEntry
        MAX-ACCESS  not-accessible
        STATUS      current
        DESCRIPTION
            ""
        INDEX     { ifIndex, wmanIf2mBsSsMacAddress }
        ::= { wmanIf2mBsMobileScanResponseTable 1 }
                                                              
WmanIf2mBsMobileScanResponseEntry ::= SEQUENCE {
        wmanIf2mBsScanRspDuration               INTEGER,
        wmanIf2mBsScanRspInterleavingInterval   INTEGER,
        wmanIf2mBsScanRspIteration              INTEGER,
        wmanIf2mBsReportMode                    WmanIf2mReportMode,
        wmanIf2mBsReportPeriod                  INTEGER,
        wmanIf2mBsReportMatric                  WmanIf2mReportMatric,
        wmanIf2mBsStartFrame                    INTEGER}
                    
wmanIf2mBsScanRspDuration OBJECT-TYPE
        SYNTAX      INTEGER (0 .. 255)
        UNITS       "frames"
        MAX-ACCESS  read-only
        STATUS      current
        DESCRIPTION
            "Duration where the MS may perform scanning or association
             for Available BSs. When MOB_SCN-RSP is sent in response to
             MOB_SCN-REQ, setting Scan duration to zero indicates the
             request for an allocation of scanning interval is denied."
        ::= { wmanIf2mBsMobileScanResponseEntry 1 }

wmanIf2mBsScanRspInterleavingInterval OBJECT-TYPE
        SYNTAX      INTEGER (0 .. 255)
        UNITS       "frames"
        MAX-ACCESS  read-only
        STATUS      current
        DESCRIPTION
            "The period interleaved between Scanning Intervals when MS
             shall perform Normal Operation."
        ::= { wmanIf2mBsMobileScanResponseEntry 2 }
        
wmanIf2mBsScanRspIteration OBJECT-TYPE
        SYNTAX      INTEGER (0 .. 255)
        UNITS       "frames"
        MAX-ACCESS  read-only
        STATUS      current
        DESCRIPTION
            "The number of iterating scanning interval."
        ::= { wmanIf2mBsMobileScanResponseEntry 3 }

wmanIf2mBsReportMode OBJECT-TYPE
        SYNTAX      WmanIf2mReportMode
        MAX-ACCESS  read-only
        STATUS      current
        DESCRIPTION
            "Action code for an MS's report of CINR measurement."
        ::= { wmanIf2mBsMobileScanResponseEntry 4 }

wmanIf2mBsReportPeriod OBJECT-TYPE
        SYNTAX      INTEGER (0 .. 255)
        MAX-ACCESS  read-only
        STATUS      current
        DESCRIPTION
            "The period of MS is report of CINR measurement when the MS
             is required to report the value periodically."
        ::= { wmanIf2mBsMobileScanResponseEntry 5 }

-- change xxMatric to xxMetric
wmanIf2mBsReportMatric OBJECT-TYPE
        SYNTAX      WmanIf2mReportMatric
        MAX-ACCESS  read-only
        STATUS      current
        DESCRIPTION
            "Bitmap indicator of trigger metrics that the serving BS
             requests the MS to report."
        ::= { wmanIf2mBsMobileScanResponseEntry 6 }
        
wmanIf2mBsStartFrame OBJECT-TYPE
        SYNTAX      INTEGER (0 .. 15)
        MAX-ACCESS  read-only
        STATUS      current
        DESCRIPTION
            "Measured from the frame in which this message was received.
             A value of zero means that first Scanning Interval starts
             in the next frame."
        ::= { wmanIf2mBsMobileScanResponseEntry 7 }
        
--
-- wmanIf2mBsNeighborBsInfoTable       
--             
wmanIf2mBsNeighborBsInfoTable OBJECT-TYPE
        SYNTAX      SEQUENCE OF WmanIf2mBsNeighborBsInfoEntry
        MAX-ACCESS  not-accessible
        STATUS      current
        DESCRIPTION
            "This table contains the neighbor BS information that is
             sent in the MOB_SCN-RSP and MOB_SCN-REP messages."
        REFERENCE
            "Subclause 6.3.2.3.49 and 6.3.2.3.50, Table 109i and 109j
             in IEEE Std 802.16e-2005"
        ::= { wmanIf2mBsPm 4 }

wmanIf2mBsNeighborBsInfoEntry OBJECT-TYPE
        SYNTAX      WmanIf2mBsNeighborBsInfoEntry
        MAX-ACCESS  not-accessible
        STATUS      current
        DESCRIPTION
            ""
        INDEX     { ifIndex,
                    wmanIf2mBsSsMacAddress,
                    wmanIf2mBsNeighbirBsIndex }
        ::= { wmanIf2mBsNeighborBsInfoTable 1 }
                                                              
WmanIf2mBsNeighborBsInfoEntry ::= SEQUENCE {
        wmanIf2mBsNeighbirBsIndex               INTEGER,
        wmanIf2mBsFullBsId                      WmanIf2mFullBsId,
        wmanIf2mBsScanningType                  WmanIf2mScanType,
        wmanIf2mBsRendezvousTime                INTEGER,
        wmanIf2mBsScanCdmaCode                  INTEGER,
        wmanIf2mBsTxOpportunityOffset           INTEGER,
        wmanIf2mBsCinrMean                      INTEGER,
        wmanIf2mBsRssiMean                      INTEGER,
        wmanIf2mBsRelativeDelay                 INTEGER}
                    
wmanIf2mBsNeighbirBsIndex OBJECT-TYPE
        SYNTAX      INTEGER (0 .. 65535)
        MAX-ACCESS  not-accessible
        STATUS      current
        DESCRIPTION
            "Index to the neighbor BS."
        ::= { wmanIf2mBsNeighborBsInfoEntry 1 }

wmanIf2mBsFullBsId OBJECT-TYPE
        SYNTAX      WmanIf2mFullBsId
        MAX-ACCESS  read-only
        STATUS      current
        DESCRIPTION
            "This object contains the BS ID if full 48 bits BS ID is
             used to scan the neighbor BS. This object returns NULL if
             the Neighbor_BS_index as defined in MOB_SCN-RSP is used
             instead."
        ::= { wmanIf2mBsNeighborBsInfoEntry 2 }        

wmanIf2mBsScanningType OBJECT-TYPE
        SYNTAX      WmanIf2mScanType
        MAX-ACCESS  read-only
        STATUS      current
        DESCRIPTION
            "Type of scanning or association used by the MS and
             coordinated by the Serving BS."
        ::= { wmanIf2mBsNeighborBsInfoEntry 3 }

wmanIf2mBsRendezvousTime OBJECT-TYPE
        SYNTAX      INTEGER (0 .. 255)
        UNITS       "frames"
        MAX-ACCESS  read-only
        STATUS      current
        DESCRIPTION
            "This is offset, measured in units of frame duration (of
             Serving BS), when the corresponding Recommended BS is
             expected to provide non-contention-based ranging
             opportunity for the MS."
        ::= { wmanIf2mBsNeighborBsInfoEntry 4 }

wmanIf2mBsScanCdmaCode OBJECT-TYPE
        SYNTAX      INTEGER (0 .. 255)
        MAX-ACCESS  read-only
        STATUS      current
        DESCRIPTION
            "A unique code assigned to the MS, to be used for
             association with the neighbor BS. Code is from the initial
             ranging codeset."
        ::= { wmanIf2mBsNeighborBsInfoEntry 5 }

wmanIf2mBsTxOpportunityOffset OBJECT-TYPE
        SYNTAX      INTEGER (0 .. 255)
        MAX-ACCESS  read-only
        STATUS      current
        DESCRIPTION
            "A unique transmission opportunity assigned to the MS, to be
             used for association with the Target BS in units of symbol
             duration."
        ::= { wmanIf2mBsNeighborBsInfoEntry 6 }

wmanIf2mBsCinrMean OBJECT-TYPE
        SYNTAX      INTEGER (0 .. 255)
        UNITS       "0.5 dB" 
        MAX-ACCESS  read-only
        STATUS      current
        DESCRIPTION
            "The BS CINR mean parameter indicates the CINR measured by
             the MS from the particular BS. The value shall be
             interpreted as a signed byte with units of 0.5 dB. The
             measurement shall be performed on the subcarriers of the
             frame preamble that are active in the particular BS's
             segment and averaged over the measurement period."
        ::= { wmanIf2mBsNeighborBsInfoEntry 7 }

wmanIf2mBsRssiMean OBJECT-TYPE
        SYNTAX      INTEGER (0 .. 255)
        UNITS       "0.25 dB" 
        MAX-ACCESS  read-only
        STATUS      current
        DESCRIPTION
            "The BS RSSI mean parameter indicates the Received Signal
             Strength measured by the MS from the particular BS. The
             value shall be interpreted as an unsigned byte with units
             of 0.25 dB."
        ::= { wmanIf2mBsNeighborBsInfoEntry 8 }        

wmanIf2mBsRelativeDelay OBJECT-TYPE
        SYNTAX      INTEGER (0 .. 255)
        UNITS       "samples" 
        MAX-ACCESS  read-only
        STATUS      current
        DESCRIPTION
            "This parameter indicates the delay of neighbor DL signals
             relative to the serving BS, as measured by the MS for the
             particular BS. The value shall be interpreted as a signed
             integer in units of samples."
        ::= { wmanIf2mBsNeighborBsInfoEntry 9 }

--
-- wmanIf2mBsDiversityBsInfoTable       
--             
wmanIf2mBsDiversityBsInfoTable OBJECT-TYPE
        SYNTAX      SEQUENCE OF WmanIf2mBsDiversityBsInfoEntry
        MAX-ACCESS  not-accessible
        STATUS      current
        DESCRIPTION
            "This table contains the diversity BS information that is
             sent in the MOB_SCN-REP messages."
        REFERENCE
            "Subclause 6.3.2.3.49 and 6.3.2.3.50, Table 109i and 109j
             in IEEE Std 802.16e-2005"
        ::= { wmanIf2mBsPm 5 }

wmanIf2mBsDiversityBsInfoEntry OBJECT-TYPE
        SYNTAX      WmanIf2mBsDiversityBsInfoEntry
        MAX-ACCESS  not-accessible
        STATUS      current
        DESCRIPTION
            ""
        INDEX     { ifIndex,
                    wmanIf2mBsSsMacAddress,
                    wmanIf2mBsTempBsIndex }
        ::= { wmanIf2mBsDiversityBsInfoTable 1 }
                                                              
WmanIf2mBsDiversityBsInfoEntry ::= SEQUENCE {
        wmanIf2mBsTempBsIndex                   INTEGER,
        wmanIf2mBsFbssMdhoCinrMean              INTEGER,
        wmanIf2mBsFbssMdhoRssiMean              INTEGER,
        wmanIf2mBsFbssMdhoRelativeDelay         INTEGER,
        wmanIf2mBsFbssMdhoRtd                   INTEGER}
                    
wmanIf2mBsTempBsIndex OBJECT-TYPE
        SYNTAX      INTEGER (0 .. 15)
        MAX-ACCESS  not-accessible
        STATUS      current
        DESCRIPTION
            "Diversity set member ID assigned to this BS. When the MS
             has an empty diversity set or FBSS/MDHO is not supported,
             Temp BSID shall be set to 0.."
        ::= { wmanIf2mBsDiversityBsInfoEntry 1 }

wmanIf2mBsFbssMdhoCinrMean OBJECT-TYPE
        SYNTAX      INTEGER (0 .. 255)
        UNITS       "0.5 dB" 
        MAX-ACCESS  read-only
        STATUS      current
        DESCRIPTION
            "The BS CINR mean parameter indicates the CINR measured by
             the MS from the particular BS. The value shall be
             interpreted as a signed byte with units of 0.5 dB. The
             measurement shall be performed on the subcarriers of the
             frame preamble that are active in the particular BS's
             segment and averaged over the measurement period."
        ::= { wmanIf2mBsDiversityBsInfoEntry 2 }

wmanIf2mBsFbssMdhoRssiMean OBJECT-TYPE
        SYNTAX      INTEGER (0 .. 255)
        UNITS       "0.25 dB" 
        MAX-ACCESS  read-only
        STATUS      current
        DESCRIPTION
            "The BS RSSI mean parameter indicates the Received Signal
             Strength measured by the MS from the particular BS. The
             value shall be interpreted as an unsigned byte with units
             of 0.25 dB."
        ::= { wmanIf2mBsDiversityBsInfoEntry 3 }        

wmanIf2mBsFbssMdhoRelativeDelay OBJECT-TYPE
        SYNTAX      INTEGER (0 .. 255)
        UNITS       "samples" 
        MAX-ACCESS  read-only
        STATUS      current
        DESCRIPTION
            "This parameter indicates the delay of neighbor DL signals
             relative to the serving BS, as measured by the MS for the
             particular BS. The value shall be interpreted as a signed
             integer in units of samples."
        ::= { wmanIf2mBsDiversityBsInfoEntry 4 }

wmanIf2mBsFbssMdhoRtd OBJECT-TYPE
        SYNTAX      INTEGER (0 .. 255)
        UNITS       "1/Fs" 
        MAX-ACCESS  read-only
        STATUS      current
        DESCRIPTION
            "The BS RTD parameter indicates the round trip delay (RTD)
             measured by the MS from the serving BS. RTD can be given by
             the latest time advance taken by MS. The value shall be
             interpreted as an unsigned byte with units of 1/Fs (see
             10.3.4.3). This parameter shall be only measured on serving
             BS/anchor BS."
        ::= { wmanIf2mBsDiversityBsInfoEntry 5 }                
END
