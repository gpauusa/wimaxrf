--
-- ASIB-FT-MIB.mib
-- MIB generated by MG-SOFT Visual MIB Builder 2010 Version 8.0  Build 400
-- Thursday, September 22, 2011 at 15:30:51
--

	ASIB-FT-MIB DEFINITIONS ::= BEGIN
 
		IMPORTS
			asIb			
				FROM AIRSPAN-PRODUCTS-MIB			
			AsCmnTcBooleanSwitch, AsCmnTcResetCmd, AsCmnTcOperationalStatus			
				FROM ASCMN-TC-MIB			
			ifIndex			
				FROM IF-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			DisplayString, RowStatus, TEXTUAL-CONVENTION			
				FROM SNMPv2-TC;
	
	
		-- 1.3.6.1.4.1.989.1.21.1
		asIbFt MODULE-IDENTITY 
			LAST-UPDATED "201103290941Z"		-- March 29, 2011 at 09:41 GMT
			ORGANIZATION 
				"Airspan Communications Ltd"
			CONTACT-INFO 
				"kdudzins@airspan.com"
			DESCRIPTION 
				"Propriatory MIB for Airspan iBridge Feeder Terminal functionality on an Airspan BS."
			REVISION "201103150941Z"		-- March 15, 2011 at 09:41 GMT
			DESCRIPTION 
				"Pre-Draft 1:
				- initial version "
			REVISION "201103290941Z"		-- March 29, 2011 at 09:41 GMT
			DESCRIPTION 
				"Pre-Draft 2:
				- added asIbFtChannelListTable"
			REVISION "201109201619Z"		-- September 20, 2011 at 16:19 GMT
			DESCRIPTION 
				"Pre-Draft 3:
				- added:
				-    asIbFtActiveUlChannelTable,
				-    asIbFtActiveDlChannelTable,
				-    asIbFtUlBurstProfTable,
				-    asIbFtDlBurstProfTable,
				-    asIbFtActiveSfTable,
				-    asIbFtClassifierRuleTable
				   "
			REVISION "201109221527Z"		-- September 22, 2011 at 15:27 GMT
			DESCRIPTION 
				"Pre-Draft 4:
				- removed tables:
				-    asIbFtActiveUlChannelTable,
				-    asIbFtActiveDlChannelTable,
				-    asIbFtUlBurstProfTable,
				-    asIbFtDlBurstProfTable,
				-    asIbFtActiveSfTable,
				-    asIbFtClassifierRuleTable
				- added table:
				-    asIbFtCardTable
				
				"
			::= { asIb 1 }

		
	
--
-- Textual conventions
--
	
		AsIbFtChannelListBandwidth ::= TEXTUAL-CONVENTION
			STATUS current
			DESCRIPTION 
				"Defines common encoding of available channel bandwidths."
			SYNTAX INTEGER
				{
				bandwidth1dot75MHz(0),
				bandwidth3dot5MHz(1),
				bandwidth5MHz(2),
				bandwidth7MHz(3),
				bandwidth10MHz(4),
				bandwidth2dot75MHz(5),
				bandwidth2dot5MHz(6),
				bandwidth3MHz(7),
				bandwidth1dot5MHz(8),
				bandwidth6MHz(9),
				bandwidth8dot75MHz(10),
				bandwidth14MHz(11),
				bandwidth17dot5MHz(12),
				bandwidth20MHz(13)
				}

		AsIbFtChannelListFftSize ::= TEXTUAL-CONVENTION
			STATUS current
			DESCRIPTION 
				"Defines possible FFT sizes for the channel"
			SYNTAX INTEGER
				{
				fftSize2048(0),
				fftSize1024(1),
				fftSize512(2),
				fftSize256(3),
				fftSize128(4)
				}

		AsIbFtChannelListCpSize ::= TEXTUAL-CONVENTION
			STATUS current
			DESCRIPTION 
				"Defines possible cyclic prefix sizes for the channel"
			SYNTAX INTEGER
				{
				cpSize32(0),
				cpSize16(1),
				cpSize8(2),
				cpSize4(3)
				}

		AsIbFtChannelListFrameDuration ::= TEXTUAL-CONVENTION
			STATUS current
			DESCRIPTION 
				"Defines possible frame durations for the channel"
			SYNTAX INTEGER { duration5ms(0) }

		ModulationType ::= TEXTUAL-CONVENTION
			STATUS current
			DESCRIPTION 
				"Description."
			SYNTAX INTEGER
				{
				ofdmaQpskCc12(0),
				ofdmaQpskCc34(1),
				ofdma16qamCc12(2),
				ofdma16qamCc34(3),
				ofdma64qamCc12(4),
				ofdma64qamCc23(5),
				ofdma64qamCc34(6),
				ofdmaQpskBtc12(7),
				ofdmaQpskBtc34(8),
				ofdma16qamBtc35(9),
				ofdma16qamBtc45(10),
				ofdma64qamBtc58(11),
				ofdma64qamBtc45(12),
				ofdmaQpskCtc12(13),
				ofdmaQpskCtc34(15),
				ofdma16qamCtc12(16),
				ofdma16qamCtc34(17),
				ofdma64qamCtc12(18),
				ofdma64qamCtc23(19),
				ofdma64qamCtc34(20),
				ofdma64qamCtc56(21),
				ofdmaQpskZtcc12(22),
				ofdmaQpskZtcc34(23),
				ofdma16qamZtcc12(24),
				ofdma16qamZtcc34(25),
				ofdma64qamZtcc12(26),
				ofdma64qamZtcc23(27),
				ofdma64qamZtcc34(28),
				ofdmaQpskLdpc12(29),
				ofdmaQpskLdpc23a(30),
				ofdmaQpskLdpc34a(31),
				ofdma16qamLdpc12(32),
				ofdma16qamLdpc23a(33),
				ofdma16qamLdpc34a(34),
				ofdma64qamLdpc12(35),
				ofdma64qamLdpc23a(36),
				ofdma64qamLdpc34a(37),
				ofdmaQpskLdpc23b(38),
				ofdmaQpskLdpc34b(39),
				ofdma16qamLdpc23b(40),
				ofdma16qamLdpc34b(41),
				ofdma64qamLdpc23b(42),
				ofdma64qamLdpc34b(43),
				ofdmaQpskCco12(44),
				ofdmaQpskCco34(45),
				ofdma16qamCco12(46),
				ofdma16qamCco34(47),
				ofdma64qamCco23(48),
				ofdma64qamCco34(49),
				ofdmaQpskLdpc56(50),
				ofdma16qamLdpc56(51),
				ofdma64qamLdpc56(52)
				}

	
--
-- Node definitions
--
	
		-- 1.3.6.1.4.1.989.1.21.1.1
		asIbFtConformance OBJECT IDENTIFIER ::= { asIbFt 1 }

		
		-- 1.3.6.1.4.1.989.1.21.1.1.1
		asIbFtCompliance MODULE-COMPLIANCE
			STATUS current
			DESCRIPTION 
				"Description."
			MODULE -- this module
				MANDATORY-GROUPS { asIbFtObjectGroup }
			::= { asIbFtConformance 1 }

		
		-- 1.3.6.1.4.1.989.1.21.1.1.2
		asIbFtObjectGroup OBJECT-GROUP
			OBJECTS { asIbFtIndex, asIbFtOperationalStatusChangedTrapEnabled, asIbFtStackStatusOperationalStatus, asIbFtStackCfgOperationalStatus, asIbFtChannelListRowStatus, 
				asIbFtChannelListCpSize, asIbFtChannelListFrameDuration, asIbFtChannelListPreamble, asIbFtChannelListCentreFrequency, asIbFtChannelListBandwidth, 
				asIbFtChannelListFftSize, asIbFtCardMinPower, asIbFtCardMaxPower, asIbFtCardTimerT7, asIbFtCardTimerT8, 
				asIbFtCardDsxAckMaxRetries, asIbFtCardDsxRspMaxRetries, asIbFtCardTimerT6, asIbFtCardTimerT18, asIbFtCardSbcRspMaxRetries, 
				asIbFtCardRegRspMaxRetries, asIbFtCardPagingCycleRequest, asIbFtCardMacHashSkipThreshold, asIbFtCardNbrAdvIntervalTimeout, asIbFtCardRhmRangingTimeout, 
				asIbFtCardPhyScanTimeout, asIbFtCardPhyStopTimeout, asIbFtCardScanInterleavingInterval, asIbFtCardT44Timer, asIbFtCardMobScnReqRetries, 
				asIbFtCardT1Timeout, asIbFtCardT2Timeout, asIbFtCardT3Timeout, asIbFtCardT12Timeout, asIbFtCardDlSyncTimeout, 
				asIbFtCardChannelTableTimeout, asIbFtCardMaxContentionRetries, asIbFtCardPhyResetTimeout, asIbFtCardBridgeRouteLife, asIbFtCardPhyRespTimeout, 
				asIbFtCardPhyDlSyncTimeout, asIbFtCardPhyActivityTimeout, asIbFtCardRfcKeepAliveTimeout, asIbFtCardRfcpStartingThreshold, asIbFtCardRfcpDiedThreshold, 
				asIbFtCardTimerT45, asIbFtCardDregCmdMaxRetries, asIbFtCardTimerDeregistration, asIbFtCardRfcpConfigTimeout, asIbFtCardPctlRfConfigTimeout, 
				asIbFtStackStatusOperationalStatusInfo, asIbFtStackCfgResetRequest }
			STATUS current
			DESCRIPTION 
				"Description."
			::= { asIbFtConformance 2 }

		
		-- 1.3.6.1.4.1.989.1.21.1.1.3
		asIbFtNotificationGroup NOTIFICATION-GROUP
			NOTIFICATIONS { asIbFtOperationalStatusChangedTrap }
			STATUS current
			DESCRIPTION 
				"Description."
			::= { asIbFtConformance 3 }

		
		-- 1.3.6.1.4.1.989.1.21.1.2
		asIbFtNotifications OBJECT IDENTIFIER ::= { asIbFt 2 }

		
		-- 1.3.6.1.4.1.989.1.21.1.2.0
		asIbFtTrapPrefix OBJECT IDENTIFIER ::= { asIbFtNotifications 0 }

		
		-- 1.3.6.1.4.1.989.1.21.1.2.0.1
		asIbFtOperationalStatusChangedTrap NOTIFICATION-TYPE
			OBJECTS { asIbFtStackStatusOperationalStatus, asIbFtStackStatusOperationalStatusInfo }
			STATUS current
			DESCRIPTION 
				"Signifies that iBridge stack operational status has changed."
			::= { asIbFtTrapPrefix 1 }

		
		-- 1.3.6.1.4.1.989.1.21.1.2.1
		asIbFtTrapControlTable OBJECT-TYPE
			SYNTAX SEQUENCE OF AsIbFtTrapControlEntry
			MAX-ACCESS not-accessible
			STATUS current
			DESCRIPTION
				"Defines enabled/disabled controls for each traps independently. 
				The traps are enabled/disabled simulanously across the all cells/sectors of the stack."
			::= { asIbFtNotifications 1 }

		
		-- 1.3.6.1.4.1.989.1.21.1.2.1.1
		asIbFtTrapControlEntry OBJECT-TYPE
			SYNTAX AsIbFtTrapControlEntry
			MAX-ACCESS not-accessible
			STATUS current
			DESCRIPTION
				"Single row."
			INDEX { asIbFtTrapControlIndex }
			::= { asIbFtTrapControlTable 1 }

		
		AsIbFtTrapControlEntry ::=
			SEQUENCE { 
				asIbFtTrapControlIndex
					INTEGER,
				asIbFtOperationalStatusChangedTrapEnabled
					AsCmnTcBooleanSwitch
			 }

		-- 1.3.6.1.4.1.989.1.21.1.2.1.1.1
		asIbFtTrapControlIndex OBJECT-TYPE
			SYNTAX INTEGER (1)
			MAX-ACCESS not-accessible
			STATUS current
			DESCRIPTION
				"Arbitrary index - one row only."
			::= { asIbFtTrapControlEntry 1 }

		
		-- 1.3.6.1.4.1.989.1.21.1.2.1.1.2
		asIbFtOperationalStatusChangedTrapEnabled OBJECT-TYPE
			SYNTAX AsCmnTcBooleanSwitch
			MAX-ACCESS read-write
			STATUS current
			DESCRIPTION
				"Enables/disables the iBridge Stack Operational Status change Trap"
			DEFVAL { booleanTrue }
			::= { asIbFtTrapControlEntry 2 }

		
		-- 1.3.6.1.4.1.989.1.21.1.3
		asIbFtDevice OBJECT IDENTIFIER ::= { asIbFt 3 }

		
		-- 1.3.6.1.4.1.989.1.21.1.3.1
		asIbFtStackCfgTable OBJECT-TYPE
			SYNTAX SEQUENCE OF AsIbFtStackCfgEntry
			MAX-ACCESS not-accessible
			STATUS current
			DESCRIPTION
				"Table grouping per iBridge stack configuration properties."
			::= { asIbFtDevice 1 }

		
		-- 1.3.6.1.4.1.989.1.21.1.3.1.1
		asIbFtStackCfgEntry OBJECT-TYPE
			SYNTAX AsIbFtStackCfgEntry
			MAX-ACCESS not-accessible
			STATUS current
			DESCRIPTION
				"Description."
			INDEX { asIbFtIndex }
			::= { asIbFtStackCfgTable 1 }

		
		AsIbFtStackCfgEntry ::=
			SEQUENCE { 
				asIbFtIndex
					Integer32,
				asIbFtStackCfgResetRequest
					AsCmnTcResetCmd,
				asIbFtStackCfgOperationalStatus
					AsCmnTcOperationalStatus
			 }

		-- 1.3.6.1.4.1.989.1.21.1.3.1.1.1
		asIbFtIndex OBJECT-TYPE
			SYNTAX Integer32 (1)
			MAX-ACCESS accessible-for-notify
			STATUS current
			DESCRIPTION
				"Arbitrary index - only one instance ever."
			::= { asIbFtStackCfgEntry 1 }

		
		-- 1.3.6.1.4.1.989.1.21.1.3.1.1.2
		asIbFtStackCfgResetRequest OBJECT-TYPE
			SYNTAX AsCmnTcResetCmd
			MAX-ACCESS read-write
			STATUS current
			DESCRIPTION
				"Request to reset the stack"
			DEFVAL { resetCmdIdle }
			::= { asIbFtStackCfgEntry 2 }

		
		-- 1.3.6.1.4.1.989.1.21.1.3.1.1.3
		asIbFtStackCfgOperationalStatus OBJECT-TYPE
			SYNTAX AsCmnTcOperationalStatus
			MAX-ACCESS read-write
			STATUS current
			DESCRIPTION
				"The requested operational status for the stack."
			DEFVAL { operationalStatusOutOfService }
			::= { asIbFtStackCfgEntry 3 }

		
		-- 1.3.6.1.4.1.989.1.21.1.3.2
		asIbFtStackStatusTable OBJECT-TYPE
			SYNTAX SEQUENCE OF AsIbFtStackStatusEntry
			MAX-ACCESS not-accessible
			STATUS current
			DESCRIPTION
				"Table grouping per iBridge stack status properties."
			::= { asIbFtDevice 2 }

		
		-- 1.3.6.1.4.1.989.1.21.1.3.2.1
		asIbFtStackStatusEntry OBJECT-TYPE
			SYNTAX AsIbFtStackStatusEntry
			MAX-ACCESS not-accessible
			STATUS current
			DESCRIPTION
				"Description."
			INDEX { asIbFtIndex }
			::= { asIbFtStackStatusTable 1 }

		
		AsIbFtStackStatusEntry ::=
			SEQUENCE { 
				asIbFtStackStatusOperationalStatus
					AsCmnTcOperationalStatus,
				asIbFtStackStatusOperationalStatusInfo
					DisplayString
			 }

		-- 1.3.6.1.4.1.989.1.21.1.3.2.1.1
		asIbFtStackStatusOperationalStatus OBJECT-TYPE
			SYNTAX AsCmnTcOperationalStatus
			MAX-ACCESS read-only
			STATUS current
			DESCRIPTION
				"The current operational status for the iBridge stack."
			::= { asIbFtStackStatusEntry 1 }

		
		-- 1.3.6.1.4.1.989.1.21.1.3.2.1.2
		asIbFtStackStatusOperationalStatusInfo OBJECT-TYPE
			SYNTAX DisplayString
			MAX-ACCESS read-only
			STATUS current
			DESCRIPTION
				"Provides further information on the iBridge Stack Operational Status"
			::= { asIbFtStackStatusEntry 2 }

		
		-- 1.3.6.1.4.1.989.1.21.1.3.3
		asIbFtChannelListTable OBJECT-TYPE
			SYNTAX SEQUENCE OF AsIbFtChannelListEntry
			MAX-ACCESS not-accessible
			STATUS current
			DESCRIPTION
				"Table defining the channel scan list"
			::= { asIbFtDevice 3 }

		
		-- 1.3.6.1.4.1.989.1.21.1.3.3.1
		asIbFtChannelListEntry OBJECT-TYPE
			SYNTAX AsIbFtChannelListEntry
			MAX-ACCESS not-accessible
			STATUS current
			DESCRIPTION
				"Description."
			INDEX { asIbFtChannelListIndex }
			::= { asIbFtChannelListTable 1 }

		
		AsIbFtChannelListEntry ::=
			SEQUENCE { 
				asIbFtChannelListIndex
					Integer32,
				asIbFtChannelListCentreFrequency
					Integer32,
				asIbFtChannelListBandwidth
					AsIbFtChannelListBandwidth,
				asIbFtChannelListFftSize
					AsIbFtChannelListFftSize,
				asIbFtChannelListCpSize
					AsIbFtChannelListCpSize,
				asIbFtChannelListFrameDuration
					AsIbFtChannelListFrameDuration,
				asIbFtChannelListPreamble
					Integer32,
				asIbFtChannelListRowStatus
					RowStatus
			 }

		-- 1.3.6.1.4.1.989.1.21.1.3.3.1.1
		asIbFtChannelListIndex OBJECT-TYPE
			SYNTAX Integer32 (1..2147483647)
			MAX-ACCESS not-accessible
			STATUS current
			DESCRIPTION
				"Arbitrary index for entry in the channel scan list table. "
			::= { asIbFtChannelListEntry 1 }

		
		-- 1.3.6.1.4.1.989.1.21.1.3.3.1.2
		asIbFtChannelListCentreFrequency OBJECT-TYPE
			SYNTAX Integer32 (1..2147483647)
			UNITS "kHz"
			MAX-ACCESS read-create
			STATUS current
			DESCRIPTION
				"Channel Centre Frequency"
			::= { asIbFtChannelListEntry 2 }

		
		-- 1.3.6.1.4.1.989.1.21.1.3.3.1.3
		asIbFtChannelListBandwidth OBJECT-TYPE
			SYNTAX AsIbFtChannelListBandwidth
			MAX-ACCESS read-create
			STATUS current
			DESCRIPTION
				"Channel Bandwidth"
			::= { asIbFtChannelListEntry 3 }

		
		-- 1.3.6.1.4.1.989.1.21.1.3.3.1.4
		asIbFtChannelListFftSize OBJECT-TYPE
			SYNTAX AsIbFtChannelListFftSize
			MAX-ACCESS read-create
			STATUS current
			DESCRIPTION
				"Channel FFT Size"
			::= { asIbFtChannelListEntry 4 }

		
		-- 1.3.6.1.4.1.989.1.21.1.3.3.1.5
		asIbFtChannelListCpSize OBJECT-TYPE
			SYNTAX AsIbFtChannelListCpSize
			MAX-ACCESS read-create
			STATUS current
			DESCRIPTION
				"Channel cyclic prefix length"
			::= { asIbFtChannelListEntry 5 }

		
		-- 1.3.6.1.4.1.989.1.21.1.3.3.1.6
		asIbFtChannelListFrameDuration OBJECT-TYPE
			SYNTAX AsIbFtChannelListFrameDuration
			MAX-ACCESS read-create
			STATUS current
			DESCRIPTION
				"Channel Frame Duration"
			::= { asIbFtChannelListEntry 6 }

		
		-- 1.3.6.1.4.1.989.1.21.1.3.3.1.7
		asIbFtChannelListPreamble OBJECT-TYPE
			SYNTAX Integer32 (1..2147483647)
			MAX-ACCESS read-create
			STATUS current
			DESCRIPTION
				"Channel Preamble"
			::= { asIbFtChannelListEntry 7 }

		
		-- 1.3.6.1.4.1.989.1.21.1.3.3.1.8
		asIbFtChannelListRowStatus OBJECT-TYPE
			SYNTAX RowStatus
			MAX-ACCESS read-create
			STATUS current
			DESCRIPTION
				"Handles Row Creation/ Deletion in the table."
			::= { asIbFtChannelListEntry 8 }

		
		-- 1.3.6.1.4.1.989.1.21.1.3.4
		asIbFtCardTable OBJECT-TYPE
			SYNTAX SEQUENCE OF AsIbFtCardEntry
			MAX-ACCESS not-accessible
			STATUS current
			DESCRIPTION
				"Description."
			::= { asIbFtDevice 4 }

		
		-- 1.3.6.1.4.1.989.1.21.1.3.4.1
		asIbFtCardEntry OBJECT-TYPE
			SYNTAX AsIbFtCardEntry
			MAX-ACCESS not-accessible
			STATUS current
			DESCRIPTION
				"Description."
			INDEX { asIbFtCardId }
			::= { asIbFtCardTable 1 }

		
		AsIbFtCardEntry ::=
			SEQUENCE { 
				asIbFtCardId
					Integer32,
				asIbFtCardMinPower
					Integer32,
				asIbFtCardMaxPower
					Integer32,
				asIbFtCardTimerT7
					Unsigned32,
				asIbFtCardTimerT8
					Unsigned32,
				asIbFtCardDsxAckMaxRetries
					Unsigned32,
				asIbFtCardDsxRspMaxRetries
					Unsigned32,
				asIbFtCardTimerT6
					Unsigned32,
				asIbFtCardTimerT18
					Unsigned32,
				asIbFtCardSbcRspMaxRetries
					Unsigned32,
				asIbFtCardRegRspMaxRetries
					Unsigned32,
				asIbFtCardPagingCycleRequest
					Unsigned32,
				asIbFtCardMacHashSkipThreshold
					Unsigned32,
				asIbFtCardNbrAdvIntervalTimeout
					Unsigned32,
				asIbFtCardRhmRangingTimeout
					Unsigned32,
				asIbFtCardPhyScanTimeout
					Unsigned32,
				asIbFtCardPhyStopTimeout
					Unsigned32,
				asIbFtCardScanInterleavingInterval
					Unsigned32,
				asIbFtCardT44Timer
					Unsigned32,
				asIbFtCardMobScnReqRetries
					Unsigned32,
				asIbFtCardT1Timeout
					Unsigned32,
				asIbFtCardT2Timeout
					Unsigned32,
				asIbFtCardT3Timeout
					Integer32,
				asIbFtCardT12Timeout
					Integer32,
				asIbFtCardDlSyncTimeout
					Unsigned32,
				asIbFtCardChannelTableTimeout
					Unsigned32,
				asIbFtCardMaxContentionRetries
					Unsigned32,
				asIbFtCardPhyResetTimeout
					Unsigned32,
				asIbFtCardBridgeRouteLife
					Unsigned32,
				asIbFtCardPhyRespTimeout
					Unsigned32,
				asIbFtCardPhyDlSyncTimeout
					Unsigned32,
				asIbFtCardPhyActivityTimeout
					Unsigned32,
				asIbFtCardRfcKeepAliveTimeout
					Unsigned32,
				asIbFtCardRfcpStartingThreshold
					Unsigned32,
				asIbFtCardRfcpDiedThreshold
					Unsigned32,
				asIbFtCardTimerT45
					Unsigned32,
				asIbFtCardDregCmdMaxRetries
					Unsigned32,
				asIbFtCardTimerDeregistration
					Unsigned32,
				asIbFtCardRfcpConfigTimeout
					Unsigned32,
				asIbFtCardPctlRfConfigTimeout
					Unsigned32
			 }

		-- 1.3.6.1.4.1.989.1.21.1.3.4.1.1
		asIbFtCardId OBJECT-TYPE
			SYNTAX Integer32 (1..65535)
			MAX-ACCESS not-accessible
			STATUS current
			DESCRIPTION
				"Description."
			::= { asIbFtCardEntry 1 }

		
		-- 1.3.6.1.4.1.989.1.21.1.3.4.1.3
		asIbFtCardMinPower OBJECT-TYPE
			SYNTAX Integer32
			MAX-ACCESS read-write
			STATUS current
			DESCRIPTION
				"Description."
			::= { asIbFtCardEntry 3 }

		
		-- 1.3.6.1.4.1.989.1.21.1.3.4.1.4
		asIbFtCardMaxPower OBJECT-TYPE
			SYNTAX Integer32
			MAX-ACCESS read-write
			STATUS current
			DESCRIPTION
				"Description."
			::= { asIbFtCardEntry 4 }

		
		-- 1.3.6.1.4.1.989.1.21.1.3.4.1.5
		asIbFtCardTimerT7 OBJECT-TYPE
			SYNTAX Unsigned32 (0..65535)
			MAX-ACCESS read-write
			STATUS current
			DESCRIPTION
				"The DSX-RSP timeout, in milliseconds."
			DEFVAL { 1000 }
			::= { asIbFtCardEntry 5 }

		
		-- 1.3.6.1.4.1.989.1.21.1.3.4.1.6
		asIbFtCardTimerT8 OBJECT-TYPE
			SYNTAX Unsigned32 (0..65535)
			MAX-ACCESS read-write
			STATUS current
			DESCRIPTION
				"The DSX-ACK timeout, in milliseconds."
			DEFVAL { 300 }
			::= { asIbFtCardEntry 6 }

		
		-- 1.3.6.1.4.1.989.1.21.1.3.4.1.7
		asIbFtCardDsxAckMaxRetries OBJECT-TYPE
			SYNTAX Unsigned32 (0..65535)
			MAX-ACCESS read-write
			STATUS current
			DESCRIPTION
				"The maximum number of DSX-ACK retries"
			DEFVAL { 16 }
			::= { asIbFtCardEntry 7 }

		
		-- 1.3.6.1.4.1.989.1.21.1.3.4.1.8
		asIbFtCardDsxRspMaxRetries OBJECT-TYPE
			SYNTAX Unsigned32 (0..65535)
			MAX-ACCESS read-write
			STATUS current
			DESCRIPTION
				"The maximum number of DSX-RSP retries"
			DEFVAL { 16 }
			::= { asIbFtCardEntry 8 }

		
		-- 1.3.6.1.4.1.989.1.21.1.3.4.1.9
		asIbFtCardTimerT6 OBJECT-TYPE
			SYNTAX Unsigned32 (0..65535)
			MAX-ACCESS read-write
			STATUS current
			DESCRIPTION
				"The REG-RSP timeout, in milliseconds."
			DEFVAL { 3000 }
			::= { asIbFtCardEntry 9 }

		
		-- 1.3.6.1.4.1.989.1.21.1.3.4.1.10
		asIbFtCardTimerT18 OBJECT-TYPE
			SYNTAX Unsigned32 (0..65535)
			MAX-ACCESS read-write
			STATUS current
			DESCRIPTION
				"The SBC-RSP timeout, in milliseconds."
			DEFVAL { 50 }
			::= { asIbFtCardEntry 10 }

		
		-- 1.3.6.1.4.1.989.1.21.1.3.4.1.11
		asIbFtCardSbcRspMaxRetries OBJECT-TYPE
			SYNTAX Unsigned32 (0..65535)
			MAX-ACCESS read-write
			STATUS current
			DESCRIPTION
				"The maximum number of SBC-RSP retries"
			DEFVAL { 3 }
			::= { asIbFtCardEntry 11 }

		
		-- 1.3.6.1.4.1.989.1.21.1.3.4.1.12
		asIbFtCardRegRspMaxRetries OBJECT-TYPE
			SYNTAX Unsigned32 (0..65535)
			MAX-ACCESS read-write
			STATUS current
			DESCRIPTION
				"The maximum number of REG-RSP retries"
			DEFVAL { 3 }
			::= { asIbFtCardEntry 12 }

		
		-- 1.3.6.1.4.1.989.1.21.1.3.4.1.13
		asIbFtCardPagingCycleRequest OBJECT-TYPE
			SYNTAX Unsigned32 (0..128)
			MAX-ACCESS read-write
			STATUS current
			DESCRIPTION
				"Requested cycle in which the paging message is transmitted within the paging group."
			::= { asIbFtCardEntry 13 }

		
		-- 1.3.6.1.4.1.989.1.21.1.3.4.1.14
		asIbFtCardMacHashSkipThreshold OBJECT-TYPE
			SYNTAX Unsigned32 (0..128)
			MAX-ACCESS read-write
			STATUS current
			DESCRIPTION
				"Maximum number of successive MOB_PAG-ADV messages that may be sent from a BS without
 individual notification for an MS, including MAC address hash of an MS for which the action code for the MS is 00 (No Action Required)."
			::= { asIbFtCardEntry 14 }

		
		-- 1.3.6.1.4.1.989.1.21.1.3.4.1.15
		asIbFtCardNbrAdvIntervalTimeout OBJECT-TYPE
			SYNTAX Unsigned32 (0..65535)
			MAX-ACCESS read-write
			STATUS current
			DESCRIPTION
				"The MOB_NBR-ADV interval timeout, in milliseconds(30 sec)."
			DEFVAL { 30000 }
			::= { asIbFtCardEntry 15 }

		
		-- 1.3.6.1.4.1.989.1.21.1.3.4.1.16
		asIbFtCardRhmRangingTimeout OBJECT-TYPE
			SYNTAX Unsigned32 (0..65535)
			MAX-ACCESS read-write
			STATUS current
			DESCRIPTION
				"The Rehoming ranging timeout, in milliseconds."
			::= { asIbFtCardEntry 16 }

		
		-- 1.3.6.1.4.1.989.1.21.1.3.4.1.17
		asIbFtCardPhyScanTimeout OBJECT-TYPE
			SYNTAX Unsigned32 (0..65535)
			MAX-ACCESS read-write
			STATUS current
			DESCRIPTION
				"The PHY Scan timeout, in milliseconds."
			DEFVAL { 7000 }
			::= { asIbFtCardEntry 17 }

		
		-- 1.3.6.1.4.1.989.1.21.1.3.4.1.18
		asIbFtCardPhyStopTimeout OBJECT-TYPE
			SYNTAX Unsigned32 (0..65535)
			MAX-ACCESS read-write
			STATUS current
			DESCRIPTION
				"The PHY Stop timeout, in milliseconds."
			DEFVAL { 1000 }
			::= { asIbFtCardEntry 18 }

		
		-- 1.3.6.1.4.1.989.1.21.1.3.4.1.19
		asIbFtCardScanInterleavingInterval OBJECT-TYPE
			SYNTAX Unsigned32 (0..65535)
			MAX-ACCESS read-write
			STATUS current
			DESCRIPTION
				"The PHY Stop timeout, in frames."
			DEFVAL { 1000 }
			::= { asIbFtCardEntry 19 }

		
		-- 1.3.6.1.4.1.989.1.21.1.3.4.1.20
		asIbFtCardT44Timer OBJECT-TYPE
			SYNTAX Unsigned32 (0..65535)
			MAX-ACCESS read-write
			STATUS current
			DESCRIPTION
				"Time the FT waits for MOB_SCN-RSP."
			DEFVAL { 200 }
			::= { asIbFtCardEntry 20 }

		
		-- 1.3.6.1.4.1.989.1.21.1.3.4.1.21
		asIbFtCardMobScnReqRetries OBJECT-TYPE
			SYNTAX Unsigned32 (0..16)
			MAX-ACCESS read-write
			STATUS current
			DESCRIPTION
				"No of times FT should send MOB_SCN-REQ beforing giving up."
			::= { asIbFtCardEntry 21 }

		
		-- 1.3.6.1.4.1.989.1.21.1.3.4.1.22
		asIbFtCardT1Timeout OBJECT-TYPE
			SYNTAX Unsigned32 (0..65535)
			MAX-ACCESS read-write
			STATUS current
			DESCRIPTION
				"DCD Timeout."
			DEFVAL { 50000 }
			::= { asIbFtCardEntry 22 }

		
		-- 1.3.6.1.4.1.989.1.21.1.3.4.1.23
		asIbFtCardT2Timeout OBJECT-TYPE
			SYNTAX Unsigned32 (0..65535)
			MAX-ACCESS read-write
			STATUS current
			DESCRIPTION
				"T2 Timeout."
			DEFVAL { 25 }
			::= { asIbFtCardEntry 23 }

		
		-- 1.3.6.1.4.1.989.1.21.1.3.4.1.24
		asIbFtCardT3Timeout OBJECT-TYPE
			SYNTAX Integer32 (0..65535)
			MAX-ACCESS read-write
			STATUS current
			DESCRIPTION
				"T3 Timeout."
			DEFVAL { 60 }
			::= { asIbFtCardEntry 24 }

		
		-- 1.3.6.1.4.1.989.1.21.1.3.4.1.26
		asIbFtCardT12Timeout OBJECT-TYPE
			SYNTAX Integer32 (0..65535)
			MAX-ACCESS read-write
			STATUS current
			DESCRIPTION
				"Description."
			DEFVAL { 50000 }
			::= { asIbFtCardEntry 26 }

		
		-- 1.3.6.1.4.1.989.1.21.1.3.4.1.27
		asIbFtCardDlSyncTimeout OBJECT-TYPE
			SYNTAX Unsigned32 (0..65535)
			MAX-ACCESS read-write
			STATUS current
			DESCRIPTION
				"Description."
			DEFVAL { 2000 }
			::= { asIbFtCardEntry 27 }

		
		-- 1.3.6.1.4.1.989.1.21.1.3.4.1.28
		asIbFtCardChannelTableTimeout OBJECT-TYPE
			SYNTAX Unsigned32 (0..65535)
			MAX-ACCESS read-write
			STATUS current
			DESCRIPTION
				"Channel Table Timeout."
			DEFVAL { 1000 }
			::= { asIbFtCardEntry 28 }

		
		-- 1.3.6.1.4.1.989.1.21.1.3.4.1.29
		asIbFtCardMaxContentionRetries OBJECT-TYPE
			SYNTAX Unsigned32 (0..16)
			MAX-ACCESS read-write
			STATUS current
			DESCRIPTION
				"Maxium Contention Retries."
			DEFVAL { 16 }
			::= { asIbFtCardEntry 29 }

		
		-- 1.3.6.1.4.1.989.1.21.1.3.4.1.30
		asIbFtCardPhyResetTimeout OBJECT-TYPE
			SYNTAX Unsigned32 (0..65535)
			MAX-ACCESS read-write
			STATUS current
			DESCRIPTION
				"Phy Reset timeout."
			DEFVAL { 1250 }
			::= { asIbFtCardEntry 30 }

		
		-- 1.3.6.1.4.1.989.1.21.1.3.4.1.31
		asIbFtCardBridgeRouteLife OBJECT-TYPE
			SYNTAX Unsigned32 (0..65535)
			MAX-ACCESS read-write
			STATUS current
			DESCRIPTION
				"Description."
			DEFVAL { 20000 }
			::= { asIbFtCardEntry 31 }

		
		-- 1.3.6.1.4.1.989.1.21.1.3.4.1.32
		asIbFtCardPhyRespTimeout OBJECT-TYPE
			SYNTAX Unsigned32 (0..65535)
			MAX-ACCESS read-write
			STATUS current
			DESCRIPTION
				"Phy Resp timer timeout."
			DEFVAL { 70 }
			::= { asIbFtCardEntry 32 }

		
		-- 1.3.6.1.4.1.989.1.21.1.3.4.1.33
		asIbFtCardPhyDlSyncTimeout OBJECT-TYPE
			SYNTAX Unsigned32 (0..65535)
			MAX-ACCESS read-write
			STATUS current
			DESCRIPTION
				"Phy DL Sync timeout."
			DEFVAL { 2000 }
			::= { asIbFtCardEntry 33 }

		
		-- 1.3.6.1.4.1.989.1.21.1.3.4.1.34
		asIbFtCardPhyActivityTimeout OBJECT-TYPE
			SYNTAX Unsigned32 (0..65535)
			MAX-ACCESS read-write
			STATUS current
			DESCRIPTION
				"Phy Activity timeout."
			DEFVAL { 5000 }
			::= { asIbFtCardEntry 34 }

		
		-- 1.3.6.1.4.1.989.1.21.1.3.4.1.35
		asIbFtCardRfcKeepAliveTimeout OBJECT-TYPE
			SYNTAX Unsigned32 (0..65535)
			MAX-ACCESS read-write
			STATUS current
			DESCRIPTION
				"RFC-RFCP Keep Alive timeout."
			DEFVAL { 1000 }
			::= { asIbFtCardEntry 35 }

		
		-- 1.3.6.1.4.1.989.1.21.1.3.4.1.36
		asIbFtCardRfcpStartingThreshold OBJECT-TYPE
			SYNTAX Unsigned32 (0..65535)
			MAX-ACCESS read-write
			STATUS current
			DESCRIPTION
				"RFCP Starting Threshold"
			DEFVAL { 60 }
			::= { asIbFtCardEntry 36 }

		
		-- 1.3.6.1.4.1.989.1.21.1.3.4.1.37
		asIbFtCardRfcpDiedThreshold OBJECT-TYPE
			SYNTAX Unsigned32 (0..65535)
			MAX-ACCESS read-write
			STATUS current
			DESCRIPTION
				"Rfcp Died Threshold"
			DEFVAL { 29 }
			::= { asIbFtCardEntry 37 }

		
		-- 1.3.6.1.4.1.989.1.21.1.3.4.1.38
		asIbFtCardTimerT45 OBJECT-TYPE
			SYNTAX Unsigned32 (0..65535)
			MAX-ACCESS read-write
			STATUS current
			DESCRIPTION
				"The DREG-CMD timeout, in milliseconds."
			DEFVAL { 250 }
			::= { asIbFtCardEntry 38 }

		
		-- 1.3.6.1.4.1.989.1.21.1.3.4.1.39
		asIbFtCardDregCmdMaxRetries OBJECT-TYPE
			SYNTAX Unsigned32 (0..65535)
			MAX-ACCESS read-write
			STATUS current
			DESCRIPTION
				"Description."
			DEFVAL { 3 }
			::= { asIbFtCardEntry 39 }

		
		-- 1.3.6.1.4.1.989.1.21.1.3.4.1.40
		asIbFtCardTimerDeregistration OBJECT-TYPE
			SYNTAX Unsigned32 (0..65535)
			MAX-ACCESS read-write
			STATUS current
			DESCRIPTION
				"The deregistation timeout (following receipt of unsolicited DREG-CMD), in milliseconds."
			DEFVAL { 50 }
			::= { asIbFtCardEntry 40 }

		
		-- 1.3.6.1.4.1.989.1.21.1.3.4.1.41
		asIbFtCardRfcpConfigTimeout OBJECT-TYPE
			SYNTAX Unsigned32 (0..65535)
			MAX-ACCESS read-write
			STATUS current
			DESCRIPTION
				"RFCP SendConfig Timeout"
			DEFVAL { 100 }
			::= { asIbFtCardEntry 41 }

		
		-- 1.3.6.1.4.1.989.1.21.1.3.4.1.42
		asIbFtCardPctlRfConfigTimeout OBJECT-TYPE
			SYNTAX Unsigned32 (0..65535)
			MAX-ACCESS read-write
			STATUS current
			DESCRIPTION
				"RF Configure Timeout"
			DEFVAL { 200 }
			::= { asIbFtCardEntry 42 }

		
	
	END

--
-- ASIB-FT-MIB.mib
--
