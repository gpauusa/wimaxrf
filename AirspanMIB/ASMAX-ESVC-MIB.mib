--
-- ASMAX-ESVC-MIB.mib
-- MIB generated by MG-SOFT Visual MIB Builder Version 7.0  Build 240
-- Thursday, February 18, 2010 at 18:39:18
--

	ASMAX-ESVC-MIB DEFINITIONS ::= BEGIN
 
		IMPORTS
			AsmaxBooleanSwitch			
				FROM AIRSPAN-ASMAX-COMMON-MIB			
			asMaxBS, asMaxBSCommon, asMaxBSHiperMax, asMaxBSPicoMax, asMaxBSDemoMax, 
			asMaxBSSoc, asMaxBsStats, asMaxEbs			
				FROM AIRSPAN-PRODUCTS-MIB			
			ifIndex			
				FROM IF-MIB			
			InetAddressType, InetAddress			
				FROM INET-ADDRESS-MIB			
			OBJECT-GROUP, MODULE-COMPLIANCE			
				FROM SNMPv2-CONF			
			Integer32, OBJECT-TYPE, MODULE-IDENTITY			
				FROM SNMPv2-SMI			
			MacAddress, RowStatus			
				FROM SNMPv2-TC			
			wmanIf2fBsSsProvMacAddress, wmanIf2fBsSfId, wmanIf2fBsQoSProfileIndex, wmanIf2fBsSfMacAddress, wmanIf2fBsProvClsfRuleIndex, 
			WmanIf2fSfState, WmanIf2fIpv6FlowLabel, WmanIf2fActionRule, WmanIf2fClassifierMap			
				FROM WMAN-IF2F-BS-MIB;
	
	
		-- 1.3.6.1.4.1.989.1.16.2.8
		asMaxEsvc MODULE-IDENTITY 
			LAST-UPDATED "201002181837Z"		-- February 18, 2010 at 18:37 GMT
			ORGANIZATION 
				"Airspan Communication Ltd"
			CONTACT-INFO 
				"kdudzins@airspan.com"
			DESCRIPTION 
				"Defines propriatory classes for MS provisioning
				in mobile systems. Some classes defined are used 
				as default for BSs working in WiMAX network."
			REVISION "200710181415Z"		-- October 18, 2007 at 14:15 GMT
			DESCRIPTION 
				"Draft 1:
				- initial template"
			REVISION "200711210828Z"		-- November 21, 2007 at 08:28 GMT
			DESCRIPTION 
				"Draft 2:
				- added service class extension table and properties"
			REVISION "200712131400Z"		-- December 13, 2007 at 14:00 GMT
			DESCRIPTION 
				"Draft 3:
				- changed to use imported symbol from new MIB module WMAN-IF2F-BS-MIB"
			REVISION "200801290956Z"		-- January 29, 2008 at 09:56 GMT
			DESCRIPTION 
				"Draft 4:
				- added asxEsvcServiceProductTable, asxEsvcSfClassTable and asxEsvcRuleClassTable"
			REVISION "200801291042Z"		-- January 29, 2008 at 10:42 GMT
			DESCRIPTION 
				"Draft 5:
				- added descriptions to leaves of asxEsvcServiceProductTable and asxEsvcSfClassTable"
			REVISION "200801291450Z"		-- January 29, 2008 at 14:50 GMT
			DESCRIPTION 
				"Draft 6:
				- reomoved unused tables asxEsvcMsConfigClassTable and asxEsvcMsVlanPortClassTable and moved service product and SfClass tables to their position
				- rectified indexes of asxEsvcServiceProductTable, asxEsvcSfClassTable and asxEsvcRuleClassTable.
				- Octet string length specified for service product name "
			REVISION "200802061418Z"		-- February 06, 2008 at 14:18 GMT
			DESCRIPTION 
				"Draft 7:
				- asxEsvcSfClassDownlink changed to asxEsvcSfClassDirection,
				- having an enumerated list of downstream(1) and upstream(2)"
			REVISION "200803121733Z"		-- March 12, 2008 at 17:33 GMT
			DESCRIPTION 
				"Draft 8:
				access for asxEsvcSfClassServiceClassId changed to read-create."
			REVISION "200803281542Z"		-- March 28, 2008 at 15:42 GMT
			DESCRIPTION 
				"Draft 9:
				asxEsvcServiceCfgTable added."
			REVISION "200805081732Z"		-- May 08, 2008 at 17:32 GMT
			DESCRIPTION 
				"Draft 10:
				- Added HARQ objects to asxEsvcServiceClassExtTable"
			REVISION "200805161434Z"		-- May 16, 2008 at 14:34 GMT
			DESCRIPTION 
				"Draft 11:
				- added objects asxEsvcServiceClassExtArqEnabled, asxEsvcServiceClassExtArqDeliverInOrder
				- added tabled asxEsvcSfExtTable"
			REVISION "200907171600Z"		-- July 17, 2009 at 16:00 GMT
			DESCRIPTION 
				"Draft 12:
				- added to asxEsvcRuleClassTable:
				  phs provisioning objects and asxEsvcRuleClassDiscardRule, asxEsvcRuleClassIpv6FlowLabel
				- created new table asxEsvcProvRuleExtTable with
				  phs provisioning objects and asxEsvcProvRuleExtDiscardRule, asxEsvcProvRuleExtIpv6FlowLabel"
			REVISION "200907201610Z"		-- July 20, 2009 at 16:10 GMT
			DESCRIPTION 
				"Draft 13:
				- Change imported MacAddress index to wmanIf2fBsSsProvMacAddress
				- Renamed object asxEsvcProvRuleExtIpv6FlowLabel2"
			REVISION "200907211218Z"		-- July 21, 2009 at 12:18 GMT
			DESCRIPTION 
				"Draft 14:
				- added row status for asxEsvcProvRuleExtTable"
			REVISION "200909031225Z"		-- September 03, 2009 at 12:25 GMT
			DESCRIPTION 
				"Draft 15:
				- Added objects to Service Class Extention table:
				asxEsvcServiceClassExtHarqMaxMatrixBRetransmission (iib 29:34)"
			REVISION "200912231014Z"		-- December 23, 2009 at 10:14 GMT
			DESCRIPTION 
				"Draft 16:
				- Added asxEsvcServiceClassExtSetUlDiffServe
				- Added asxEsvcServiceClassExtUlDiffServeField"
			REVISION "201002181837Z"		-- February 18, 2010 at 18:37 GMT
			DESCRIPTION 
				"Draft 17:
				- Added object asxEsvcServiceClassExtSetUlDiffServeMode
				- Deprecated object asxEsvcServiceClassExtSetUlDiffServe"
			::= { asMaxBS 8 }

		
	
	
--
-- Node definitions
--
	
		-- 1.3.6.1.4.1.989.1.16.2.8.1
		asxEsvcConformance OBJECT IDENTIFIER ::= { asMaxEsvc 1 }

		
		-- 1.3.6.1.4.1.989.1.16.2.8.1.1
		asxEsvcCompliance MODULE-COMPLIANCE
			STATUS current
			DESCRIPTION 
				"Description."
			MODULE -- this module
				MANDATORY-GROUPS { asxEsvcObjectGroup }
			::= { asxEsvcConformance 1 }

		
		-- 1.3.6.1.4.1.989.1.16.2.8.1.2
		asxEsvcObjectGroup OBJECT-GROUP
			OBJECTS { asxEsvcServiceClassExtPollPeriod, asxEsvcServiceClassExtRowStatus, asxEsvcRuleClassPriority, asxEsvcRuleClassIpTosLow, asxEsvcRuleClassIpTosHigh, 
				asxEsvcRuleClassIpTosMask, asxEsvcRuleClassIpProtocol, asxEsvcRuleClassIpSrcAddr, asxEsvcRuleClassIpSrcMask, asxEsvcRuleClassIpDestAddr, 
				asxEsvcRuleClassIpDestMask, asxEsvcRuleClassSrcPortStart, asxEsvcRuleClassSrcPortEnd, asxEsvcRuleClassDestPortStart, asxEsvcRuleClassDestPortEnd, 
				asxEsvcRuleClassDestMacAddr, asxEsvcRuleClassDestMacMask, asxEsvcRuleClassSrcMacAddr, asxEsvcRuleClassSrcMacMask, asxEsvcRuleClassEnetProtType, 
				asxEsvcRuleClassEnetProtocol, asxEsvcRuleClassUserPriLow, asxEsvcRuleClassUserPriHigh, asxEsvcRuleClassVlanId, asxEsvcRuleClassBitMap, 
				asxEsvcRuleClassRowStatus, asxEsvcSfClassAdmissionState, asxEsvcSfClassSaid, asxEsvcSfClassRowStatus, asxEsvcSfClassServiceClassId, 
				asxEsvcServiceCfgUlBasicMgmtQosProfIndex, asxEsvcServiceCfgDlBasicMgmtQosProfIndex, asxEsvcServiceCfgUlPrimaryMgmtQosProfIndex, asxEsvcServiceCfgDlPrimaryMgmtQosProfIndex, asxEsvcServiceCfgUlSecondaryMgmtQosProfIndex, 
				asxEsvcServiceCfgDlSecondaryMgmtQosProfIndex, asxEsvcServiceCfgUlMinTolOverBookingRatio, asxEsvcServiceCfgDlMinTolOverBookingRatio, asxEsvcServiceCfgUlCirOverBookingRatio, asxEsvcServiceCfgDlCirOverBookingRatio, 
				asxEsvcServiceClassExtHarqEnabled, asxEsvcServiceClassExtHarqAcidMask, asxEsvcServiceClassExtHarqMaxTransmission, asxEsvcServiceClassExtHarqReorderSnSubheader, asxEsvcServiceClassExtArqEnabled, 
				asxEsvcServiceClassExtArqDeliverInOrder, asxEsvcSfExtProvSource, asxEsvcSfExtAsnDataPathEncap, asxEsvcSfExtAsnDataPathId, asxEsvcSfExtTunnelPresent, 
				asxEsvcSfExtInternalState, asxEsvcProvRuleExtDiscardRule, asxEsvcProvRuleExtPhsValidate, asxEsvcProvRuleExtPhsMask, asxEsvcProvRuleExtPhsSize, 
				asxEsvcProvRuleExtPhsField, asxEsvcRuleClassIpAddrType, asxEsvcServiceProductRowStatus, asxEsvcRuleClassDiscardRule, asxEsvcRuleClassPhsValidate, 
				asxEsvcRuleClassPhsMask, asxEsvcRuleClassPhsSize, asxEsvcRuleClassIpv6FlowLabel2, asxEsvcProvRuleExtRowStatus, asxEsvcServiceClassExtHarqMaxMatrixBRetransmission, 
				asxEsvcServiceClassExtUlDiffServeField, asxEsvcServiceClassExtSetUlDiffServeMode, asxEsvcRuleClassPhsField, asxEsvcSfClassDirection, asxEsvcProvRuleExtIpv6FlowLabel2
				 }
			STATUS current
			DESCRIPTION 
				"Description."
			::= { asxEsvcConformance 2 }

		
		-- 1.3.6.1.4.1.989.1.16.2.8.1.3
		asxEsvcObsoleteGroup OBJECT-GROUP
			OBJECTS { asxEsvcRuleClassIpv6FlowLabel, asxEsvcRuleClassActionRule }
			STATUS obsolete
			DESCRIPTION 
				"Description."
			::= { asxEsvcConformance 3 }

		
		-- 1.3.6.1.4.1.989.1.16.2.8.1.4
		asxEsvcDeprecatedGroup OBJECT-GROUP
			OBJECTS { asxEsvcServiceClassExtSetUlDiffServe }
			STATUS deprecated
			DESCRIPTION 
				"Description."
			::= { asxEsvcConformance 4 }

		
		-- 1.3.6.1.4.1.989.1.16.2.8.2
		asxEsvcNotifications OBJECT IDENTIFIER ::= { asMaxEsvc 2 }

		
		-- 1.3.6.1.4.1.989.1.16.2.8.2.1
		asxEsvcTrapPrefix OBJECT IDENTIFIER ::= { asxEsvcNotifications 1 }

		
		-- 1.3.6.1.4.1.989.1.16.2.8.3
		asxEsvcObjects OBJECT IDENTIFIER ::= { asMaxEsvc 3 }

		
		-- 1.3.6.1.4.1.989.1.16.2.8.3.1
		asxEsvcServiceProductTable OBJECT-TYPE
			SYNTAX SEQUENCE OF AsxEsvcServiceProductEntry
			MAX-ACCESS not-accessible
			STATUS current
			DESCRIPTION
				"This table contains service product information"
			::= { asxEsvcObjects 1 }

		
		-- 1.3.6.1.4.1.989.1.16.2.8.3.1.1
		asxEsvcServiceProductEntry OBJECT-TYPE
			SYNTAX AsxEsvcServiceProductEntry
			MAX-ACCESS not-accessible
			STATUS current
			DESCRIPTION
				"Service Product Entry, one entry per service product"
			INDEX { ifIndex, asxEsvcServiceProductName }
			::= { asxEsvcServiceProductTable 1 }

		
		AsxEsvcServiceProductEntry ::=
			SEQUENCE { 
				asxEsvcServiceProductName
					OCTET STRING,
				asxEsvcServiceProductRowStatus
					RowStatus
			 }

		-- 1.3.6.1.4.1.989.1.16.2.8.3.1.1.1
		asxEsvcServiceProductName OBJECT-TYPE
			SYNTAX OCTET STRING (SIZE (1..64))
			MAX-ACCESS not-accessible
			STATUS current
			DESCRIPTION
				"The unique name of the service product."
			::= { asxEsvcServiceProductEntry 1 }

		
		-- 1.3.6.1.4.1.989.1.16.2.8.3.1.1.2
		asxEsvcServiceProductRowStatus OBJECT-TYPE
			SYNTAX RowStatus
			MAX-ACCESS read-create
			STATUS current
			DESCRIPTION
				"Tracks the state of the row."
			::= { asxEsvcServiceProductEntry 2 }

		
		-- 1.3.6.1.4.1.989.1.16.2.8.3.2
		asxEsvcSfClassTable OBJECT-TYPE
			SYNTAX SEQUENCE OF AsxEsvcSfClassEntry
			MAX-ACCESS not-accessible
			STATUS current
			DESCRIPTION
				"This table contains service flow rules associated
				with service products"
			::= { asxEsvcObjects 2 }

		
		-- 1.3.6.1.4.1.989.1.16.2.8.3.2.1
		asxEsvcSfClassEntry OBJECT-TYPE
			SYNTAX AsxEsvcSfClassEntry
			MAX-ACCESS not-accessible
			STATUS current
			DESCRIPTION
				"Service Flow class entry, one entry per service flow definition"
			INDEX { ifIndex, asxEsvcServiceProductName, asxEsvcSfClassId }
			::= { asxEsvcSfClassTable 1 }

		
		AsxEsvcSfClassEntry ::=
			SEQUENCE { 
				asxEsvcSfClassId
					Integer32,
				asxEsvcSfClassServiceClassId
					Integer32,
				asxEsvcSfClassDirection
					INTEGER,
				asxEsvcSfClassAdmissionState
					WmanIf2fSfState,
				asxEsvcSfClassSaid
					Integer32,
				asxEsvcSfClassRowStatus
					RowStatus
			 }

		-- 1.3.6.1.4.1.989.1.16.2.8.3.2.1.1
		asxEsvcSfClassId OBJECT-TYPE
			SYNTAX Integer32 (1..2147483647)
			MAX-ACCESS not-accessible
			STATUS current
			DESCRIPTION
				"The ID number of the service flow class. Only has to be unique within a service product"
			::= { asxEsvcSfClassEntry 1 }

		
		-- 1.3.6.1.4.1.989.1.16.2.8.3.2.1.2
		asxEsvcSfClassServiceClassId OBJECT-TYPE
			SYNTAX Integer32 (1..2147483647)
			MAX-ACCESS read-create
			STATUS current
			DESCRIPTION
				"The ID of the service class that defines this service flow's QoS and other parameters. "
			::= { asxEsvcSfClassEntry 2 }

		
		-- 1.3.6.1.4.1.989.1.16.2.8.3.2.1.3
		asxEsvcSfClassDirection OBJECT-TYPE
			SYNTAX INTEGER
				{
				downstream(1),
				upstream(2)
				}
			MAX-ACCESS read-create
			STATUS current
			DESCRIPTION
				"An attribute indicating if the service flow is downstream or upstream.
				"
			::= { asxEsvcSfClassEntry 3 }

		
		-- 1.3.6.1.4.1.989.1.16.2.8.3.2.1.4
		asxEsvcSfClassAdmissionState OBJECT-TYPE
			SYNTAX WmanIf2fSfState
			MAX-ACCESS read-create
			STATUS current
			DESCRIPTION
				"The intended admission state of service flows derived from this class. "
			DEFVAL { authorized }
			::= { asxEsvcSfClassEntry 4 }

		
		-- 1.3.6.1.4.1.989.1.16.2.8.3.2.1.5
		asxEsvcSfClassSaid OBJECT-TYPE
			SYNTAX Integer32 (0..65535)
			MAX-ACCESS read-create
			STATUS current
			DESCRIPTION
				"The identifier of the security association to be used by the service flow. A value of 0 means that the SS's primary SAID will be used, if available. "
			DEFVAL { 0 }
			::= { asxEsvcSfClassEntry 5 }

		
		-- 1.3.6.1.4.1.989.1.16.2.8.3.2.1.6
		asxEsvcSfClassRowStatus OBJECT-TYPE
			SYNTAX RowStatus
			MAX-ACCESS read-create
			STATUS current
			DESCRIPTION
				"Tracks the state of the row."
			::= { asxEsvcSfClassEntry 6 }

		
		-- 1.3.6.1.4.1.989.1.16.2.8.3.3
		asxEsvcServiceClassExtTable OBJECT-TYPE
			SYNTAX SEQUENCE OF AsxEsvcServiceClassExtEntry
			MAX-ACCESS not-accessible
			STATUS current
			DESCRIPTION
				"This table contains extended parameters associated with service classes."
			::= { asxEsvcObjects 3 }

		
		-- 1.3.6.1.4.1.989.1.16.2.8.3.3.1
		asxEsvcServiceClassExtEntry OBJECT-TYPE
			SYNTAX AsxEsvcServiceClassExtEntry
			MAX-ACCESS not-accessible
			STATUS current
			DESCRIPTION
				"Service class extension table"
			INDEX { ifIndex, wmanIf2fBsQoSProfileIndex }
			::= { asxEsvcServiceClassExtTable 1 }

		
		AsxEsvcServiceClassExtEntry ::=
			SEQUENCE { 
				asxEsvcServiceClassExtPollPeriod
					Integer32,
				asxEsvcServiceClassExtRowStatus
					RowStatus,
				asxEsvcServiceClassExtHarqEnabled
					AsmaxBooleanSwitch,
				asxEsvcServiceClassExtHarqAcidMask
					Integer32,
				asxEsvcServiceClassExtHarqMaxTransmission
					Integer32,
				asxEsvcServiceClassExtHarqReorderSnSubheader
					INTEGER,
				asxEsvcServiceClassExtArqEnabled
					AsmaxBooleanSwitch,
				asxEsvcServiceClassExtArqDeliverInOrder
					AsmaxBooleanSwitch,
				asxEsvcServiceClassExtHarqMaxMatrixBRetransmission
					Integer32,
				asxEsvcServiceClassExtSetUlDiffServe
					AsmaxBooleanSwitch,
				asxEsvcServiceClassExtUlDiffServeField
					Integer32,
				asxEsvcServiceClassExtSetUlDiffServeMode
					INTEGER
			 }

		-- 1.3.6.1.4.1.989.1.16.2.8.3.3.1.1
		asxEsvcServiceClassExtPollPeriod OBJECT-TYPE
			SYNTAX Integer32 (1..60000)
			UNITS "ms"
			MAX-ACCESS read-create
			STATUS current
			DESCRIPTION
				"Poll period (in miliseconds) used by RTPS, nRTPS and UGS (sometimes)
				to define the grant repetition rate."
			DEFVAL { 1000 }
			::= { asxEsvcServiceClassExtEntry 1 }

		
		-- 1.3.6.1.4.1.989.1.16.2.8.3.3.1.2
		asxEsvcServiceClassExtRowStatus OBJECT-TYPE
			SYNTAX RowStatus
			MAX-ACCESS read-create
			STATUS current
			DESCRIPTION
				"Description."
			::= { asxEsvcServiceClassExtEntry 2 }

		
		-- 1.3.6.1.4.1.989.1.16.2.8.3.3.1.3
		asxEsvcServiceClassExtHarqEnabled OBJECT-TYPE
			SYNTAX AsmaxBooleanSwitch
			MAX-ACCESS read-create
			STATUS current
			DESCRIPTION
				"Set to TRUE to enable the operation of HARQ. "
			DEFVAL { booleanFalse }
			::= { asxEsvcServiceClassExtEntry 3 }

		
		-- 1.3.6.1.4.1.989.1.16.2.8.3.3.1.4
		asxEsvcServiceClassExtHarqAcidMask OBJECT-TYPE
			SYNTAX Integer32 (0..65535)
			MAX-ACCESS read-create
			STATUS current
			DESCRIPTION
				"A 16 bit mask that determines which HARQ ACIDs are to be used with the connection. "
			DEFVAL { 0 }
			::= { asxEsvcServiceClassExtEntry 4 }

		
		-- 1.3.6.1.4.1.989.1.16.2.8.3.3.1.5
		asxEsvcServiceClassExtHarqMaxTransmission OBJECT-TYPE
			SYNTAX Integer32 (0..2147483647)
			MAX-ACCESS read-create
			STATUS current
			DESCRIPTION
				"The maximum number of HARQ transmissions. "
			DEFVAL { 0 }
			::= { asxEsvcServiceClassExtEntry 5 }

		
		-- 1.3.6.1.4.1.989.1.16.2.8.3.3.1.6
		asxEsvcServiceClassExtHarqReorderSnSubheader OBJECT-TYPE
			SYNTAX INTEGER
				{
				harqReorderSnSubheaderNone(0),
				harqReorderSnSubheaderShort(1),
				harqReorderSnSubheaderLong(2)
				}
			MAX-ACCESS read-create
			STATUS current
			DESCRIPTION
				"HARQ reordering sequence number subheader. "
			DEFVAL { harqReorderSnSubheaderNone }
			::= { asxEsvcServiceClassExtEntry 6 }

		
		-- 1.3.6.1.4.1.989.1.16.2.8.3.3.1.7
		asxEsvcServiceClassExtArqEnabled OBJECT-TYPE
			SYNTAX AsmaxBooleanSwitch
			MAX-ACCESS read-create
			STATUS current
			DESCRIPTION
				"Set to TRUE to enable the operation of ARQ. 
				This column duplicates the column wmanIf2fBsQosScArqEnable but it is encoded as boolean."
			DEFVAL { booleanFalse }
			::= { asxEsvcServiceClassExtEntry 7 }

		
		-- 1.3.6.1.4.1.989.1.16.2.8.3.3.1.8
		asxEsvcServiceClassExtArqDeliverInOrder OBJECT-TYPE
			SYNTAX AsmaxBooleanSwitch
			MAX-ACCESS read-create
			STATUS current
			DESCRIPTION
				"Set to TRUE if ARQ protected traffic is to be delivered in order.
				This column duplicates the column wmanIf2fBsQosScArqDeliverInOrder but it is encoded as boolean."
			DEFVAL { booleanFalse }
			::= { asxEsvcServiceClassExtEntry 8 }

		
		-- 1.3.6.1.4.1.989.1.16.2.8.3.3.1.9
		asxEsvcServiceClassExtHarqMaxMatrixBRetransmission OBJECT-TYPE
			SYNTAX Integer32 (0..2147483647)
			MAX-ACCESS read-create
			STATUS current
			DESCRIPTION
				"The maximum number of times that a given HARQ subburst is retransmitted using matrix B 
				after a NACK, before falling back to matrix A for all further retranmissions. 
				A value of 0 indicates that only the first transmission is in matrix B, 
				and all subsequent retransmissions are in matrix A. "
			DEFVAL { 1 }
			::= { asxEsvcServiceClassExtEntry 9 }

		
		-- 1.3.6.1.4.1.989.1.16.2.8.3.3.1.10
		asxEsvcServiceClassExtSetUlDiffServe OBJECT-TYPE
			SYNTAX AsmaxBooleanSwitch
			MAX-ACCESS read-create
			STATUS deprecated
			DESCRIPTION
				"Set to TRUE to allow the replacement of the IP differential services field 
				in uplink traffic with the value in the ulDiffServeField column.
				This property is deprecated and should be set to:
				- booleanTrue if asxEsvcServiceClassExtSetUlDiffServeMode is set to ulDiffServeModeFixed
				- booleanFalse in all other cases"
			DEFVAL { booleanFalse }
			::= { asxEsvcServiceClassExtEntry 10 }

		
		-- 1.3.6.1.4.1.989.1.16.2.8.3.3.1.11
		asxEsvcServiceClassExtUlDiffServeField OBJECT-TYPE
			SYNTAX Integer32 (0..2147483647)
			MAX-ACCESS read-create
			STATUS current
			DESCRIPTION
				"Description."
			REFERENCE
				"The value to place in the IP differential services field in uplink traffic carried on this service flow."
			DEFVAL { 0 }
			::= { asxEsvcServiceClassExtEntry 11 }

		
		-- 1.3.6.1.4.1.989.1.16.2.8.3.3.1.12
		asxEsvcServiceClassExtSetUlDiffServeMode OBJECT-TYPE
			SYNTAX INTEGER
				{
				ulDiffServeModeNone(0),
				ulDiffServeModeFixed(1),
				ulDiffServeModeDynamic(2)
				}
			MAX-ACCESS read-create
			STATUS current
			DESCRIPTION
				"Instructs BS how to set the DiffServe field in uplink packets. 
				When ulDiffServeModeFixed the value of asxEsvcServiceClassExtUlDiffServeField is used.
				When ulDiffServeModeDynamic the service flow priority is used."
			DEFVAL { ulDiffServeModeNone }
			::= { asxEsvcServiceClassExtEntry 12 }

		
		-- 1.3.6.1.4.1.989.1.16.2.8.3.4
		asxEsvcRuleClassTable OBJECT-TYPE
			SYNTAX SEQUENCE OF AsxEsvcRuleClassEntry
			MAX-ACCESS not-accessible
			STATUS current
			DESCRIPTION
				"This table contains packet classifier rules associated
				with service flows."
			REFERENCE
				"Subclause 11.13.19.3.4 in IEEE Std 802.16-2004"
			::= { asxEsvcObjects 4 }

		
		-- 1.3.6.1.4.1.989.1.16.2.8.3.4.1
		asxEsvcRuleClassEntry OBJECT-TYPE
			SYNTAX AsxEsvcRuleClassEntry
			MAX-ACCESS not-accessible
			STATUS current
			DESCRIPTION
				"This table provides one row for each packet classifier 
				rule."
			INDEX { ifIndex, asxEsvcServiceProductName, asxEsvcSfClassId, asxEsvcRuleClassId }
			::= { asxEsvcRuleClassTable 1 }

		
		AsxEsvcRuleClassEntry ::=
			SEQUENCE { 
				asxEsvcRuleClassId
					Integer32,
				asxEsvcRuleClassPriority
					Integer32,
				asxEsvcRuleClassIpTosLow
					Integer32,
				asxEsvcRuleClassIpTosHigh
					Integer32,
				asxEsvcRuleClassIpTosMask
					Integer32,
				asxEsvcRuleClassIpProtocol
					Integer32,
				asxEsvcRuleClassIpAddrType
					InetAddressType,
				asxEsvcRuleClassIpSrcAddr
					InetAddress,
				asxEsvcRuleClassIpSrcMask
					InetAddress,
				asxEsvcRuleClassIpDestAddr
					InetAddress,
				asxEsvcRuleClassIpDestMask
					InetAddress,
				asxEsvcRuleClassSrcPortStart
					Integer32,
				asxEsvcRuleClassSrcPortEnd
					Integer32,
				asxEsvcRuleClassDestPortStart
					Integer32,
				asxEsvcRuleClassDestPortEnd
					Integer32,
				asxEsvcRuleClassDestMacAddr
					MacAddress,
				asxEsvcRuleClassDestMacMask
					MacAddress,
				asxEsvcRuleClassSrcMacAddr
					MacAddress,
				asxEsvcRuleClassSrcMacMask
					MacAddress,
				asxEsvcRuleClassEnetProtType
					INTEGER,
				asxEsvcRuleClassEnetProtocol
					Integer32,
				asxEsvcRuleClassUserPriLow
					Integer32,
				asxEsvcRuleClassUserPriHigh
					Integer32,
				asxEsvcRuleClassVlanId
					Integer32,
				asxEsvcRuleClassIpv6FlowLabel
					WmanIf2fIpv6FlowLabel,
				asxEsvcRuleClassActionRule
					WmanIf2fActionRule,
				asxEsvcRuleClassBitMap
					WmanIf2fClassifierMap,
				asxEsvcRuleClassRowStatus
					RowStatus,
				asxEsvcRuleClassDiscardRule
					AsmaxBooleanSwitch,
				asxEsvcRuleClassPhsValidate
					AsmaxBooleanSwitch,
				asxEsvcRuleClassPhsMask
					OCTET STRING,
				asxEsvcRuleClassPhsSize
					Integer32,
				asxEsvcRuleClassIpv6FlowLabel2
					Integer32,
				asxEsvcRuleClassPhsField
					OCTET STRING
			 }

		-- 1.3.6.1.4.1.989.1.16.2.8.3.4.1.1
		asxEsvcRuleClassId OBJECT-TYPE
			SYNTAX Integer32 (1..2147483647)
			MAX-ACCESS not-accessible
			STATUS current
			DESCRIPTION
				"An index is assigned to a classifier in BS classifiers
				table"
			::= { asxEsvcRuleClassEntry 1 }

		
		-- 1.3.6.1.4.1.989.1.16.2.8.3.4.1.2
		asxEsvcRuleClassPriority OBJECT-TYPE
			SYNTAX Integer32 (0..255)
			MAX-ACCESS read-create
			STATUS current
			DESCRIPTION
				"The value specifies the priority for the Classifier, which
				is used for determining the order of the Classifier. A
				higher value indicates higher priority. Classifiers may
				have priorities in the range 0..255."
			REFERENCE
				"Subclause 11.13.19.3.4.1 in IEEE Std 802.16-2004"
			::= { asxEsvcRuleClassEntry 2 }

		
		-- 1.3.6.1.4.1.989.1.16.2.8.3.4.1.3
		asxEsvcRuleClassIpTosLow OBJECT-TYPE
			SYNTAX Integer32 (0..255)
			MAX-ACCESS read-create
			STATUS current
			DESCRIPTION
				"The low value of a range of TOS byte values. If the
				referenced parameter is not present in a classifier, this
				object reports the value of 0."
			REFERENCE
				"Subclause 11.13.19.3.4.2 in IEEE Std 802.16-2004"
			::= { asxEsvcRuleClassEntry 3 }

		
		-- 1.3.6.1.4.1.989.1.16.2.8.3.4.1.4
		asxEsvcRuleClassIpTosHigh OBJECT-TYPE
			SYNTAX Integer32 (0..255)
			MAX-ACCESS read-create
			STATUS current
			DESCRIPTION
				"The 8-bit high value of a range of TOS byte values.
				If the referenced parameter is not present in a classifier,
				this object reports the value of 0."
			REFERENCE
				"Subclause 11.13.19.3.4.2 in IEEE Std 802.16-2004"
			::= { asxEsvcRuleClassEntry 4 }

		
		-- 1.3.6.1.4.1.989.1.16.2.8.3.4.1.5
		asxEsvcRuleClassIpTosMask OBJECT-TYPE
			SYNTAX Integer32 (0..255)
			MAX-ACCESS read-create
			STATUS current
			DESCRIPTION
				"The value of this object specifies the matching parameter
				for the IP type of service/DSCP [IETF RFC 2474] byte mask.
				An IP packet with IP type of service (ToS) byte value
				ip-tos matches this parameter if tos-low less than or
				equal (ip-tos AND tos-mask) less than or equal tos-high."
			REFERENCE
				"Subclause 11.13.19.3.4.2 in IEEE Std 802.16-2004"
			::= { asxEsvcRuleClassEntry 5 }

		
		-- 1.3.6.1.4.1.989.1.16.2.8.3.4.1.6
		asxEsvcRuleClassIpProtocol OBJECT-TYPE
			SYNTAX Integer32 (0..255)
			MAX-ACCESS read-create
			STATUS current
			DESCRIPTION
				"This object indicates the value of the IP Protocol field
				required for IP packets to match this rule. If the
				referenced parameter is not present in a classifier, this
				object reports the value of 0."
			REFERENCE
				"Subclause 11.13.19.3.4.3 in IEEE Std 802.16-2004"
			DEFVAL { 0 }
			::= { asxEsvcRuleClassEntry 6 }

		
		-- 1.3.6.1.4.1.989.1.16.2.8.3.4.1.7
		asxEsvcRuleClassIpAddrType OBJECT-TYPE
			SYNTAX InetAddressType
			MAX-ACCESS read-create
			STATUS current
			DESCRIPTION
				"Description."
			::= { asxEsvcRuleClassEntry 7 }

		
		-- 1.3.6.1.4.1.989.1.16.2.8.3.4.1.8
		asxEsvcRuleClassIpSrcAddr OBJECT-TYPE
			SYNTAX InetAddress
			MAX-ACCESS read-create
			STATUS current
			DESCRIPTION
				"This object specifies the value of the IP Source Address
				required for packets to match this rule. An IP packet
				matches the rule when the packet ip source address bitwise
				ANDed with the wmanIf2fBsClassifierRuleIpSrcMask value
				equals the wmanIf2fBsClassifierRuleIpSrcAddr value.
				If the referenced parameter is not present in a classifier,
				this object reports the value of 0.0.0.0."
			REFERENCE
				"Subclause 11.13.19.3.4.4 in IEEE Std 802.16-2004"
			DEFVAL { "" }
			::= { asxEsvcRuleClassEntry 8 }

		
		-- 1.3.6.1.4.1.989.1.16.2.8.3.4.1.9
		asxEsvcRuleClassIpSrcMask OBJECT-TYPE
			SYNTAX InetAddress
			MAX-ACCESS read-create
			STATUS current
			DESCRIPTION
				"This object specifies which bits of a packet's IP Source
				Address that are compared to match this rule. An IP packet
				matches the rule when the packet source address bitwise
				ANDed with the
				wmanIf2fBsClassifierRuleIpSrcMask value equals the
				wmanIf2fBsClassifierRuleIpSrcAddr value.
				If the referenced parameter is not present in a classifier,
				this object reports the value of 0.0.0.0."
			REFERENCE
				"Subclause 11.13.19.3.4.4 in IEEE Std 802.16-2004"
			DEFVAL { "" }
			::= { asxEsvcRuleClassEntry 9 }

		
		-- 1.3.6.1.4.1.989.1.16.2.8.3.4.1.10
		asxEsvcRuleClassIpDestAddr OBJECT-TYPE
			SYNTAX InetAddress
			MAX-ACCESS read-create
			STATUS current
			DESCRIPTION
				"This object specifies the value of the IP Destination
				Address required for packets to match this rule. An IP
				packet matches the rule when the packet IP destination
				address bitwise ANDed with the
				wmanIf2fBsClassifierRuleIpDestMask value equals the
				wmanIf2fBsClassifierRuleIpDestAddr value.
				If the referenced parameter is not present in a 
				classifier, this object reports the value of 0.0.0.0."
			REFERENCE
				"Subclause 11.13.19.3.4.5 in IEEE Std 802.16-2004"
			DEFVAL { "" }
			::= { asxEsvcRuleClassEntry 10 }

		
		-- 1.3.6.1.4.1.989.1.16.2.8.3.4.1.11
		asxEsvcRuleClassIpDestMask OBJECT-TYPE
			SYNTAX InetAddress
			MAX-ACCESS read-create
			STATUS current
			DESCRIPTION
				"This object specifies which bits of a packet's IP 
				Destination Address that are compared to match this rule.
				An IP packet matches the rule when the packet destination
				address bitwise ANDed with the
				wmanIf2fBsClassifierRuleIpDestMask value equals the
				wmanIf2fBsClassifierRuleIpDestAddr value.
				If the referenced parameter is not present in a classifier
				, this object reports the value of 0.0.0.0."
			REFERENCE
				"Subclause 11.13.19.3.4.5 in IEEE Std 802.16-2004"
			DEFVAL { "" }
			::= { asxEsvcRuleClassEntry 11 }

		
		-- 1.3.6.1.4.1.989.1.16.2.8.3.4.1.12
		asxEsvcRuleClassSrcPortStart OBJECT-TYPE
			SYNTAX Integer32 (0..65535)
			MAX-ACCESS read-create
			STATUS current
			DESCRIPTION
				"This object specifies the low end inclusive range of
				TCP/UDP source port numbers to which a packet is compared.
				This object is irrelevant for non-TCP/UDP IP packets.
				If the referenced parameter is not present in a
				classifier, this object reports the value of 0."
			REFERENCE
				"Subclause 11.13.19.3.4.6 in IEEE Std 802.16-2004"
			DEFVAL { 0 }
			::= { asxEsvcRuleClassEntry 12 }

		
		-- 1.3.6.1.4.1.989.1.16.2.8.3.4.1.13
		asxEsvcRuleClassSrcPortEnd OBJECT-TYPE
			SYNTAX Integer32 (0..65535)
			MAX-ACCESS read-create
			STATUS current
			DESCRIPTION
				"This object specifies the high end inclusive range of
				TCP/UDP source port numbers to which a packet is compared.
				This object is irrelevant for non-TCP/UDP IP packets.
				If the referenced parameter is not present in a classifier,
				this object reports the value of 65535."
			REFERENCE
				"Subclause 11.13.19.3.4.6 in IEEE Std 802.16-2004"
			DEFVAL { 0 }
			::= { asxEsvcRuleClassEntry 13 }

		
		-- 1.3.6.1.4.1.989.1.16.2.8.3.4.1.14
		asxEsvcRuleClassDestPortStart OBJECT-TYPE
			SYNTAX Integer32 (0..65535)
			MAX-ACCESS read-create
			STATUS current
			DESCRIPTION
				"This object specifies the low end inclusive range of
				TCP/UDP destination port numbers to which a packet is
				compared. If the referenced parameter is not present in a
				classifier, this object reports the value of 0."
			REFERENCE
				"Subclause 11.13.19.3.4.7 in IEEE Std 802.16-2004"
			DEFVAL { 0 }
			::= { asxEsvcRuleClassEntry 14 }

		
		-- 1.3.6.1.4.1.989.1.16.2.8.3.4.1.15
		asxEsvcRuleClassDestPortEnd OBJECT-TYPE
			SYNTAX Integer32 (0..65535)
			MAX-ACCESS read-create
			STATUS current
			DESCRIPTION
				"This object specifies the high end inclusive range of
				TCP/UDP destination port numbers to which a packet is
				compared. If the referenced parameter is not present in a
				classifier, this object reports the value of 65535."
			REFERENCE
				"Subclause 11.13.19.3.4.7 in IEEE Std 802.16-2004"
			DEFVAL { 0 }
			::= { asxEsvcRuleClassEntry 15 }

		
		-- 1.3.6.1.4.1.989.1.16.2.8.3.4.1.16
		asxEsvcRuleClassDestMacAddr OBJECT-TYPE
			SYNTAX MacAddress
			MAX-ACCESS read-create
			STATUS current
			DESCRIPTION
				"An Ethernet packet matches an entry when its destination
				MAC address bitwise ANDed with 
				wmanIf2fBsClassifierRuleDestMacMask equals the value of
				wmanIf2fBsClassifierRuleDestMacAddr. If the referenced
				parameter is not present in a classifier, this object
				reports the value of '000000000000'H."
			REFERENCE
				"Subclause 11.13.19.3.4.8 in IEEE Std 802.16-2004"
			::= { asxEsvcRuleClassEntry 16 }

		
		-- 1.3.6.1.4.1.989.1.16.2.8.3.4.1.17
		asxEsvcRuleClassDestMacMask OBJECT-TYPE
			SYNTAX MacAddress
			MAX-ACCESS read-create
			STATUS current
			DESCRIPTION
				"An Ethernet packet matches an entry when its destination
				MAC address bitwise ANDed with
				wmanIf2fBsClassifierRuleDestMacMask equals the value of
				wmanIf2fBsClassifierRuleDestMacAddr. If the referenced
				parameter is not present in a classifier, this object
				reports the value of '000000000000'H."
			REFERENCE
				"Subclause 11.13.19.3.4.8 in IEEE Std 802.16-2004"
			::= { asxEsvcRuleClassEntry 17 }

		
		-- 1.3.6.1.4.1.989.1.16.2.8.3.4.1.18
		asxEsvcRuleClassSrcMacAddr OBJECT-TYPE
			SYNTAX MacAddress
			MAX-ACCESS read-create
			STATUS current
			DESCRIPTION
				"An Ethernet packet matches this entry when its source
				MAC address  bitwise ANDed with
				wmanIf2fBsClassifierRuleSrcMacMask equals the value
				of wmanIf2fBsClassifierRuleSrcMacAddr. If the
				referenced parameter is not present in a classifier,
				this object reports the value of '000000000000'H."
			REFERENCE
				"Subclause 11.13.19.3.4.9 in IEEE Std 802.16-2004"
			::= { asxEsvcRuleClassEntry 18 }

		
		-- 1.3.6.1.4.1.989.1.16.2.8.3.4.1.19
		asxEsvcRuleClassSrcMacMask OBJECT-TYPE
			SYNTAX MacAddress
			MAX-ACCESS read-create
			STATUS current
			DESCRIPTION
				"An Ethernet packet matches an entry when its source
				MAC address bitwise ANDed with
				wmanIf2fBsClassifierRuleSrcMacMask equals the value of
				wmanIf2fBsClassifierRuleSrcMacAddr. If the referenced
				parameter is not present in a classifier, this object
				reports the value of '000000000000'H."
			REFERENCE
				"Subclause 11.13.19.3.4.9 in IEEE Std 802.16-2004"
			::= { asxEsvcRuleClassEntry 19 }

		
		-- 1.3.6.1.4.1.989.1.16.2.8.3.4.1.20
		asxEsvcRuleClassEnetProtType OBJECT-TYPE
			SYNTAX INTEGER
				{
				none(0),
				ethertype(1),
				dsap(2)
				}
			MAX-ACCESS read-create
			STATUS current
			DESCRIPTION
				"This object indicates the format of the layer 3 protocol
				id in the Ethernet packet. A value of none(0) means that
				the rule does not use the layer 3 protocol type as a
				matching criteria. A value of ethertype(1) means that the
				rule applies only to frames which contains an EtherType
				value. Ethertype values are contained in packets using
				the Dec-Intel-Xerox (DIX) encapsulation or the RFC1042
				Sub-Network Access Protocol (SNAP) encapsulation formats.
				A value of dsap(2) means that the rule applies only to
				frames using the IEEE802.3 encapsulation format with a
				Destination Service Access Point (DSAP) other than 0xAA
				(which is reserved for SNAP). If the Ethernet frame
				contains an 802.1P/Q Tag header (i.e. EtherType 0x8100),
				this object applies to the embedded EtherType field within
				the 802.1P/Q header. If the referenced parameter is not
				present in a classifier, this object reports the value of
				0."
			REFERENCE
				"Subclause 11.13.19.3.4.10 in IEEE Std 802.16-2004"
			::= { asxEsvcRuleClassEntry 20 }

		
		-- 1.3.6.1.4.1.989.1.16.2.8.3.4.1.21
		asxEsvcRuleClassEnetProtocol OBJECT-TYPE
			SYNTAX Integer32 (0..65535)
			MAX-ACCESS read-create
			STATUS current
			DESCRIPTION
				"If wmanIf2fBsClassifierRuleEnetProtocolType is none(0),
				this object is ignored when considering whether a packet
				matches the current rule.
				If wmanIf2fBsClassifierRuleEnetProtocolType is ethertype(1),
				this object gives the 16-bit value of the EtherType that
				the packet must match in order to match the rule.
				If wmanIf2fBsClassifierRuleEnetProtocolType is dsap(2), the
				lower 8 bits of this object's value must match the DSAP
				byte of the packet in order to match the rule.
				If the Ethernet frame contains an 802.1P/Q Tag header
				(i.e. EtherType 0x8100), this object applies to the
				embedded EtherType field within the 802.1P/Q header.
				If the referenced parameter is not present in the
				classifier, the value of this object is reported as 0."
			REFERENCE
				"Subclause 11.13.19.3.4.10 in IEEE Std 802.16-2004"
			::= { asxEsvcRuleClassEntry 21 }

		
		-- 1.3.6.1.4.1.989.1.16.2.8.3.4.1.22
		asxEsvcRuleClassUserPriLow OBJECT-TYPE
			SYNTAX Integer32 (0..7)
			MAX-ACCESS read-create
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority field
				within the range of wmanIf2fBsClassifierRuleUserPriLow and
				wmanIf2fBsClassifierRuleUserPriHigh in order to match this
				rule.
				If the referenced parameter is not present in the
				classifier, the value of this object is reported as 0."
			REFERENCE
				"Subclause 11.13.19.3.4.11 in IEEE Std 802.16-2004"
			::= { asxEsvcRuleClassEntry 22 }

		
		-- 1.3.6.1.4.1.989.1.16.2.8.3.4.1.23
		asxEsvcRuleClassUserPriHigh OBJECT-TYPE
			SYNTAX Integer32 (0..7)
			MAX-ACCESS read-create
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority
				field within the range of wmanIf2fBsClassifierRuleUserPriLow
				and wmanIf2fBsClassifierRuleUserPriHigh in order to match
				this rule.
				If the referenced parameter is not present in the 
				classifier, the value of this object is reported as 7."
			REFERENCE
				"Subclause 11.13.19.3.4.11 in IEEE Std 802.16-2004"
			::= { asxEsvcRuleClassEntry 23 }

		
		-- 1.3.6.1.4.1.989.1.16.2.8.3.4.1.24
		asxEsvcRuleClassVlanId OBJECT-TYPE
			SYNTAX Integer32 (0..4095)
			MAX-ACCESS read-create
			STATUS current
			DESCRIPTION
				"This object applies only to Ethernet frames using the
				802.1P/Q tag header.
				If this object's value is nonzero, tagged packets must
				have a VLAN Identifier that matches the value in order
				to match the rule.
				Only the least significant 12 bits of this object's
				value are valid.
				If the referenced parameter is not present in the
				classifier, the value of this object is reported as 0."
			REFERENCE
				"Subclause 11.13.19.3.4.12 in IEEE Std 802.16-2004"
			::= { asxEsvcRuleClassEntry 24 }

		
		-- 1.3.6.1.4.1.989.1.16.2.8.3.4.1.25
		asxEsvcRuleClassIpv6FlowLabel OBJECT-TYPE
			SYNTAX WmanIf2fIpv6FlowLabel
			MAX-ACCESS read-create
			STATUS obsolete
			DESCRIPTION
				"OBSOLETE: Type incompatible with equipment. Replaced with asxEsvcRuleClassIpv6FlowLabel2
				The value of this field specifies the matching values for the IPv6 Flow label field."
			::= { asxEsvcRuleClassEntry 25 }

		
		-- 1.3.6.1.4.1.989.1.16.2.8.3.4.1.26
		asxEsvcRuleClassActionRule OBJECT-TYPE
			SYNTAX WmanIf2fActionRule
			MAX-ACCESS read-create
			STATUS obsolete
			DESCRIPTION
				"OBSOLETE: Type incompatible with equipment. Replaced with asxEsvcRuleClassDiscardRule.
				The value of this field specifies an action associated with
				the classifier rule. If this classification action rule
				exists, its action shall be applied on the packets that
				match this classifier rule."
			::= { asxEsvcRuleClassEntry 26 }

		
		-- 1.3.6.1.4.1.989.1.16.2.8.3.4.1.27
		asxEsvcRuleClassBitMap OBJECT-TYPE
			SYNTAX WmanIf2fClassifierMap
			MAX-ACCESS read-create
			STATUS current
			DESCRIPTION
				"This object indicates which parameter encodings were
				actually present in the entry. A bit set to '1' indicates
				the corresponding classifier encoding is present, and '0'
				means otherwise"
			::= { asxEsvcRuleClassEntry 27 }

		
		-- 1.3.6.1.4.1.989.1.16.2.8.3.4.1.28
		asxEsvcRuleClassRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { asxEsvcRuleClassEntry 28 }

		
		-- 1.3.6.1.4.1.989.1.16.2.8.3.4.1.29
		asxEsvcRuleClassDiscardRule OBJECT-TYPE
			SYNTAX AsmaxBooleanSwitch
			MAX-ACCESS read-create
			STATUS current
			DESCRIPTION
				"Indicates this is a discard rule. When true and the packet matches the rule it is discarded."
			DEFVAL { booleanFalse }
			::= { asxEsvcRuleClassEntry 29 }

		
		-- 1.3.6.1.4.1.989.1.16.2.8.3.4.1.30
		asxEsvcRuleClassPhsValidate OBJECT-TYPE
			SYNTAX AsmaxBooleanSwitch
			MAX-ACCESS read-create
			STATUS current
			DESCRIPTION
				"Set to TRUE to enable PHS validation of the field before suppression. "
			DEFVAL { booleanFalse }
			::= { asxEsvcRuleClassEntry 30 }

		
		-- 1.3.6.1.4.1.989.1.16.2.8.3.4.1.31
		asxEsvcRuleClassPhsMask OBJECT-TYPE
			SYNTAX OCTET STRING (SIZE (0..65535))
			MAX-ACCESS read-create
			STATUS current
			DESCRIPTION
				"This object is used to configure the PHS rule for this classifer. It is encoded as follows:
				bit 0:
				  0 = do not suppress first byte of the suppression field
				  1 = suppress first byte of the suppression field
				bit 1:
				  0 = do not suppress second byte of the suppression field
				  1 = suppress second byte of the suppression field
				bit x:
				  0 = do not suppress (x+1) byte of the suppression field
				  1 = suppress (x+1) byte of the suppression field
				where the length of the octet string is ceiling (PhsSize/8). 
				BS should use this value to create a new PHS rule index (PHSI) as
				defined in the standard."
			::= { asxEsvcRuleClassEntry 31 }

		
		-- 1.3.6.1.4.1.989.1.16.2.8.3.4.1.32
		asxEsvcRuleClassPhsSize OBJECT-TYPE
			SYNTAX Integer32 (0..255)
			MAX-ACCESS read-create
			STATUS current
			DESCRIPTION
				"The value of this field - PHSS is the total number of bytes in the header 
				to be suppressed and then restored in a service flow that uses PHS. 
				If the value of this field is 0 bytes then PHS is disabled for this classifer."
			DEFVAL { 0 }
			::= { asxEsvcRuleClassEntry 32 }

		
		-- 1.3.6.1.4.1.989.1.16.2.8.3.4.1.33
		asxEsvcRuleClassIpv6FlowLabel2 OBJECT-TYPE
			SYNTAX Integer32 (0..1048575)
			MAX-ACCESS read-create
			STATUS current
			DESCRIPTION
				"The IP version 6 flow label to match. It is defined as 20 bit number."
			DEFVAL { 0 }
			::= { asxEsvcRuleClassEntry 33 }

		
		-- 1.3.6.1.4.1.989.1.16.2.8.3.4.1.34
		asxEsvcRuleClassPhsField OBJECT-TYPE
			SYNTAX OCTET STRING (SIZE (0..65535))
			MAX-ACCESS read-create
			STATUS current
			DESCRIPTION
				"The PHSF (PHS Field) is a string of bytes containing the header information 
				to be suppressed by the sending CS and reconstructed by the receiving CS. 
				The most significant byte of the string corresponds to the first byte of the PDU."
			::= { asxEsvcRuleClassEntry 34 }

		
		-- 1.3.6.1.4.1.989.1.16.2.8.3.5
		asxEsvcServiceCfgTable OBJECT-TYPE
			SYNTAX SEQUENCE OF AsxEsvcServiceCfgEntry
			MAX-ACCESS not-accessible
			STATUS current
			DESCRIPTION
				"This table allows configuring QosProfile for each management connection for each wimax interface.
				"
			::= { asxEsvcObjects 5 }

		
		-- 1.3.6.1.4.1.989.1.16.2.8.3.5.1
		asxEsvcServiceCfgEntry OBJECT-TYPE
			SYNTAX AsxEsvcServiceCfgEntry
			MAX-ACCESS not-accessible
			STATUS current
			DESCRIPTION
				"This table provides configuration of QosProfile for each management connection for each wimax interface."
			INDEX { ifIndex }
			::= { asxEsvcServiceCfgTable 1 }

		
		AsxEsvcServiceCfgEntry ::=
			SEQUENCE { 
				asxEsvcServiceCfgUlBasicMgmtQosProfIndex
					Integer32,
				asxEsvcServiceCfgDlBasicMgmtQosProfIndex
					Integer32,
				asxEsvcServiceCfgUlPrimaryMgmtQosProfIndex
					Integer32,
				asxEsvcServiceCfgDlPrimaryMgmtQosProfIndex
					Integer32,
				asxEsvcServiceCfgUlSecondaryMgmtQosProfIndex
					Integer32,
				asxEsvcServiceCfgDlSecondaryMgmtQosProfIndex
					Integer32,
				asxEsvcServiceCfgUlMinTolOverBookingRatio
					Integer32,
				asxEsvcServiceCfgDlMinTolOverBookingRatio
					Integer32,
				asxEsvcServiceCfgUlCirOverBookingRatio
					Integer32,
				asxEsvcServiceCfgDlCirOverBookingRatio
					Integer32
			 }

		-- 1.3.6.1.4.1.989.1.16.2.8.3.5.1.1
		asxEsvcServiceCfgUlBasicMgmtQosProfIndex OBJECT-TYPE
			SYNTAX Integer32 (0..2147483647)
			MAX-ACCESS read-write
			STATUS current
			DESCRIPTION
				"The service class used to define the operating characteristics of uplink basic management connections. 
				This index refers to wmanIf2fBsQoSProfileIndex in wmanIf2fBsProvServiceClassTable."
			::= { asxEsvcServiceCfgEntry 1 }

		
		-- 1.3.6.1.4.1.989.1.16.2.8.3.5.1.2
		asxEsvcServiceCfgDlBasicMgmtQosProfIndex OBJECT-TYPE
			SYNTAX Integer32 (0..2147483647)
			MAX-ACCESS read-write
			STATUS current
			DESCRIPTION
				"The service class used to define the operating characteristics of downlink basic management connections. 
				This index refers to wmanIf2fBsQoSProfileIndex in wmanIf2fBsProvServiceClassTable."
			::= { asxEsvcServiceCfgEntry 2 }

		
		-- 1.3.6.1.4.1.989.1.16.2.8.3.5.1.3
		asxEsvcServiceCfgUlPrimaryMgmtQosProfIndex OBJECT-TYPE
			SYNTAX Integer32 (0..2147483647)
			MAX-ACCESS read-write
			STATUS current
			DESCRIPTION
				"The service class used to define the operating characteristics of uplink primary management connections. 
				This index refers to wmanIf2fBsQoSProfileIndex in wmanIf2fBsProvServiceClassTable."
			::= { asxEsvcServiceCfgEntry 3 }

		
		-- 1.3.6.1.4.1.989.1.16.2.8.3.5.1.4
		asxEsvcServiceCfgDlPrimaryMgmtQosProfIndex OBJECT-TYPE
			SYNTAX Integer32 (0..2147483647)
			MAX-ACCESS read-write
			STATUS current
			DESCRIPTION
				"The service class used to define the operating characteristics of downlink primary management connections. 
				This index refers to wmanIf2fBsQoSProfileIndex in wmanIf2fBsProvServiceClassTable."
			::= { asxEsvcServiceCfgEntry 4 }

		
		-- 1.3.6.1.4.1.989.1.16.2.8.3.5.1.5
		asxEsvcServiceCfgUlSecondaryMgmtQosProfIndex OBJECT-TYPE
			SYNTAX Integer32 (0..2147483647)
			MAX-ACCESS read-write
			STATUS current
			DESCRIPTION
				"The service class used to define the operating characteristics of uplink secondary management connections.
				This index refers to wmanIf2fBsQoSProfileIndex in wmanIf2fBsProvServiceClassTable."
			::= { asxEsvcServiceCfgEntry 5 }

		
		-- 1.3.6.1.4.1.989.1.16.2.8.3.5.1.6
		asxEsvcServiceCfgDlSecondaryMgmtQosProfIndex OBJECT-TYPE
			SYNTAX Integer32 (0..2147483647)
			MAX-ACCESS read-write
			STATUS current
			DESCRIPTION
				"The service class used to define the operating characteristics of downlink secondary management connections. 
				This index refers to wmanIf2fBsQoSProfileIndex in wmanIf2fBsProvServiceClassTable."
			::= { asxEsvcServiceCfgEntry 6 }

		
		-- 1.3.6.1.4.1.989.1.16.2.8.3.5.1.7
		asxEsvcServiceCfgUlMinTolOverBookingRatio OBJECT-TYPE
			SYNTAX Integer32 (0..100)
			UNITS "%"
			MAX-ACCESS read-write
			STATUS current
			DESCRIPTION
				"Overbooking ratio for the minimum tolerable rate in the uplink. in percentage."
			DEFVAL { 100 }
			::= { asxEsvcServiceCfgEntry 7 }

		
		-- 1.3.6.1.4.1.989.1.16.2.8.3.5.1.8
		asxEsvcServiceCfgDlMinTolOverBookingRatio OBJECT-TYPE
			SYNTAX Integer32 (0..100)
			UNITS "%"
			MAX-ACCESS read-write
			STATUS current
			DESCRIPTION
				"Overbooking ratio for the minimum tolerable rate in the downlink. in percentage."
			::= { asxEsvcServiceCfgEntry 8 }

		
		-- 1.3.6.1.4.1.989.1.16.2.8.3.5.1.9
		asxEsvcServiceCfgUlCirOverBookingRatio OBJECT-TYPE
			SYNTAX Integer32 (0..100)
			UNITS "%"
			MAX-ACCESS read-write
			STATUS current
			DESCRIPTION
				"Overbooking ratio for the minimum reserved rate in the uplink."
			DEFVAL { 0 }
			::= { asxEsvcServiceCfgEntry 9 }

		
		-- 1.3.6.1.4.1.989.1.16.2.8.3.5.1.10
		asxEsvcServiceCfgDlCirOverBookingRatio OBJECT-TYPE
			SYNTAX Integer32 (0..100)
			UNITS "%"
			MAX-ACCESS read-write
			STATUS current
			DESCRIPTION
				"Overbooking ratio for the minimum reserved rate in the downlink. "
			DEFVAL { 0 }
			::= { asxEsvcServiceCfgEntry 10 }

		
		-- 1.3.6.1.4.1.989.1.16.2.8.3.6
		asxEsvcSfExtTable OBJECT-TYPE
			SYNTAX SEQUENCE OF AsxEsvcSfExtEntry
			MAX-ACCESS not-accessible
			STATUS current
			DESCRIPTION
				"Extension of wmanIf2fBsServiceFlowTable with custom status objects.
				Contains important status information missed in wmanIf2fBs mib."
			::= { asxEsvcObjects 6 }

		
		-- 1.3.6.1.4.1.989.1.16.2.8.3.6.1
		asxEsvcSfExtEntry OBJECT-TYPE
			SYNTAX AsxEsvcSfExtEntry
			MAX-ACCESS not-accessible
			STATUS current
			DESCRIPTION
				"Description."
			INDEX { ifIndex, wmanIf2fBsSfMacAddress, wmanIf2fBsSfId }
			::= { asxEsvcSfExtTable 1 }

		
		AsxEsvcSfExtEntry ::=
			SEQUENCE { 
				asxEsvcSfExtInternalState
					INTEGER,
				asxEsvcSfExtProvSource
					INTEGER,
				asxEsvcSfExtAsnDataPathEncap
					INTEGER,
				asxEsvcSfExtAsnDataPathId
					Integer32,
				asxEsvcSfExtTunnelPresent
					AsmaxBooleanSwitch
			 }

		-- 1.3.6.1.4.1.989.1.16.2.8.3.6.1.1
		asxEsvcSfExtInternalState OBJECT-TYPE
			SYNTAX INTEGER
				{
				sfIntStateNull(0),
				sfIntStateAddingLocal(1),
				sfIntStateAddingRemote(2),
				sfIntStateNominal(3),
				sfIntStateChangingLocal(4),
				sfIntStateChangingRemote(5),
				sfIntStateDeleting(6),
				sfIntStateAddingLocalPending(7),
				sfIntStateAddingRemotePending(8),
				sfIntStateChangingLocalPending(9),
				sfIntStateChangingRemotePending(10),
				sfIntStateDeletingPending(11),
				sfIntStateWaiting(12),
				sfIntStateErrorDeleting(13),
				sfIntStateNominalPending(14),
				sfIntStateHandingOver(15)
				}
			MAX-ACCESS read-only
			STATUS current
			DESCRIPTION
				"Internal state of the service flow showing all the intermediate phases
				of service flow creation, changing and deletion."
			::= { asxEsvcSfExtEntry 1 }

		
		-- 1.3.6.1.4.1.989.1.16.2.8.3.6.1.2
		asxEsvcSfExtProvSource OBJECT-TYPE
			SYNTAX INTEGER
				{
				sfProvSourceLocalProvisioning(0),
				sfProvSourceRemoteSs(1),
				sfProvSourceasnGateway(2),
				sfProvSourceHandover(3)
				}
			MAX-ACCESS read-only
			STATUS current
			DESCRIPTION
				"Indicates the source of the configuration for the active service flow."
			::= { asxEsvcSfExtEntry 2 }

		
		-- 1.3.6.1.4.1.989.1.16.2.8.3.6.1.3
		asxEsvcSfExtAsnDataPathEncap OBJECT-TYPE
			SYNTAX INTEGER
				{
				sfAsnDataEncapGre(1),
				sfAsnDataEncapIpInIp(2),
				sfAsnDataEncapVlan(3)
				}
			MAX-ACCESS read-only
			STATUS current
			DESCRIPTION
				"Indicates the type of encapsulation used for the service flow data in the ASN protocol."
			::= { asxEsvcSfExtEntry 3 }

		
		-- 1.3.6.1.4.1.989.1.16.2.8.3.6.1.4
		asxEsvcSfExtAsnDataPathId OBJECT-TYPE
			SYNTAX Integer32
			MAX-ACCESS read-only
			STATUS current
			DESCRIPTION
				"The identifier used by the data path encapsulation."
			::= { asxEsvcSfExtEntry 4 }

		
		-- 1.3.6.1.4.1.989.1.16.2.8.3.6.1.5
		asxEsvcSfExtTunnelPresent OBJECT-TYPE
			SYNTAX AsmaxBooleanSwitch
			MAX-ACCESS read-only
			STATUS current
			DESCRIPTION
				"Set to TRUE if a data tunnel to an ASN-Gateway is present for this service flow."
			::= { asxEsvcSfExtEntry 5 }

		
		-- 1.3.6.1.4.1.989.1.16.2.8.3.7
		asxEsvcProvRuleExtTable OBJECT-TYPE
			SYNTAX SEQUENCE OF AsxEsvcProvRuleExtEntry
			MAX-ACCESS not-accessible
			STATUS current
			DESCRIPTION
				"Extension of wmanIf2fBsProvClassifierRuleTable with custom prov objects.
				Contains objects compatible with BS implementation."
			::= { asxEsvcObjects 7 }

		
		-- 1.3.6.1.4.1.989.1.16.2.8.3.7.1
		asxEsvcProvRuleExtEntry OBJECT-TYPE
			SYNTAX AsxEsvcProvRuleExtEntry
			MAX-ACCESS not-accessible
			STATUS current
			DESCRIPTION
				"Description."
			INDEX { ifIndex, wmanIf2fBsSsProvMacAddress, wmanIf2fBsSfId, wmanIf2fBsProvClsfRuleIndex }
			::= { asxEsvcProvRuleExtTable 1 }

		
		AsxEsvcProvRuleExtEntry ::=
			SEQUENCE { 
				asxEsvcProvRuleExtDiscardRule
					AsmaxBooleanSwitch,
				asxEsvcProvRuleExtPhsValidate
					AsmaxBooleanSwitch,
				asxEsvcProvRuleExtPhsMask
					OCTET STRING,
				asxEsvcProvRuleExtPhsSize
					Integer32,
				asxEsvcProvRuleExtIpv6FlowLabel2
					Integer32,
				asxEsvcProvRuleExtPhsField
					OCTET STRING,
				asxEsvcProvRuleExtRowStatus
					RowStatus
			 }

		-- 1.3.6.1.4.1.989.1.16.2.8.3.7.1.1
		asxEsvcProvRuleExtDiscardRule OBJECT-TYPE
			SYNTAX AsmaxBooleanSwitch
			MAX-ACCESS read-create
			STATUS current
			DESCRIPTION
				"Indicates this is a discard rule. When true and the packet matches the rule it is discarded."
			DEFVAL { booleanFalse }
			::= { asxEsvcProvRuleExtEntry 1 }

		
		-- 1.3.6.1.4.1.989.1.16.2.8.3.7.1.2
		asxEsvcProvRuleExtPhsValidate OBJECT-TYPE
			SYNTAX AsmaxBooleanSwitch
			MAX-ACCESS read-create
			STATUS current
			DESCRIPTION
				"Set to TRUE to enable PHS validation of the field before suppression. "
			DEFVAL { booleanFalse }
			::= { asxEsvcProvRuleExtEntry 2 }

		
		-- 1.3.6.1.4.1.989.1.16.2.8.3.7.1.3
		asxEsvcProvRuleExtPhsMask OBJECT-TYPE
			SYNTAX OCTET STRING (SIZE (0..65535))
			MAX-ACCESS read-create
			STATUS current
			DESCRIPTION
				"This object is used to configure the PHS rule for this classifer. It is encoded as follows:
				bit 0:
				  0 = do not suppress first byte of the suppression field
				  1 = suppress first byte of the suppression field
				bit 1:
				  0 = do not suppress second byte of the suppression field
				  1 = suppress second byte of the suppression field
				bit x:
				  0 = do not suppress (x+1) byte of the suppression field
				  1 = suppress (x+1) byte of the suppression field
				where the length of the octet string is ceiling (PhsSize/8). 
				BS should use this value to create a new PHS rule index (PHSI) as
				defined in the standard."
			::= { asxEsvcProvRuleExtEntry 3 }

		
		-- 1.3.6.1.4.1.989.1.16.2.8.3.7.1.4
		asxEsvcProvRuleExtPhsSize OBJECT-TYPE
			SYNTAX Integer32 (0..255)
			MAX-ACCESS read-create
			STATUS current
			DESCRIPTION
				"The value of this field - PHSS is the total number of bytes in the header 
				to be suppressed and then restored in a service flow that uses PHS. 
				If the value of this field is 0 bytes then PHS is disabled for this classifer."
			DEFVAL { 0 }
			::= { asxEsvcProvRuleExtEntry 4 }

		
		-- 1.3.6.1.4.1.989.1.16.2.8.3.7.1.5
		asxEsvcProvRuleExtIpv6FlowLabel2 OBJECT-TYPE
			SYNTAX Integer32 (0..1048575)
			MAX-ACCESS read-create
			STATUS current
			DESCRIPTION
				"The IP version 6 flow label to match. It is defined as 20 bit number."
			DEFVAL { 0 }
			::= { asxEsvcProvRuleExtEntry 5 }

		
		-- 1.3.6.1.4.1.989.1.16.2.8.3.7.1.6
		asxEsvcProvRuleExtPhsField OBJECT-TYPE
			SYNTAX OCTET STRING (SIZE (0..65535))
			MAX-ACCESS read-create
			STATUS current
			DESCRIPTION
				"The PHSF (PHS Field) is a string of bytes containing the header information 
				to be suppressed by the sending CS and reconstructed by the receiving CS. 
				The most significant byte of the string corresponds to the first byte of the PDU."
			::= { asxEsvcProvRuleExtEntry 6 }

		
		-- 1.3.6.1.4.1.989.1.16.2.8.3.7.1.7
		asxEsvcProvRuleExtRowStatus OBJECT-TYPE
			SYNTAX RowStatus
			MAX-ACCESS read-create
			STATUS current
			DESCRIPTION
				"Description."
			::= { asxEsvcProvRuleExtEntry 7 }

		
	
	END

--
-- ASMAX-ESVC-MIB.mib
--
