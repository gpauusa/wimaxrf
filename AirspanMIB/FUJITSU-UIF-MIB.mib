--
-- FUJITSU-UIF-MIB.mib
-- MIB generated by MG-SOFT Visual MIB Builder Version 5.0  Build 250
-- Tuesday, August 26, 2008 at 16:57:48
--
-- Modified at September 08, 2008 by Hitachi.
-- Modified at September 30, 2008 by Hitachi.
--

	FUJITSU-UIF-MIB DEFINITIONS ::= BEGIN
 
		IMPORTS
			ItuPerceivedSeverity			
				FROM ITU-ALARM-TC-MIB			
			SnmpAdminString			
				FROM SNMP-FRAMEWORK-MIB			
			OBJECT-GROUP, MODULE-COMPLIANCE, NOTIFICATION-GROUP			
				FROM SNMPv2-CONF			
			enterprises, Integer32, OBJECT-TYPE, MODULE-IDENTITY, NOTIFICATION-TYPE			
				FROM SNMPv2-SMI			
			DisplayString			
				FROM SNMPv2-TC;
	
	
		uqUif MODULE-IDENTITY 
			LAST-UPDATED ""		-- 
			ORGANIZATION 
				"uqcommunications"
			CONTACT-INFO 
				"uqcommunications
				"
			DESCRIPTION 
				"MIBs module defining the traps for NBIF of unified OMC system.
				The MIB is desinged based on the specification of NBIF for UQC."
			REVISION "200804211704Z"		-- April 21, 2008 at 17:04 GMT
			DESCRIPTION 
				"Draft 1: Initial version with AlarmTrap. This version is temporary for evaluation 
				purposes only. When the enterprise OID is aquired this MIB will be turned into 
				a properly identified one."
			REVISION "200805141608Z"		-- May 14, 2008 at 16:08 GMT
			DESCRIPTION 
				"Draft 2: Updated for 3 traps types rather than just one."
			REVISION "200805201150Z"		-- May 20, 2008 at 11:50 GMT
			DESCRIPTION 
				"Draft 3: Added trap uqUifReestablishmentCompleteTrap"
			REVISION "200805271505Z"		-- May 27, 2008 at 15:05 GMT
			DESCRIPTION 
				"Version 1.0: Changed NodeId from integer to SnmpAdminString (utf-8)
				"
			REVISION "200807161003Z"		-- July 16, 2008 at 10:03 GMT
			DESCRIPTION 
				"Version 1.1:
				Changed description of uqUifTrapMoreInfo
				Changed mib filename, module identity, OID prefixes"
			REVISION "200808261656Z"		-- August 26, 2008 at 16:56 GMT
			DESCRIPTION 
				"Version 1.1a:
				Changed SYNTAX uqUifTrapEntry to UqUifTrapEntry"
			::= { bs-omc 1 }

		
	
	
--
-- Node definitions
--
	
		fujitsu OBJECT IDENTIFIER ::= { enterprises 211}

		application OBJECT IDENTIFIER ::= { fujitsu 4 }

		aplNetwork OBJECT IDENTIFIER ::= { application 1 }

		aplNetFunction OBJECT IDENTIFIER ::= { aplNetwork 3 }

		aplWiMAX OBJECT IDENTIFIER ::= { aplNetFunction 58 }

		bs-omc OBJECT IDENTIFIER ::= { aplWiMAX 3 }
		
		uqUifConformance OBJECT IDENTIFIER ::= { uqUif 1 }

		
		uqUifCompliance MODULE-COMPLIANCE
			STATUS current
			DESCRIPTION 
				"Description."
			MODULE -- this module
				MANDATORY-GROUPS { uqUifNotificationGroup, uqUifObjectGroup }
			::= { uqUifConformance 1 }

		
		uqUifNotificationGroup NOTIFICATION-GROUP
			NOTIFICATIONS { uqUifAlarmTrap, uqUifServiceStateTrap, uqUifMaintenanceStateTrap, uqUifReestablishmentComplete }
			STATUS current
			DESCRIPTION 
				"Description."
			::= { uqUifConformance 2 }

		
		uqUifObjectGroup OBJECT-GROUP
			OBJECTS { uqUifTrapTsn, uqUifTrapTime, uqUifTrapSeverity, uqUifTrapTypeId, uqUifTrapNodeType, 
				uqUifTrapNodeId, uqUifTrapFunctionBlock, uqUifTrapMoreInfo, uqUifTrapCause, uqUifTrapServiceState, 
				uqUifTrapMaintenanceState }
			STATUS current
			DESCRIPTION 
				"Description."
			::= { uqUifConformance 3 }

		
		uqUifNotifications OBJECT IDENTIFIER ::= { uqUif 2 }

		
		uqUifTrapPrefix OBJECT IDENTIFIER ::= { uqUifNotifications 0 }

		
		uqUifAlarmTrap NOTIFICATION-TYPE
			OBJECTS { uqUifTrapTsn, uqUifTrapTime, uqUifTrapSeverity, uqUifTrapTypeId, uqUifTrapNodeType, 
				uqUifTrapNodeId, uqUifTrapFunctionBlock, uqUifTrapMoreInfo, uqUifTrapCause }
			STATUS current
			DESCRIPTION 
				"NMS sends the trap to notify the manager about the change in
				an alarm status."
			::= { uqUifTrapPrefix 1 }

		
		uqUifServiceStateTrap NOTIFICATION-TYPE
			OBJECTS { uqUifTrapTsn, uqUifTrapTime, uqUifTrapTypeId, uqUifTrapNodeType, uqUifTrapNodeId, 
				uqUifTrapFunctionBlock, uqUifTrapServiceState }
			STATUS current
			DESCRIPTION 
				"Service state change report."
			::= { uqUifTrapPrefix 2 }

		
		uqUifMaintenanceStateTrap NOTIFICATION-TYPE
			OBJECTS { uqUifTrapTsn, uqUifTrapTime, uqUifTrapTypeId, uqUifTrapNodeType, uqUifTrapNodeId, 
				uqUifTrapFunctionBlock, uqUifTrapMaintenanceState }
			STATUS current
			DESCRIPTION 
				"Description."
			::= { uqUifTrapPrefix 3 }

		
		uqUifReestablishmentComplete NOTIFICATION-TYPE
			OBJECTS { uqUifTrapTsn, uqUifTrapTime, uqUifTrapTypeId, uqUifTrapNodeType, uqUifTrapNodeId
				 }
			STATUS current
			DESCRIPTION 
				"Trap sent when reestablishment of communication with BS and OMC (BS-OMC) is complete after reset."
			::= { uqUifTrapPrefix 4 }

		
		uqUifTrapTable OBJECT-TYPE
			SYNTAX SEQUENCE OF UqUifTrapEntry
			MAX-ACCESS not-accessible
			STATUS current
			DESCRIPTION
				"Contains status of objects assotiated with NBIF Alarm and Events Traps.
				BS-OMC sends traps to notify the manager about the change in alarm state or to send traps.
				The objects are used only for traps - no data is avaialble for gets."
			::= { uqUifNotifications 1 }

		
		uqUifTrapEntry OBJECT-TYPE
			SYNTAX UqUifTrapEntry
			MAX-ACCESS not-accessible
			STATUS current
			DESCRIPTION
				"Defines objects used in traps - no actual data available."
			INDEX { uqUifTrapTsn }
			::= { uqUifTrapTable 1 }

		
		UqUifTrapEntry ::=
			SEQUENCE { 
				uqUifTrapTsn
					Integer32,
				uqUifTrapTime
					Integer32,
				uqUifTrapSeverity
					ItuPerceivedSeverity,
				uqUifTrapTypeId
					Integer32,
				uqUifTrapNodeType
					INTEGER,
				uqUifTrapNodeId
					SnmpAdminString,
				uqUifTrapFunctionBlock
					DisplayString,
				uqUifTrapMoreInfo
					DisplayString,
				uqUifTrapCause
					DisplayString,
				uqUifTrapServiceState
					INTEGER,
				uqUifTrapMaintenanceState
					INTEGER
			 }

		uqUifTrapTsn OBJECT-TYPE
			SYNTAX Integer32 (1..2147483647)
			MAX-ACCESS accessible-for-notify
			STATUS current
			DESCRIPTION
				"Trap sequence number used by OMC system to detect the synchronisation problems."
			::= { uqUifTrapEntry 1 }

		
		uqUifTrapTime OBJECT-TYPE
			SYNTAX Integer32
			MAX-ACCESS accessible-for-notify
			STATUS current
			DESCRIPTION
				"Date and time when the trap was sent.
				This is an integer representing the culmulative time since the epoch in seconds."
			::= { uqUifTrapEntry 2 }

		
		uqUifTrapSeverity OBJECT-TYPE
			SYNTAX ItuPerceivedSeverity
			MAX-ACCESS accessible-for-notify
			STATUS current
			DESCRIPTION
				"Identifies the severity of the alarm (e.g. Critical, Major, Normal)"
			::= { uqUifTrapEntry 3 }

		
		uqUifTrapTypeId OBJECT-TYPE
			SYNTAX Integer32 (1..2147483647)
			MAX-ACCESS accessible-for-notify
			STATUS current
			DESCRIPTION
				"An ID uniquely identifying the alarm or event on the OMC."
			::= { uqUifTrapEntry 4 }

		
		uqUifTrapNodeType OBJECT-TYPE
			SYNTAX INTEGER
				{
				nodeTypeBs(1),
				nodeTypeBsOmc(2)
				}
			MAX-ACCESS accessible-for-notify
			STATUS current
			DESCRIPTION
				"Type of node for the trap: BS or BS-OMC."
			::= { uqUifTrapEntry 6 }

		
		uqUifTrapNodeId OBJECT-TYPE
			SYNTAX SnmpAdminString
			MAX-ACCESS accessible-for-notify
			STATUS current
			DESCRIPTION
				"Uniquely identifieds the node for the trap. 
				For BS it is the BS Name which may contain unicode characters encoded using UTF-8.
				For BS-OMC it is an arbitrary string identifier.
				"
			::= { uqUifTrapEntry 7 }

		
		uqUifTrapFunctionBlock OBJECT-TYPE
			SYNTAX DisplayString
			MAX-ACCESS accessible-for-notify
			STATUS current
			DESCRIPTION
				"Human readable string identifying the location where the alarm occured 
				e.g. BS, BB, GPS, RF etc."
			::= { uqUifTrapEntry 8 }

		
		uqUifTrapMoreInfo OBJECT-TYPE
			SYNTAX DisplayString
			MAX-ACCESS accessible-for-notify
			STATUS current
			DESCRIPTION
				"A string describing the type of the alarm.
				The first 30 bytes should uniquely identify the BsOmc vendor alarm type."
			::= { uqUifTrapEntry 9 }

		
		uqUifTrapCause OBJECT-TYPE
			SYNTAX DisplayString
			MAX-ACCESS accessible-for-notify
			STATUS current
			DESCRIPTION
				"Describes the possible cause of the alarm."
			::= { uqUifTrapEntry 10 }

		
		uqUifTrapServiceState OBJECT-TYPE
			SYNTAX INTEGER
				{
				inService(1),
				outOfService(2)
				}
			MAX-ACCESS accessible-for-notify
			STATUS current
			DESCRIPTION
				"Service state of the function block."
			::= { uqUifTrapEntry 11 }

		
		uqUifTrapMaintenanceState OBJECT-TYPE
			SYNTAX INTEGER
				{
				mntOn(1),
				mntOff(2)
				}
			MAX-ACCESS accessible-for-notify
			STATUS current
			DESCRIPTION
				"Maintenance State of the BS."
			::= { uqUifTrapEntry 12 }

		
	
	END

--
-- FUJITSU-UIF-MIB.mib
--
