--
-- WMAN-IF-MIB-9-21_AirspanImplementation.mib
-- MIB generated by MG-SOFT Visual MIB Builder Version 5.0  Build 250
-- Wednesday, December 06, 2006 at 11:31:05
--

	WMAN-IF-ASDRAFT1-MIB DEFINITIONS ::= BEGIN
 
		IMPORTS
			ifIndex			
				FROM IF-MIB			
			InetAddressType, InetAddress			
				FROM INET-ADDRESS-MIB			
			SnmpAdminString			
				FROM SNMP-FRAMEWORK-MIB			
			transmission, Integer32, Unsigned32, Counter32, Counter64, 
			OBJECT-TYPE, MODULE-IDENTITY, NOTIFICATION-TYPE			
				FROM SNMPv2-SMI			
			MacAddress, DisplayString, TimeStamp, RowStatus, TruthValue, 
			DateAndTime, TEXTUAL-CONVENTION			
				FROM SNMPv2-TC;
	
	
		-- 1.3.6.1.2.1.10.184
		wmanIfMib MODULE-IDENTITY 
			LAST-UPDATED "200909171400Z"		-- September 17, 2009 at 14:00 GMT
			ORGANIZATION 
				"IEEE 802.16"
			CONTACT-INFO 
				"WG E-mail: stds-802-1@ieee.org
				WG Chair:  Roger B. Marks
				Postal:    IEEE
				E-mail:    r.b.marks@ieee.org
				
				TGf Chair: Phillip Barber
				Postal:    Broadband Mobile Technologies, Inc
				E-mail:    pbarber@broadbandmobiletech.com             
				
				Editor:    Joey Chou
				Postal:    Intel Corporation
				           5000 W. Chandler Blvd,
				           Chandler, AZ 85227, USA
				E-mail:    joey.chou@intel.com"
			DESCRIPTION 
				"This MIB Module defines managed objects for
				IEEE 802.16/REVd/D5-52004 based Subscriber Station
				and Base Station.  
				
				The version Draft 1A,1B,1C,... of this MIB is based on the revision published on Sept 21st 2004.
				It makes the essential syntax changes to allow proper implementation
				of the Draft 1 of the standard MIB.
				==================================
				Revision history:
		    September 17, 2009 at 14:00 GMT
				Draft 1M
				- Corrected value range for wmanIfSsPkmTEKGraceTime as per standard
			December 06, 2006 at 11:30 GMT
				Draft 1L
				- Deprecated wmanIfBsChMeasurementTable
				- Deprecated wmanIfCmnCpsServiceFlowTable
			May 05, 2006 at 12:43 GMT
				Draft 1K
				- added ieee802Dot16-2004Cor1 to wmanIfCmnOfdmMacVersion
			April 03, 2006 at 13:56 GMT
				Draft 1J
				- Module name changed to WMAN-IF-ASDRAFT1-MIB (Airspan implementation based on draft1 of the standard MIB)
				  to avoid confusion with standard WMAN-IF-MIB (currently draft6)
			October 03, 2005 at 15:37 GMT
				Draft 1H
				- Fixed definition of wmanIfCmnOfdmSubChReqRegionFull 
				  to work around the syntax error (compatible with 
				  previous MIB revisions)
			September 12, 2005 at 10:25 GMT
				Draft 1G
				- Changed definition of WmanIfClassifierBitMap
				  to match the standard where one bit corresponds 
				  to one subrule
			September 08, 2005 at 17:51 GMT
				Draft 1F
				- range for wmanIfCmnOfdmBsEIRP and wmanIfCmnOfdmInitRngMaxRSS 
				  changed to -32767..32768 (MIB error)
				- range for wmanIfCmnOfdmTTG changed to 0..65535 (corrigendum change)
				- row status removed from read-write tables: 
				  wmanIfBsConfigurationRowStatus, 
				  wmanIfSsConfigurationRowStatus, 
				  wmanIfCmnBsSsConfigurationRowStatus, 
				  wmanIfCmnOfdmUplinkChannelRowStatus
				  wmanIfCmnOfdmDownlinkChannelRowStatus,
				- row status removed from read-only tables: 
				  wmanIfCmnClassifierRuleRowStatus,
			July 29, 2005 at 17:34 GMT
				Draft 1E
				Fixed non printable character 
				in the commnet before wmanIfBsPacketCs
			July 07, 2005 at 12:11 GMT
				Draft 1D
				- added VariableMacAddress textual convention
				  to address issues with net-snmp indexing by MacAddress
				- VariableMacAddress used for:
				  wmanIfBsSsProvMacAddress
				  wmanIfBsSsPktMacAddr
				  wmanIfBsPkmAuthSsMacAddress
			June 22, 2005 at 15:17 GMT
				Draft 1C
				Changed SYNTAX of:
				wmanIfCmnOfdmUcdFecCodeType
				and wmanIfCmnOfdmDcdFecCodeType
				to use texxtual convetion:
				WmanIfOfdmFecCodeType
			May 13, 2005 at 15:25 GMT
				Draft 1B
				Changed max-access to not-accessible for:
				wmanIfBsSsPktMacAddr
				wmanIfBsSsIdIndex
				wmanIfBsChSsIdIndex
				wmanIfBsHistogramIndex
				wmanIfBsFecSsId
				wmanIfCmnCpsSfId
				wmanIfCmnSsIdIndex
				wmanIfCmnHistogramIndex
				wmanIfCmnSsFecSsId
			May 06, 2005 at 17:28 GMT
			DESCRIPTION 
				Draft 1A
				First numbered draft of Airspan Implementation of the Draft 1 of standard MIB.
				1. Changes to the MAX-ACCESS clauses in the following BS tables:
					wmanIfBsServiceClassTable (wmanIfBsQosScArqBlockSize)
					wmanIfBsSsPacketCounterTable (wmanIfBsSsResetCounterTime)
					wmanIfBsConfigurationTable (wmanIfBsClkCmpInterval, wmanIfBsConfigurationRowStatus)
				2. Changes to the MAX-ACCESS clauses in the following common tables:
					wmanIfCmnClassifierRuleTable (wmanIfCmnClassifierRuleBitMap)
					wmanIfCmnBsSsConfigurationRowStatus (wmanIfCmnBsSsConfigurationRowStatus)
					wmanIfCmnOfdmUplinkChannelTable (all columns)
					wmanIfCmnOfdmDownlinkChannelTable (all columns)
					wmanIfCmnOfdmUcdBurstProfileTable (all columns)
					wmanIfCmnOfdmDcdBurstProfileTable (all columns)
				3. Changes to the MAX-ACCESS clauses in the following SS tables:
					wmanIfSsConfigurationTable (wmanIfSsConfigurationRowStatus)
				4. Other changes:
					Fixed the naming of the Entry field in table wmanIfCmnOfdmDcdBurstProfileTable"
			::= { transmission 184 }

		
	
--
-- Textual conventions
--
	
		VariableMacAddress ::= TEXTUAL-CONVENTION
			DISPLAY-HINT 
				"1x:"
			STATUS current
			DESCRIPTION 
				"Special variant of MacAddress textual convention to force 
				agent to accept/use size of the string when the MacAddress 
				is used as an index.
				This variant defines MacAddress as OCTET STRING with variable length.
				
				Represents an 802 MAC address represented in the
				`canonical' order defined by IEEE 802.1a, i.e., as if it
				were transmitted least significant bit first, even though
				802.5 (in contrast to other 802.x protocols) requires MAC
				addresses to be transmitted most significant bit first.
				"
			SYNTAX OCTET STRING (SIZE (5..6))

--  Textual Conventions
		WmanIfSfSchedulingType ::= TEXTUAL-CONVENTION
			STATUS current
			DESCRIPTION 
				"The scheduling service provided by a SC for an
				upstream service flow. If the parameter is omitted
				from an upstream QOS Parameter Set, this object takes
				the value of bestEffort (2). This parameter must be
				reported as undefined (1) for downstream QOS Parameter
				Sets."
			SYNTAX INTEGER
				{
				undefined(1),
				bestEffort(2),
				nonRealTimePollingService(3),
				realTimePollingService(4),
				unsolictedGrantService(6)
				}

		WmanIfClassifierBitMap ::= TEXTUAL-CONVENTION
			STATUS current
			DESCRIPTION 
				"A bit of of this object is set to 1 if the parameter
				indicated by the comment was present in the classifier
				encoding, and 0 otherwise.
				Note: that BITS are encoded most significant bit first,
				so that if e.g. bits 6 and 7 are set, this object is
				encoded as the octet string '030000'H."
			SYNTAX BITS
				{
				priority(0),
				ipTos(1),
				ipProtocol(2),
				ipMaskedSrcAddr(3),
				ipMaskedDestAddr(4),
				srcPort(5),
				destPort(6),
				destMacAddr(7),
				srcMacAddr(8),
				ethernetProtocol(9),
				userPriority(10),
				vlanId(11)
				}

		WmanIfOfdmFecCodeType ::= TEXTUAL-CONVENTION
			STATUS current
			DESCRIPTION 
				"FEC code type and modulation type"
			REFERENCE 
				"Table 356 and Table 362 in IEEE 802.16-2004"
			SYNTAX INTEGER
				{
				bpskCc1Over2(0),
				qpskRsCcCc1Over2(1),
				qpskRsCcCc3Over4(2),
				sixteenQamRsCcCc1Over2(3),
				sixteenQamRsCcCc3Over4(4),
				sixtyFourQamRsCcCc2Over3(5),
				sixtyFourQamRsCcCc3Over4(6),
				qpskBtc1Over2(7),
				qpskBtc3Over4(8),
				sixteenQamBtc3Over4(9),
				sixteenQamBtc4Over5(10),
				sixtyFourQamBtc2Over3(11),
				sixtyFourQamBtc5Over6(12),
				qpskCtc1Over2(13),
				qpskCtc2Over3(14),
				qpskCtc3Over4(15),
				sixteenQamCtc1Over2(16),
				sixteenQamCtc3Over4(17),
				sixtyFourQamCtc2Over3(18),
				sixtyFourQamCtc3Over4(19)
				}

	
--
-- Node definitions
--
	
		-- 1.3.6.1.2.1.10.184.1
		wmanIfMibObjects OBJECT IDENTIFIER ::= { wmanIfMib 1 }

		
		-- 1.3.6.1.2.1.10.184.1.1
		wmanIfBsObjects OBJECT IDENTIFIER ::= { wmanIfMibObjects 1 }

		
-- BS object group containing tables and objects to be implemented in 
-- the Base station
-- 
-- wmanIfBsPacketCs contain the Base Station Packet Convergence Sublayer
-- objects
		-- 1.3.6.1.2.1.10.184.1.1.1
		wmanIfBsPacketCs OBJECT IDENTIFIER ::= { wmanIfBsObjects 1 }

		
		-- 1.3.6.1.2.1.10.184.1.1.1.1
		wmanIfBsProvisionedSfTable OBJECT-TYPE
			SYNTAX SEQUENCE OF WmanIfBsProvisionedSfEntry
			MAX-ACCESS not-accessible
			STATUS current
			DESCRIPTION
				"This table is doubly indexed (SS MAC address, SF ID) and
				contains pre-provisioned service flow profiles, Per SS.
				These connection parameters shall be provisioned for the SS
				using DSA messages. NMS shall pre-provisioning the service
				class table - wmanIfBsServiceClassTable by using
				wmanIfBsServiceClassIndex, and packet classifier rule table
				- wmanIfBsClassifierRuleTable by using wmanIfBsSfId"
			REFERENCE
				"Section 6.4.13 in IEEE 802.16REVd/D5-2004"
			::= { wmanIfBsPacketCs 1 }

		
		-- 1.3.6.1.2.1.10.184.1.1.1.1.1
		wmanIfBsProvisionedSfEntry OBJECT-TYPE
			SYNTAX WmanIfBsProvisionedSfEntry
			MAX-ACCESS not-accessible
			STATUS current
			DESCRIPTION
				"This table provides one row for each service flow been
				pre-provisioned by NMS."
			INDEX { wmanIfBsSsProvMacAddress, wmanIfBsSfId }
			::= { wmanIfBsProvisionedSfTable 1 }

		
		WmanIfBsProvisionedSfEntry ::=
			SEQUENCE { 
				wmanIfBsSfId
					Unsigned32,
				wmanIfBsSsProvMacAddress
					VariableMacAddress,
				wmanIfBsSfDirection
					INTEGER,
				wmanIfBsServiceClassIndex
					INTEGER,
				wmanIfBsServiceClassName
					DisplayString,
				wmanIfBsSfState
					INTEGER,
				wmanIfBsSfProvisionedTime
					TimeStamp,
				wmanIfBsProvisionedSfRowStatus
					RowStatus
			 }

		-- 1.3.6.1.2.1.10.184.1.1.1.1.1.1
		wmanIfBsSfId OBJECT-TYPE
			SYNTAX Unsigned32 (1..4294967295)
			MAX-ACCESS not-accessible
			STATUS current
			DESCRIPTION
				"A 32 bit quantity that uniquely identifies a service flow
				to both the subscriber station and base station (BS)."
			::= { wmanIfBsProvisionedSfEntry 1 }

		
		-- 1.3.6.1.2.1.10.184.1.1.1.1.1.2
		wmanIfBsSsProvMacAddress OBJECT-TYPE
			SYNTAX VariableMacAddress
			MAX-ACCESS not-accessible
			STATUS current
			DESCRIPTION
				"The MAC address of the SS, where the service flow resides.
				It can be used as the index to associate service flows
				with the SS."
			::= { wmanIfBsProvisionedSfEntry 2 }

		
		-- 1.3.6.1.2.1.10.184.1.1.1.1.1.3
		wmanIfBsSfDirection OBJECT-TYPE
			SYNTAX INTEGER
				{
				downstream(1),
				upstream(2)
				}
			MAX-ACCESS read-create
			STATUS current
			DESCRIPTION
				"An attribute indiating the service flow is downstream or
				upstream."
			::= { wmanIfBsProvisionedSfEntry 3 }

		
		-- 1.3.6.1.2.1.10.184.1.1.1.1.1.4
		wmanIfBsServiceClassIndex OBJECT-TYPE
			SYNTAX INTEGER
			MAX-ACCESS read-create
			STATUS current
			DESCRIPTION
				"The index in wmanIfBsServiceClassTable describing the
				service class or QoS parameters for such service flow.
				If no associated entry in wmanIfBsServiceClassTable
				exists, this object returns a value of zero."
			::= { wmanIfBsProvisionedSfEntry 4 }

		
		-- 1.3.6.1.2.1.10.184.1.1.1.1.1.5
		wmanIfBsServiceClassName OBJECT-TYPE
			SYNTAX DisplayString (SIZE (1..32))
			MAX-ACCESS read-create
			STATUS current
			DESCRIPTION
				"Refers to the Service Class Name"
			REFERENCE
				"Section 11.13.7 in IEEE 802.16REVd/D5-2004"
			::= { wmanIfBsProvisionedSfEntry 5 }

		
		-- 1.3.6.1.2.1.10.184.1.1.1.1.1.6
		wmanIfBsSfState OBJECT-TYPE
			SYNTAX INTEGER
				{
				provisioned(1),
				admitted(2),
				active(3)
				}
			MAX-ACCESS read-create
			STATUS current
			DESCRIPTION
				"wmanIfBsSfState determines the requested state of a service
				flow. 
				- provisioned state: A service flow is provisioned but
				  not resource is reserved yet
				- admitted state: service flow has resources reserved.
				- active state: has resources committed by the BS (e.g., is
				  actively sending maps containing unsolicited grants for a
				  UGS-based service flow),"
			REFERENCE
				"Section 6.4.13.6, in IEEE 802.16REVd/D5-2004"
			::= { wmanIfBsProvisionedSfEntry 6 }

		
		-- 1.3.6.1.2.1.10.184.1.1.1.1.1.7
		wmanIfBsSfProvisionedTime OBJECT-TYPE
			SYNTAX TimeStamp
			MAX-ACCESS read-create
			STATUS current
			DESCRIPTION
				"Indicates the date and time when the service flow is
				provisioned."
			::= { wmanIfBsProvisionedSfEntry 7 }

		
		-- 1.3.6.1.2.1.10.184.1.1.1.1.1.8
		wmanIfBsProvisionedSfRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { wmanIfBsProvisionedSfEntry 8 }

		
		-- 1.3.6.1.2.1.10.184.1.1.1.2
		wmanIfBsServiceClassTable OBJECT-TYPE
			SYNTAX SEQUENCE OF WmanIfBsServiceClassEntry
			MAX-ACCESS not-accessible
			STATUS current
			DESCRIPTION
				"This table is provisioned and is indexed by
				wmanIfBsQoSProfileIndex. Each entry of the table contains
				corresponding service flow characteristic attributes
				(e.g. QoS parameter set). The value of
				wmanIfBsQoSProfileIndex is obtained from 
				wmanIfBsServiceClassIndex in wmanIfBsProvisionedSfTable"
			REFERENCE
				"Section 6.4.13.4 in IEEE 802.16REVd/D5-2004"
			::= { wmanIfBsPacketCs 2 }

		
		-- 1.3.6.1.2.1.10.184.1.1.1.2.1
		wmanIfBsServiceClassEntry OBJECT-TYPE
			SYNTAX WmanIfBsServiceClassEntry
			MAX-ACCESS not-accessible
			STATUS current
			DESCRIPTION
				"This table provides one row for each service class"
			INDEX { wmanIfBsQoSProfileIndex }
			::= { wmanIfBsServiceClassTable 1 }

		
		WmanIfBsServiceClassEntry ::=
			SEQUENCE { 
				wmanIfBsQoSProfileIndex
					INTEGER,
				wmanIfBsQosServiceClassName
					DisplayString,
				wmanIfBsQoSTrafficPriority
					INTEGER,
				wmanIfBsQoSMaxSustainedRate
					INTEGER,
				wmanIfBsQoSMaxTrafficBurst
					INTEGER,
				wmanIfBsQoSMinReservedRate
					INTEGER,
				wmanIfBsQoSToleratedJitter
					INTEGER,
				wmanIfBsQoSMaxLatency
					INTEGER,
				wmanIfBsQoSFixedVsVariableSduInd
					INTEGER,
				wmanIfBsQoSSduSize
					INTEGER,
				wmanIfBsQosScSchedulingType
					WmanIfSfSchedulingType,
				wmanIfBsQosScArqEnable
					TruthValue,
				wmanIfBsQosScArqWindowSize
					INTEGER,
				wmanIfBsQosScArqFragmentLifetime
					INTEGER,
				wmanIfBsQosScArqSyncLossTimeout
					INTEGER,
				wmanIfBsQosScArqDeliverInOrder
					TruthValue,
				wmanIfBsQosScArqRxPurgeTimeout
					INTEGER,
				wmanIfBsQosScArqBlockSize
					INTEGER,
				wmanIfBsQosSCMinRsvdTolerableRate
					INTEGER,
				wmanIfBsQoSReqTxPolicy
					BITS,
				wmanIfBsQoSServiceClassRowStatus
					RowStatus
			 }

		-- 1.3.6.1.2.1.10.184.1.1.1.2.1.1
		wmanIfBsQoSProfileIndex OBJECT-TYPE
			SYNTAX INTEGER (1..1000)
			MAX-ACCESS not-accessible
			STATUS current
			DESCRIPTION
				"The index value which uniquely identifies an entry
				in the wmanIfBsServiceClassTable"
			::= { wmanIfBsServiceClassEntry 1 }

		
		-- 1.3.6.1.2.1.10.184.1.1.1.2.1.2
		wmanIfBsQosServiceClassName OBJECT-TYPE
			SYNTAX DisplayString (SIZE (2..128))
			MAX-ACCESS read-create
			STATUS current
			DESCRIPTION
				"Refers to the Service Class Name"
			REFERENCE
				"Section 11.13.3 in IEEE 802.16REVd/D5-2004"
			::= { wmanIfBsServiceClassEntry 2 }

		
		-- 1.3.6.1.2.1.10.184.1.1.1.2.1.3
		wmanIfBsQoSTrafficPriority OBJECT-TYPE
			SYNTAX INTEGER (0..7)
			MAX-ACCESS read-create
			STATUS current
			DESCRIPTION
				"The value of this parameter specifies the priority
				assigned to a service flow. For uplink service flows,
				the BS should use this parameter when determining
				precedence in request service and grant generation,
				and the SS shall preferentially select contention
				Request opportunities for Priority Request CIDs
				based on this priority. Higher numbers indicate higher
				priority"
			REFERENCE
				"Section 11.13.7 in IEEE 802.16REVd/D5-2004"
			::= { wmanIfBsServiceClassEntry 3 }

		
		-- 1.3.6.1.2.1.10.184.1.1.1.2.1.4
		wmanIfBsQoSMaxSustainedRate OBJECT-TYPE
			SYNTAX INTEGER
			UNITS "bps"
			MAX-ACCESS read-create
			STATUS current
			DESCRIPTION
				"This parameter defines the peak information rate
				of the service. The rate is expressed in bits per
				second and pertains to the SDUs at the input to
				the system."
			REFERENCE
				"Section 11.13.8 in IEEE 802.16REVd/D5-2004"
			::= { wmanIfBsServiceClassEntry 4 }

		
		-- 1.3.6.1.2.1.10.184.1.1.1.2.1.5
		wmanIfBsQoSMaxTrafficBurst OBJECT-TYPE
			SYNTAX INTEGER
			UNITS "byte"
			MAX-ACCESS read-create
			STATUS current
			DESCRIPTION
				"This parameter defines the maximum burst size that
				must be accommodated for the service."
			REFERENCE
				"Section 11.13.9 in IEEE 802.16REVd/D5-2004"
			::= { wmanIfBsServiceClassEntry 5 }

		
		-- 1.3.6.1.2.1.10.184.1.1.1.2.1.6
		wmanIfBsQoSMinReservedRate OBJECT-TYPE
			SYNTAX INTEGER
			UNITS "bps"
			MAX-ACCESS read-create
			STATUS current
			DESCRIPTION
				"This parameter specifies the minimum rate reserved
				for this service flow."
			REFERENCE
				"Section 11.13.10 in IEEE 802.16REVd/D5-2004"
			::= { wmanIfBsServiceClassEntry 6 }

		
		-- 1.3.6.1.2.1.10.184.1.1.1.2.1.7
		wmanIfBsQoSToleratedJitter OBJECT-TYPE
			SYNTAX INTEGER
			UNITS "millisecond"
			MAX-ACCESS read-create
			STATUS current
			DESCRIPTION
				"This parameter defines the Maximum delay 
				variation (jitter) for the connection."
			REFERENCE
				"Section 11.13.15 in IEEE 802.16REVd/D5-2004"
			::= { wmanIfBsServiceClassEntry 7 }

		
		-- 1.3.6.1.2.1.10.184.1.1.1.2.1.8
		wmanIfBsQoSMaxLatency OBJECT-TYPE
			SYNTAX INTEGER
			UNITS "millisecond"
			MAX-ACCESS read-create
			STATUS current
			DESCRIPTION
				"The value of this parameter specifies the maximum
				latency between the reception of a packet by the BS
				or SS on its network interface and the forwarding
				of the packet to its RF Interface."
			REFERENCE
				"Section 11.13.16 in IEEE 802.16REVd/D5-2004"
			::= { wmanIfBsServiceClassEntry 8 }

		
		-- 1.3.6.1.2.1.10.184.1.1.1.2.1.9
		wmanIfBsQoSFixedVsVariableSduInd OBJECT-TYPE
			SYNTAX INTEGER
				{
				variableLength(0),
				fixedLength(1)
				}
			MAX-ACCESS read-create
			STATUS current
			DESCRIPTION
				"The value of this parameter specifies whether the SDUs
				on the service flow are variable-length (0) or 
				fixed-length (1). The parameter is used only if
				packing is on for the service flow. The default value
				is 0, i.e.,variable-length SDUs."
			REFERENCE
				"Section 11.13.15 in IEEE 802.16REVd/D5-2004"
			DEFVAL { 0 }
			::= { wmanIfBsServiceClassEntry 9 }

		
		-- 1.3.6.1.2.1.10.184.1.1.1.2.1.10
		wmanIfBsQoSSduSize OBJECT-TYPE
			SYNTAX INTEGER
			UNITS "byte"
			MAX-ACCESS read-create
			STATUS current
			DESCRIPTION
				"The value of this parameter specifies the length of the
				SDU for a fixed-length SDU service flow. This parameter
				is used only if packing is on and the service flow is
				indicated as carrying fixed-length SDUs. The default
				value is 49 bytes, i.e., VC-switched ATM cells with PHS.
				The parameter is relevant for both ATM and Packet
				Convergence Sublayers."
			REFERENCE
				"Section 11.13.17 in IEEE 802.16REVd/D4-2004"
			DEFVAL { 49 }
			::= { wmanIfBsServiceClassEntry 10 }

		
		-- 1.3.6.1.2.1.10.184.1.1.1.2.1.11
		wmanIfBsQosScSchedulingType OBJECT-TYPE
			SYNTAX WmanIfSfSchedulingType
			MAX-ACCESS read-create
			STATUS current
			DESCRIPTION
				"Specifies the upstream scheduling service used for
				upstream service flow. If the referenced parameter
				is not present in the corresponding 802.16 QOS
				Parameter Set of an upstream service flow, the
				default value of this object is bestEffort(2)."
			REFERENCE
				"Section 11.13.13 in IEEE 802.16REVd/D5-2004"
			DEFVAL { 2 }
			::= { wmanIfBsServiceClassEntry 11 }

		
		-- 1.3.6.1.2.1.10.184.1.1.1.2.1.12
		wmanIfBsQosScArqEnable OBJECT-TYPE
			SYNTAX TruthValue
			MAX-ACCESS read-create
			STATUS current
			DESCRIPTION
				"True(1) ARQ enabling is requested for the connection."
			REFERENCE
				"Section 11.13.20 in IEEE 802.16REVd/D5-2004"
			::= { wmanIfBsServiceClassEntry 12 }

		
		-- 1.3.6.1.2.1.10.184.1.1.1.2.1.13
		wmanIfBsQosScArqWindowSize OBJECT-TYPE
			SYNTAX INTEGER (1..1024)
			MAX-ACCESS read-create
			STATUS current
			DESCRIPTION
				"Indicates the maximum number of unacknowledged 
				fragments at any time."
			REFERENCE
				"Section 11.13.20 in IEEE 802.16REVd/D5-2004"
			::= { wmanIfBsServiceClassEntry 13 }

		
		-- 1.3.6.1.2.1.10.184.1.1.1.2.1.14
		wmanIfBsQosScArqFragmentLifetime OBJECT-TYPE
			SYNTAX INTEGER (0..65535)
			UNITS "10 us"
			MAX-ACCESS read-create
			STATUS current
			DESCRIPTION
				"The maximum time interval an ARQ fragment will be
				managed by the transmitter ARQ machine, once
				initial transmission of the fragment has occured.
				If transmission or retransmission of the fragment
				is not acknowledged by the receiver before the 
				time limit is reached, the fragmnet is discarded.
				A value of 0 means Infinite."
			REFERENCE
				"Section 11.13.20 in IEEE 802.16REVd/D5-2004"
			DEFVAL { 0 }
			::= { wmanIfBsServiceClassEntry 14 }

		
		-- 1.3.6.1.2.1.10.184.1.1.1.2.1.15
		wmanIfBsQosScArqSyncLossTimeout OBJECT-TYPE
			SYNTAX INTEGER (0..65535)
			UNITS "10 us"
			MAX-ACCESS read-create
			STATUS current
			DESCRIPTION
				"The maximum interval before declaring a loss
				of synchronization of the sender and receiver
				state machines. A value of 0 means Infinite."
			REFERENCE
				"Section 11.13.20 in IEEE 802.16REVd/D5-2004"
			DEFVAL { 0 }
			::= { wmanIfBsServiceClassEntry 15 }

		
		-- 1.3.6.1.2.1.10.184.1.1.1.2.1.16
		wmanIfBsQosScArqDeliverInOrder OBJECT-TYPE
			SYNTAX TruthValue
			MAX-ACCESS read-create
			STATUS current
			DESCRIPTION
				"Indicates whether or not data is to be delivered
				by the receiving MAC to its client application
				in the order in which data was handed off to the
				originating MAC."
			REFERENCE
				"Section 11.13.20 in IEEE 802.16REVd/D5-2004"
			::= { wmanIfBsServiceClassEntry 16 }

		
		-- 1.3.6.1.2.1.10.184.1.1.1.2.1.17
		wmanIfBsQosScArqRxPurgeTimeout OBJECT-TYPE
			SYNTAX INTEGER (0..65535)
			UNITS "10 us"
			MAX-ACCESS read-create
			STATUS current
			DESCRIPTION
				"Indicates the time interval the ARQ window is advanced
				after a fragment is received. A value of 0 means
				Infinite."
			REFERENCE
				"Section 11.13.20 in IEEE 802.16REVd/D5-2004"
			DEFVAL { 0 }
			::= { wmanIfBsServiceClassEntry 17 }

		
		-- 1.3.6.1.2.1.10.184.1.1.1.2.1.18
		wmanIfBsQosScArqBlockSize OBJECT-TYPE
			SYNTAX INTEGER (1..2040)
			UNITS "byte"
			MAX-ACCESS read-create
			STATUS current
			DESCRIPTION
				"This value of this parameter specifies the size of an
				ARQ block. This parameter shall be established by
				negotiation during the connection creation dialog."
			REFERENCE
				"Section 11.13.18.8 in IEEE 802.16REVd/D5-2004"
			::= { wmanIfBsServiceClassEntry 18 }

		
		-- 1.3.6.1.2.1.10.184.1.1.1.2.1.19
		wmanIfBsQosSCMinRsvdTolerableRate OBJECT-TYPE
			SYNTAX INTEGER
			UNITS "bps"
			MAX-ACCESS read-create
			STATUS current
			DESCRIPTION
				"Minimum Tolerable Traffic Rate = R (bits/sec) with
				time base T(sec) means the following. Let S denote
				additional demand accumulated at the MAC SAP of the
				transmitter during an arbitrary time interval of the
				length T. Then the amount of data forwarded at the
				receiver to CS (in bits) during this interval should
				be not less than min {S, R * T}."
			REFERENCE
				"Section 11.13.11 in IEEE 802.16REVd/D5-2004"
			::= { wmanIfBsServiceClassEntry 19 }

		
		-- 1.3.6.1.2.1.10.184.1.1.1.2.1.20
		wmanIfBsQoSReqTxPolicy OBJECT-TYPE
			SYNTAX BITS
				{
				noBroadcastBwReq(0),
				reserved1(1),
				noPiggybackReq(2),
				noFragmentData(3),
				noPHS(4),
				noSduPacking(5),
				noCrc(6),
				reserved2(7)
				}
			MAX-ACCESS read-create
			STATUS current
			DESCRIPTION
				"The value of this parameter provides the capability to
				specify certain attributes for the associated service
				flow. An attribute is enabled by setting the
				corresponding bit position to 1."
			REFERENCE
				"Section 11.13.12 in IEEE 802.16REVd/D5-2004"
			::= { wmanIfBsServiceClassEntry 20 }

		
		-- 1.3.6.1.2.1.10.184.1.1.1.2.1.21
		wmanIfBsQoSServiceClassRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { wmanIfBsServiceClassEntry 21 }

		
		-- 1.3.6.1.2.1.10.184.1.1.1.3
		wmanIfBsClassifierRuleTable OBJECT-TYPE
			SYNTAX SEQUENCE OF WmanIfBsClassifierRuleEntry
			MAX-ACCESS not-accessible
			STATUS current
			DESCRIPTION
				"This table contains packet classifier rules associated
				with service flows."
			REFERENCE
				"Section 11.13.22.3.4 in IEEE 802.16REVd/D5-2004"
			::= { wmanIfBsPacketCs 3 }

		
		-- 1.3.6.1.2.1.10.184.1.1.1.3.1
		wmanIfBsClassifierRuleEntry OBJECT-TYPE
			SYNTAX WmanIfBsClassifierRuleEntry
			MAX-ACCESS not-accessible
			STATUS current
			DESCRIPTION
				"This table provides one row for each packet classifier 
				rule, and is indexed by wmanIfBsSfId and
				wmanIfBsClassifierRuleIndex. wmanIfBsSfIndex
				identifies the service flow, while
				wmanIfBsClassifierRuleIndex identifies the packet
				classifier rule."
			INDEX { wmanIfBsSfIndex, wmanIfBsClassifierRuleIndex }
			::= { wmanIfBsClassifierRuleTable 1 }

		
		WmanIfBsClassifierRuleEntry ::=
			SEQUENCE { 
				wmanIfBsSfIndex
					Unsigned32,
				wmanIfBsClassifierRuleIndex
					Unsigned32,
				wmanIfBsClassifierRulePriority
					INTEGER,
				wmanIfBsClassifierRuleIpTosLow
					OCTET STRING,
				wmanIfBsClassifierRuleIpTosHigh
					OCTET STRING,
				wmanIfBsClassifierRuleIpTosMask
					OCTET STRING,
				wmanIfBsClassifierRuleIpProtocol
					Integer32,
				wmanIfBsClassifierRuleIpAddressType
					InetAddressType,
				wmanIfBsClassifierRuleIpSourceAddr
					InetAddress,
				wmanIfBsClassifierRuleIpSourceMask
					InetAddress,
				wmanIfBsClassifierRuleIpDestAddr
					InetAddress,
				wmanIfBsClassifierRuleIpDestMask
					InetAddress,
				wmanIfBsClassifierRuleSourcePortStart
					Integer32,
				wmanIfBsClassifierRuleSourcePortEnd
					Integer32,
				wmanIfBsClassifierRuleDestPortStart
					Integer32,
				wmanIfBsClassifierRuleDestPortEnd
					Integer32,
				wmanIfBsClassifierRuleDestMacAddr
					MacAddress,
				wmanIfBsClassifierRuleDestMacMask
					MacAddress,
				wmanIfBsClassifierRuleSourceMacAddr
					MacAddress,
				wmanIfBsClassifierRuleSourceMacMask
					MacAddress,
				wmanIfBsClassifierRuleEnetProtocolType
					INTEGER,
				wmanIfBsClassifierRuleEnetProtocol
					Integer32,
				wmanIfBsClassifierRuleUserPriLow
					Integer32,
				wmanIfBsClassifierRuleUserPriHigh
					Integer32,
				wmanIfBsClassifierRuleVlanId
					Integer32,
				wmanIfBsClassifierRuleState
					INTEGER,
				wmanIfBsClassifierRulePkts
					Counter64,
				wmanIfBSClassifierRuleBitMap
					WmanIfClassifierBitMap,
				wmanIfBsClassifierRuleRowStatus
					RowStatus
			 }

		-- 1.3.6.1.2.1.10.184.1.1.1.3.1.1
		wmanIfBsSfIndex OBJECT-TYPE
			SYNTAX Unsigned32 (1..4294967295)
			MAX-ACCESS not-accessible
			STATUS current
			DESCRIPTION
				"A 32 bit quantity that uniquely identifies a service flow
				to both the subscriber station and base station (BS)."
			::= { wmanIfBsClassifierRuleEntry 1 }

		
		-- 1.3.6.1.2.1.10.184.1.1.1.3.1.2
		wmanIfBsClassifierRuleIndex OBJECT-TYPE
			SYNTAX Unsigned32 (1..4294967295)
			MAX-ACCESS not-accessible
			STATUS current
			DESCRIPTION
				"An index is assigned to a classifier in BS classifiers
				table"
			::= { wmanIfBsClassifierRuleEntry 2 }

		
		-- 1.3.6.1.2.1.10.184.1.1.1.3.1.3
		wmanIfBsClassifierRulePriority OBJECT-TYPE
			SYNTAX INTEGER (0..255)
			MAX-ACCESS read-create
			STATUS current
			DESCRIPTION
				"The value specifies the priority for the Classifier, which
				is used for determining the order of the Classifier. A
				higher value indicates higher priority. Classifiers may
				have priorities in the range 0..255."
			REFERENCE
				"Section 11.13.19.3.4.1 in IEEE 802.16REVd/D4-2004"
			DEFVAL { 0 }
			::= { wmanIfBsClassifierRuleEntry 3 }

		
		-- 1.3.6.1.2.1.10.184.1.1.1.3.1.4
		wmanIfBsClassifierRuleIpTosLow OBJECT-TYPE
			SYNTAX OCTET STRING (SIZE (1))
			MAX-ACCESS read-create
			STATUS current
			DESCRIPTION
				"The low value of a range of TOS byte values. If the
				referenced parameter is not present in a classifier, this
				object reports the value of 0."
			REFERENCE
				"Section 11.13.19.3.4.2 in IEEE 802.16REVd/D5-2004"
			::= { wmanIfBsClassifierRuleEntry 4 }

		
		-- 1.3.6.1.2.1.10.184.1.1.1.3.1.5
		wmanIfBsClassifierRuleIpTosHigh OBJECT-TYPE
			SYNTAX OCTET STRING (SIZE (1))
			MAX-ACCESS read-create
			STATUS current
			DESCRIPTION
				"The 8-bit high value of a range of TOS byte values.
				If the referenced parameter is not present in a classifier,
				this object reports the value of 0."
			REFERENCE
				"Section 11.13.19.3.4.2 in IEEE 802.16REVd/D5-2004"
			::= { wmanIfBsClassifierRuleEntry 5 }

		
		-- 1.3.6.1.2.1.10.184.1.1.1.3.1.6
		wmanIfBsClassifierRuleIpTosMask OBJECT-TYPE
			SYNTAX OCTET STRING (SIZE (1))
			MAX-ACCESS read-create
			STATUS current
			DESCRIPTION
				"The mask value is bitwise ANDed with TOS byte in an IP
				packet and this value is used check range checking of
				TosLow and TosHigh. If the referenced parameter is not
				present in a classifier, this object reports the value
				of 0."
			REFERENCE
				"Section 11.13.19.3.4.2 in IEEE 802.16REVd/D5-2004"
			::= { wmanIfBsClassifierRuleEntry 6 }

		
		-- 1.3.6.1.2.1.10.184.1.1.1.3.1.7
		wmanIfBsClassifierRuleIpProtocol OBJECT-TYPE
			SYNTAX Integer32 (0..255)
			MAX-ACCESS read-create
			STATUS current
			DESCRIPTION
				"This object indicates the value of the IP Protocol field
				required for IP packets to match this rule. If the
				referenced parameter is not present in a classifier, this
				object reports the value of 0."
			REFERENCE
				"Section 11.13.19.3.4.3 in IEEE 802.16REVd/D5-2004"
			::= { wmanIfBsClassifierRuleEntry 7 }

		
		-- 1.3.6.1.2.1.10.184.1.1.1.3.1.8
		wmanIfBsClassifierRuleIpAddressType OBJECT-TYPE
			SYNTAX InetAddressType
			MAX-ACCESS read-create
			STATUS current
			DESCRIPTION
				"The type of the internet address for
				wmanIfBsClassifierRuleIpSourceAddr,
				wmanIfBsClassifierRuleIpSourceMask,
				wmanIfBsClassifierRuleIpDestAddr, and
				wmanIfBsClassifierRuleIpDestMask.
				If the referenced parameter is not present in a classifier,
				this object reports the value of ipv4(1)."
			::= { wmanIfBsClassifierRuleEntry 8 }

		
		-- 1.3.6.1.2.1.10.184.1.1.1.3.1.9
		wmanIfBsClassifierRuleIpSourceAddr OBJECT-TYPE
			SYNTAX InetAddress
			MAX-ACCESS read-create
			STATUS current
			DESCRIPTION
				"This object specifies the value of the IP Source Address
				required for packets to match this rule. An IP packet
				matches the rule when the packet ip source address bitwise
				ANDed with the wmanIfBsClassifierRuleIpSourceMask value
				equals the wmanIfBsClassifierRuleIpSourceAddr value.
				If the referenced parameter is not present n a classifier,
				this object reports the value of 0.0.0.0."
			REFERENCE
				"Section 11.13.19.3.4.4 in IEEE 802.16REVd/D5-2004"
			::= { wmanIfBsClassifierRuleEntry 9 }

		
		-- 1.3.6.1.2.1.10.184.1.1.1.3.1.10
		wmanIfBsClassifierRuleIpSourceMask OBJECT-TYPE
			SYNTAX InetAddress
			MAX-ACCESS read-create
			STATUS current
			DESCRIPTION
				"This object specifies which bits of a packet's IP Source
				Address that are compared to match this rule. An IP packet
				matches the rule when the packet source address bitwise
				ANDed with the
				wmanIfBsClassifierRuleIpSourceMask value equals the
				wmanIfBsClassifierRuleIpSourceAddr value.
				If the referenced parameter is not present in a classifier,
				this object reports the value of 0.0.0.0."
			REFERENCE
				"Section 11.13.19.3.4.4 in IEEE 802.16REVd/D5-2004"
			::= { wmanIfBsClassifierRuleEntry 10 }

		
		-- 1.3.6.1.2.1.10.184.1.1.1.3.1.11
		wmanIfBsClassifierRuleIpDestAddr OBJECT-TYPE
			SYNTAX InetAddress
			MAX-ACCESS read-create
			STATUS current
			DESCRIPTION
				"This object specifies the value of the IP Destination
				Address required for packets to match this rule. An IP
				packet matches the rule when the packet IP destination
				address bitwise ANDed with the
				wmanIfBsClassifierRuleIpDestMask value equals the
				wmanIfBsClassifierRuleIpDestAddr value.
				If the referenced parameter is not present in a 
				classifier, this object reports the value of 0.0.0.0."
			REFERENCE
				"Section 11.13.19.3.4.5 in IEEE 802.16REVd/D5-2004"
			::= { wmanIfBsClassifierRuleEntry 11 }

		
		-- 1.3.6.1.2.1.10.184.1.1.1.3.1.12
		wmanIfBsClassifierRuleIpDestMask OBJECT-TYPE
			SYNTAX InetAddress
			MAX-ACCESS read-create
			STATUS current
			DESCRIPTION
				"This object specifies which bits of a packet's IP 
				Destination Address that are compared to match this rule.
				An IP packet matches the rule when the packet destination
				address bitwise ANDed with the
				wmanIfBsClassifierRuleIpDestMask value equals the
				wmanIfBsClassifierRuleIpDestAddr value.
				If the referenced parameter is not present in a classifier
				, this object reports the value of 0.0.0.0."
			REFERENCE
				"Section 11.13.19.3.4.5 in IEEE 802.16REVd/D5-2004"
			::= { wmanIfBsClassifierRuleEntry 12 }

		
		-- 1.3.6.1.2.1.10.184.1.1.1.3.1.13
		wmanIfBsClassifierRuleSourcePortStart OBJECT-TYPE
			SYNTAX Integer32 (0..65535)
			MAX-ACCESS read-create
			STATUS current
			DESCRIPTION
				"This object specifies the low end inclusive range of
				TCP/UDP source port numbers to which a packet is compared.
				This object is irrelevant for non-TCP/UDP IP packets.
				If the referenced parameter is not present in a
				classifier, this object reports the value of 0."
			REFERENCE
				"Section 11.13.19.3.4.6 in IEEE 802.16REVd/D5-2004"
			::= { wmanIfBsClassifierRuleEntry 13 }

		
		-- 1.3.6.1.2.1.10.184.1.1.1.3.1.14
		wmanIfBsClassifierRuleSourcePortEnd OBJECT-TYPE
			SYNTAX Integer32 (0..65535)
			MAX-ACCESS read-create
			STATUS current
			DESCRIPTION
				"This object specifies the high end inclusive range of
				TCP/UDP source port numbers to which a packet is compared.
				This object is irrelevant for non-TCP/UDP IP packets.
				If the referenced parameter is not present in a classifier,
				this object reports the value of 65535."
			REFERENCE
				"Section 11.13.19.3.4.6 in IEEE 802.16REVd/D5-2004"
			::= { wmanIfBsClassifierRuleEntry 14 }

		
		-- 1.3.6.1.2.1.10.184.1.1.1.3.1.15
		wmanIfBsClassifierRuleDestPortStart OBJECT-TYPE
			SYNTAX Integer32 (0..65535)
			MAX-ACCESS read-create
			STATUS current
			DESCRIPTION
				"This object specifies the low end inclusive range of
				TCP/UDP destination port numbers to which a packet is
				compared. If the referenced parameter is not present
				in a classifier, this object reports the value of 0."
			REFERENCE
				"Section 11.13.19.3.4.7 in IEEE 802.16REVd/D5-2004"
			::= { wmanIfBsClassifierRuleEntry 15 }

		
		-- 1.3.6.1.2.1.10.184.1.1.1.3.1.16
		wmanIfBsClassifierRuleDestPortEnd OBJECT-TYPE
			SYNTAX Integer32 (0..65535)
			MAX-ACCESS read-create
			STATUS current
			DESCRIPTION
				"This object specifies the high end inclusive range of
				TCP/UDP destination port numbers to which a packet is
				compared. If the referenced parameter is not present
				in a classifier, this object reports the value of
				65535."
			REFERENCE
				"Section 11.13.19.3.4.7 in IEEE 802.16REVd/D5-2004"
			::= { wmanIfBsClassifierRuleEntry 16 }

		
		-- 1.3.6.1.2.1.10.184.1.1.1.3.1.17
		wmanIfBsClassifierRuleDestMacAddr OBJECT-TYPE
			SYNTAX MacAddress
			MAX-ACCESS read-create
			STATUS current
			DESCRIPTION
				"An Ethernet packet matches an entry when its destination
				MAC address bitwise ANDed with 
				wmanIfBsClassifierRuleDestMacMask equals the value of
				wmanIfBsClassifierRuleDestMacAddr. If the referenced
				parameter is not present in a classifier, this object
				reports the value of '000000000000'H."
			REFERENCE
				"Section 11.13.19.3.4.8 in IEEE 802.16REVd/D5-2004"
			::= { wmanIfBsClassifierRuleEntry 17 }

		
		-- 1.3.6.1.2.1.10.184.1.1.1.3.1.18
		wmanIfBsClassifierRuleDestMacMask OBJECT-TYPE
			SYNTAX MacAddress
			MAX-ACCESS read-create
			STATUS current
			DESCRIPTION
				"An Ethernet packet matches an entry when its destination
				MAC address bitwise ANDed with
				wmanIfBsClassifierRuleDestMacMask equals the value of
				wmanIfBsClassifierRuleDestMacAddr. If the referenced
				parameter is not present in a classifier, this object
				reports the value of '000000000000'H."
			REFERENCE
				"Section 11.13.19.3.4.8 in IEEE 802.16REVd/D5-2004"
			::= { wmanIfBsClassifierRuleEntry 18 }

		
		-- 1.3.6.1.2.1.10.184.1.1.1.3.1.19
		wmanIfBsClassifierRuleSourceMacAddr OBJECT-TYPE
			SYNTAX MacAddress
			MAX-ACCESS read-create
			STATUS current
			DESCRIPTION
				"An Ethernet packet matches this entry when its source
				MAC address  bitwise ANDed with
				wmanIfBsClassifierRuleSourceMacMask equals the value
				of wmanIfBsClassifierRuleSourceMacAddr. If the
				referenced parameter is not present in a classifier,
				this object reports the value of '000000000000'H."
			REFERENCE
				"Section 11.13.19.3.4.9 in IEEE 802.16REVd/D5-2004"
			::= { wmanIfBsClassifierRuleEntry 19 }

		
		-- 1.3.6.1.2.1.10.184.1.1.1.3.1.20
		wmanIfBsClassifierRuleSourceMacMask OBJECT-TYPE
			SYNTAX MacAddress
			MAX-ACCESS read-create
			STATUS current
			DESCRIPTION
				"An Ethernet packet matches an entry when its destination
				MAC address bitwise ANDed with
				wmanIfBsClassifierRuleSourceMacMask equals the value of
				wmanIfBsClassifierRuleSourceMacAddr. If the referenced
				parameter is not present in a classifier, this object
				reports the value of '000000000000'H."
			REFERENCE
				"Section 11.13.19.3.4.9 in IEEE 802.16REVd/D5-2004"
			::= { wmanIfBsClassifierRuleEntry 20 }

		
		-- 1.3.6.1.2.1.10.184.1.1.1.3.1.21
		wmanIfBsClassifierRuleEnetProtocolType OBJECT-TYPE
			SYNTAX INTEGER
				{
				none(0),
				ethertype(1),
				dsap(2)
				}
			MAX-ACCESS read-create
			STATUS current
			DESCRIPTION
				"This object indicates the format of the layer 3 protocol
				id in the Ethernet packet. A value of none(0) means that
				the rule does not use the layer 3 protocol type as a
				matching criteria. A value of ethertype(1) means that the
				rule applies only to frames which contains an EtherType
				value. Ethertype values are contained in packets using
				the Dec-Intel-Xerox (DIX) encapsulation or the RFC1042
				Sub-Network Access Protocol (SNAP) encapsulation formats.
				A value of dsap(2) means that the rule applies only to
				frames using the IEEE802.3 encapsulation format with a
				Destination Service Access Point (DSAP) other than 0xAA
				(which is reserved for SNAP). If the Ethernet frame
				contains an 802.1P/Q Tag header (i.e. EtherType 0x8100),
				this object applies to the embedded EtherType field within
				the 802.1P/Q header. If the referenced parameter is not
				present in a classifier, this object reports the value of
				0."
			REFERENCE
				"Section 11.13.19.3.4.10 in IEEE 802.16REVd/D5-2004"
			::= { wmanIfBsClassifierRuleEntry 21 }

		
		-- 1.3.6.1.2.1.10.184.1.1.1.3.1.22
		wmanIfBsClassifierRuleEnetProtocol OBJECT-TYPE
			SYNTAX Integer32 (0..65535)
			MAX-ACCESS read-create
			STATUS current
			DESCRIPTION
				"If wmanIfBsClassifierRuleEnetProtocolType is none(0),
				this object is ignored when considering whether a packet
				matches the current rule.
				If wmanIfBsClassifierRuleEnetProtocolType is ethertype(1),
				this object gives the 16-bit value of the EtherType that
				the packet must match in order to match the rule.
				If wmanIfBsClassifierRuleEnetProtocolType is dsap(2), the
				lower 8 bits of this object's value must match the DSAP
				byte of the packet in order to match the rule.
				If the Ethernet frame contains an 802.1P/Q Tag header
				(i.e. EtherType 0x8100), this object applies to the
				embedded EtherType field within the 802.1P/Q header.
				If the referenced parameter is not present in the
				classifier, the value of this object is reported as 0."
			REFERENCE
				"Section 11.13.19.3.4.10 in IEEE 802.16REVd/D5-2004"
			::= { wmanIfBsClassifierRuleEntry 22 }

		
		-- 1.3.6.1.2.1.10.184.1.1.1.3.1.23
		wmanIfBsClassifierRuleUserPriLow OBJECT-TYPE
			SYNTAX Integer32 (0..7)
			MAX-ACCESS read-create
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority field
				within the range of wmanIfBsClassifierRulePriLow and
				wmanIfBsClassifierRulePriHigh in order to match this
				rule.
				If the referenced parameter is not present in the
				classifier, the value of this object is reported as 0."
			REFERENCE
				"Section 11.13.19.3.4.11 in IEEE 802.16REVd/D5-2004"
			::= { wmanIfBsClassifierRuleEntry 23 }

		
		-- 1.3.6.1.2.1.10.184.1.1.1.3.1.24
		wmanIfBsClassifierRuleUserPriHigh OBJECT-TYPE
			SYNTAX Integer32 (0..7)
			MAX-ACCESS read-create
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority
				field within the range of wmanIfBsClassifierRulePriLow
				and wmanIfBsClassifierRulePriHigh in order to match
				this rule.
				If the referenced parameter is not present in the 
				classifier, the value of this object is reported as 7."
			REFERENCE
				"Section 11.13.19.3.4.11 in IEEE 802.16REVd/D5-2004"
			::= { wmanIfBsClassifierRuleEntry 24 }

		
		-- 1.3.6.1.2.1.10.184.1.1.1.3.1.25
		wmanIfBsClassifierRuleVlanId OBJECT-TYPE
			SYNTAX Integer32 (0..4095)
			MAX-ACCESS read-create
			STATUS current
			DESCRIPTION
				"This object applies only to Ethernet frames using the
				802.1P/Q tag header.
				If this object's value is nonzero, tagged packets must
				have a VLAN Identifier that matches the value in order
				to match the rule.
				Only the least significant 12 bits of this object's
				value are valid.
				If the referenced parameter is not present in the
				classifier, the value of this object is reported as 0."
			REFERENCE
				"Section 11.13.19.3.4.12 in IEEE 802.16REVd/D5-2004"
			::= { wmanIfBsClassifierRuleEntry 25 }

		
		-- 1.3.6.1.2.1.10.184.1.1.1.3.1.26
		wmanIfBsClassifierRuleState OBJECT-TYPE
			SYNTAX INTEGER
				{
				active(1),
				inactive(2)
				}
			MAX-ACCESS read-create
			STATUS current
			DESCRIPTION
				"This object indicates whether or not the classifier is
				enabled to classify packets to a Service Flow.
				If the referenced parameter is not present in the
				classifier, the value of this object is reported
				as active(1)."
			::= { wmanIfBsClassifierRuleEntry 26 }

		
		-- 1.3.6.1.2.1.10.184.1.1.1.3.1.27
		wmanIfBsClassifierRulePkts OBJECT-TYPE
			SYNTAX Counter64
			MAX-ACCESS read-create
			STATUS current
			DESCRIPTION
				"This object counts the number of packets that have
				been classified using this entry."
			REFERENCE
				"Section 11.13.19.3.4.1 in IEEE 802.16REVd/D5-2004"
			::= { wmanIfBsClassifierRuleEntry 27 }

		
		-- 1.3.6.1.2.1.10.184.1.1.1.3.1.28
		wmanIfBSClassifierRuleBitMap OBJECT-TYPE
			SYNTAX WmanIfClassifierBitMap
			MAX-ACCESS read-create
			STATUS current
			DESCRIPTION
				"This object indicates which parameter encodings were
				actually present in the entry. A bit set to '1' indicates
				the corresponding classifier encoding is present, and '0'
				means otherwise"
			::= { wmanIfBsClassifierRuleEntry 28 }

		
		-- 1.3.6.1.2.1.10.184.1.1.1.3.1.29
		wmanIfBsClassifierRuleRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { wmanIfBsClassifierRuleEntry 29 }

		
		-- 1.3.6.1.2.1.10.184.1.1.1.4
		wmanIfBsSsPacketCounterTable OBJECT-TYPE
			SYNTAX SEQUENCE OF WmanIfBsSsPacketCounterEntry
			MAX-ACCESS not-accessible
			STATUS current
			DESCRIPTION
				"This table contains counters to keep track of the number
				of packets or octets that have been received or 
				transmitted on the per service flow basis."
			::= { wmanIfBsPacketCs 4 }

		
		-- 1.3.6.1.2.1.10.184.1.1.1.4.1
		wmanIfBsSsPacketCounterEntry OBJECT-TYPE
			SYNTAX WmanIfBsSsPacketCounterEntry
			MAX-ACCESS not-accessible
			STATUS current
			DESCRIPTION
				"This table provides one row for each service flow, and 
				is indexed by wmanIfBsSsSfIndex and
				wmanIfBsSsPktMacAddress."
			INDEX { wmanIfBsSsSfIndex, wmanIfBsSsPktMacAddr }
			::= { wmanIfBsSsPacketCounterTable 1 }

		
		WmanIfBsSsPacketCounterEntry ::=
			SEQUENCE { 
				wmanIfBsSsSfIndex
					Unsigned32,
				wmanIfBsSsPktMacAddr
					VariableMacAddress,
				wmanIfBsSsSfDirection
					INTEGER,
				wmanIfBsSsMacSduCount
					Counter64,
				wmanIfBsSsOctetCount
					Counter64,
				wmanIfBsSsResetCounter
					INTEGER,
				wmanIfBsSsResetCounterTime
					TimeStamp
			 }

		-- 1.3.6.1.2.1.10.184.1.1.1.4.1.1
		wmanIfBsSsSfIndex OBJECT-TYPE
			SYNTAX Unsigned32 (1..4294967295)
			MAX-ACCESS not-accessible
			STATUS current
			DESCRIPTION
				"A 32 bit quantity that uniquely identifies a service flow."
			::= { wmanIfBsSsPacketCounterEntry 1 }

		
		-- 1.3.6.1.2.1.10.184.1.1.1.4.1.2
		wmanIfBsSsPktMacAddr OBJECT-TYPE
			SYNTAX VariableMacAddress
			MAX-ACCESS not-accessible
			STATUS current
			DESCRIPTION
				"The MAC address of the SS, where the service flow resides.
				It can be used as the index to associate service flows
				with the SS."
			::= { wmanIfBsSsPacketCounterEntry 2 }

		
		-- 1.3.6.1.2.1.10.184.1.1.1.4.1.3
		wmanIfBsSsSfDirection OBJECT-TYPE
			SYNTAX INTEGER
				{
				transmit(1),
				receive(2)
				}
			MAX-ACCESS read-only
			STATUS current
			DESCRIPTION
				"An attribute indiating whether the packet counter is on
				transmit or receive direction from the BS perspective."
			::= { wmanIfBsSsPacketCounterEntry 3 }

		
		-- 1.3.6.1.2.1.10.184.1.1.1.4.1.4
		wmanIfBsSsMacSduCount OBJECT-TYPE
			SYNTAX Counter64
			MAX-ACCESS read-only
			STATUS current
			DESCRIPTION
				"This object counts the number of MAC SDUs that have
				been transmitted or received."
			::= { wmanIfBsSsPacketCounterEntry 4 }

		
		-- 1.3.6.1.2.1.10.184.1.1.1.4.1.5
		wmanIfBsSsOctetCount OBJECT-TYPE
			SYNTAX Counter64
			MAX-ACCESS read-only
			STATUS current
			DESCRIPTION
				"This object counts the number of octets that have
				been transmitted or received."
			::= { wmanIfBsSsPacketCounterEntry 5 }

		
		-- 1.3.6.1.2.1.10.184.1.1.1.4.1.6
		wmanIfBsSsResetCounter OBJECT-TYPE
			SYNTAX INTEGER
				{
				null(0),
				resetCounter(1)
				}
			MAX-ACCESS read-write
			STATUS current
			DESCRIPTION
				"When SET this attribute to resetCounter(1), the
				corresponding entry of packet counters will be reset.
				A GET operation performed on this object will always
				return null(0). The counter is normally reset after
				the packet count information is retrieved. "
			::= { wmanIfBsSsPacketCounterEntry 6 }

		
		-- 1.3.6.1.2.1.10.184.1.1.1.4.1.7
		wmanIfBsSsResetCounterTime OBJECT-TYPE
			SYNTAX TimeStamp
			MAX-ACCESS read-only
			STATUS current
			DESCRIPTION
				"Indicates the date and time when the counter is
				reset."
			::= { wmanIfBsSsPacketCounterEntry 7 }

		
--  wmanIfBsCps contain the Base Station Common Part Sublayer objects
		-- 1.3.6.1.2.1.10.184.1.1.2
		wmanIfBsCps OBJECT IDENTIFIER ::= { wmanIfBsObjects 2 }

		
		-- 1.3.6.1.2.1.10.184.1.1.2.1
		wmanIfBsRegisteredSsTable OBJECT-TYPE
			SYNTAX SEQUENCE OF WmanIfBsRegisteredSsEntry
			MAX-ACCESS not-accessible
			STATUS current
			DESCRIPTION
				"This table contains the basic capability information
				of SSs that have been negotiated and agreed between
				BS and SS via REG-REQ and REG-RSP messages. An entry
				in this table indicates the SS has entered and registered
				into the BS."
			REFERENCE
				"Section 6.3.2.3.7 in IEEE 802.16REVd/D5-2004"
			::= { wmanIfBsCps 1 }

		
		-- 1.3.6.1.2.1.10.184.1.1.2.1.1
		wmanIfBsRegisteredSsEntry OBJECT-TYPE
			SYNTAX WmanIfBsRegisteredSsEntry
			MAX-ACCESS not-accessible
			STATUS current
			DESCRIPTION
				"This table provides one row for each SS that has been
				registered in the BS, and is indexed by 
				wmanIfBsSsIdIndex. The primary index is the ifIndex
				with an ifType of propBWAp2Mp, indicating the BS sector
				with which the SS is associated. wmanIfBsSsIdIndex
				identifies the SS being registered."
			INDEX { ifIndex, wmanIfBsSsIdIndex }
			::= { wmanIfBsRegisteredSsTable 1 }

		
		WmanIfBsRegisteredSsEntry ::=
			SEQUENCE { 
				wmanIfBsSsIdIndex
					Unsigned32,
				wmanIfBsSsMacAddress
					MacAddress,
				wmanIfBsSsBasicCid
					INTEGER,
				wmanIfBsSsPrimaryCid
					INTEGER,
				wmanIfBsSsSecondaryCid
					INTEGER,
				wmanIfBsSsHmacTuple
					OCTET STRING,
				wmanIfBsSsUlCidSupport
					INTEGER,
				wmanIfBsSsManagementSupport
					INTEGER,
				wmanIfBsSsArqSupport
					INTEGER,
				wmanIfBsSsDsxFlowControl
					INTEGER,
				wmanIfBsSsMacCrcSupport
					INTEGER,
				wmanIfBsSsMcaFlowControl
					INTEGER,
				wmanIfBsSsMcpGroupCidSupport
					INTEGER,
				wmanIfBsSsPkmFlowControl
					INTEGER,
				wmanIfBsSsAuthorizationPolicyControl
					BITS,
				wmanIfBsSsMaxNumOfSupportedSA
					INTEGER,
				wmanIfBsSsIpVersion
					INTEGER,
				wmanIfBsSsMacCsSupportBitMap
					BITS,
				wmanIfBsSsMaxNumOfClassifier
					INTEGER,
				wmanIfBsSsPhsSupport
					INTEGER,
				wmanIfBsSsIpManagementSupport
					INTEGER,
				wmanIfBsSs2ndMgmtArqEnable
					TruthValue,
				wmanIfBsSs2ndMgmtArqWindowSize
					INTEGER,
				wmanIfBsSs2ndMgmtArqFragmentLifetime
					INTEGER,
				wmanIfBsSs2ndMgmtArqSyncLossTimeout
					INTEGER,
				wmanIfBsSs2ndMgmtArqDeliverInOrder
					TruthValue,
				wmanIfBsSs2ndMgmtArqRxPurgeTimeout
					INTEGER,
				wmanIfBsSsVendorIdEncoding
					OCTET STRING
			 }

		-- 1.3.6.1.2.1.10.184.1.1.2.1.1.1
		wmanIfBsSsIdIndex OBJECT-TYPE
			SYNTAX Unsigned32 (1..4294967295)
			MAX-ACCESS not-accessible
			STATUS current
			DESCRIPTION
				"wmanIfBsSsIdIndex identifies the SS that is registered."
			::= { wmanIfBsRegisteredSsEntry 1 }

		
		-- 1.3.6.1.2.1.10.184.1.1.2.1.1.2
		wmanIfBsSsMacAddress OBJECT-TYPE
			SYNTAX MacAddress
			MAX-ACCESS read-only
			STATUS current
			DESCRIPTION
				"The MAC address of SS is received from the RNG-REQ
				message. When SS registers, this MAC address is entered
				into the table, and used as the identifier to the SS."
			REFERENCE
				"Section 6.3.2.3.6 in IEEE 802.16REVd/D5-2004"
			::= { wmanIfBsRegisteredSsEntry 2 }

		
		-- 1.3.6.1.2.1.10.184.1.1.2.1.1.3
		wmanIfBsSsBasicCid OBJECT-TYPE
			SYNTAX INTEGER
			MAX-ACCESS read-only
			STATUS current
			DESCRIPTION
				"The value of this object indicates the SS's basic CID
				that was sent in the RNG-RSP message."
			REFERENCE
				"Section 6.3.2.3.8 in IEEE 802.16REVd/D5-2004"
			::= { wmanIfBsRegisteredSsEntry 3 }

		
		-- 1.3.6.1.2.1.10.184.1.1.2.1.1.4
		wmanIfBsSsPrimaryCid OBJECT-TYPE
			SYNTAX INTEGER
			MAX-ACCESS read-only
			STATUS current
			DESCRIPTION
				"The value of this object indicates the primary CID of the
				SS received from the RNG-RSP message."
			REFERENCE
				"Section 6.3.2.3.8 in IEEE 802.16REVd/D5-2004"
			::= { wmanIfBsRegisteredSsEntry 4 }

		
		-- 1.3.6.1.2.1.10.184.1.1.2.1.1.5
		wmanIfBsSsSecondaryCid OBJECT-TYPE
			SYNTAX INTEGER
			MAX-ACCESS read-only
			STATUS current
			DESCRIPTION
				"The value of this object indicates the secondary
				management CID present in the REG-RSP message. The value
				should be null if the 2nd management channel is not
				available."
			REFERENCE
				"Section 6.4.2.3.8 in IEEE 802.16REVd/D5-2004"
			::= { wmanIfBsRegisteredSsEntry 5 }

		
		-- 1.3.6.1.2.1.10.184.1.1.2.1.1.6
		wmanIfBsSsHmacTuple OBJECT-TYPE
			SYNTAX OCTET STRING
			MAX-ACCESS read-only
			STATUS current
			DESCRIPTION
				"This parameter contains the HMAC Key Sequence Number
				concatenated with an HMAC-Digest message during the
				authentication. The HMAC Key Sequence Number is stored
				in the four least significant bits of the first byte of
				the HMAC Tuple, and the most significant four bits
				are reserved."
			REFERENCE
				"Section 11.1.2 in IEEE 802.16REVd/D5-2004"
			::= { wmanIfBsRegisteredSsEntry 6 }

		
		-- 1.3.6.1.2.1.10.184.1.1.2.1.1.7
		wmanIfBsSsUlCidSupport OBJECT-TYPE
			SYNTAX INTEGER
			MAX-ACCESS read-only
			STATUS current
			DESCRIPTION
				"This object shows the number of Uplink CIDs the SS can
				support."
			REFERENCE
				"Section 11.7.4 in IEEE 802.16REVd/D5-2004"
			::= { wmanIfBsRegisteredSsEntry 7 }

		
		-- 1.3.6.1.2.1.10.184.1.1.2.1.1.8
		wmanIfBsSsManagementSupport OBJECT-TYPE
			SYNTAX INTEGER
				{
				unmanagedSs(0),
				managedSs(1)
				}
			MAX-ACCESS read-only
			STATUS current
			DESCRIPTION
				"This object indicates whether or not the SS is managed."
			REFERENCE
				"Section 11.7.1.1 in IEEE 802.16REVd/D5-2004"
			::= { wmanIfBsRegisteredSsEntry 8 }

		
		-- 1.3.6.1.2.1.10.184.1.1.2.1.1.9
		wmanIfBsSsArqSupport OBJECT-TYPE
			SYNTAX INTEGER
				{
				arqNotSupported(0),
				arqSupported(1)
				}
			MAX-ACCESS read-only
			STATUS current
			DESCRIPTION
				"This object indicates whether the SS support ARQ."
			REFERENCE
				"Section 11.7.6.1 in IEEE 802.16REVd/D5-2004"
			::= { wmanIfBsRegisteredSsEntry 9 }

		
		-- 1.3.6.1.2.1.10.184.1.1.2.1.1.10
		wmanIfBsSsDsxFlowControl OBJECT-TYPE
			SYNTAX INTEGER (0..255)
			MAX-ACCESS read-only
			STATUS current
			DESCRIPTION
				"This object specifies the maximum number of concurrent
				DSA, DSC, or DSD transactions that may be outstanding."
			REFERENCE
				"Section 11.7.6.2 in IEEE 802.16REVd/D5-2004"
			DEFVAL { 0 }
			::= { wmanIfBsRegisteredSsEntry 10 }

		
		-- 1.3.6.1.2.1.10.184.1.1.2.1.1.11
		wmanIfBsSsMacCrcSupport OBJECT-TYPE
			SYNTAX INTEGER
				{
				noMacCrcSupport(0),
				macCrcSupport(1)
				}
			MAX-ACCESS read-only
			STATUS current
			DESCRIPTION
				"This object indicates whether or not the SS supports MAC
				level CRC."
			REFERENCE
				"Section 11.7.6.3 in IEEE 802.16REVd/D5-2004"
			DEFVAL { 1 }
			::= { wmanIfBsRegisteredSsEntry 11 }

		
		-- 1.3.6.1.2.1.10.184.1.1.2.1.1.12
		wmanIfBsSsMcaFlowControl OBJECT-TYPE
			SYNTAX INTEGER (0..255)
			MAX-ACCESS read-only
			STATUS current
			DESCRIPTION
				"This object specifies the maximum number of concurrent
				MCA transactions that may be outstanding."
			REFERENCE
				"Section 11.7.6.4 in IEEE 802.16REVd/D5-2004"
			DEFVAL { 0 }
			::= { wmanIfBsRegisteredSsEntry 12 }

		
		-- 1.3.6.1.2.1.10.184.1.1.2.1.1.13
		wmanIfBsSsMcpGroupCidSupport OBJECT-TYPE
			SYNTAX INTEGER (0..255)
			MAX-ACCESS read-only
			STATUS current
			DESCRIPTION
				"This object indicates the maximum number of
				simultaneous Multicast Polling Groups the SS is
				capable of belonging to."
			REFERENCE
				"Section 11.7.6.5 in IEEE 802.16REVd/D5-2004"
			DEFVAL { 0 }
			::= { wmanIfBsRegisteredSsEntry 13 }

		
		-- 1.3.6.1.2.1.10.184.1.1.2.1.1.14
		wmanIfBsSsPkmFlowControl OBJECT-TYPE
			SYNTAX INTEGER (0..255)
			MAX-ACCESS read-only
			STATUS current
			DESCRIPTION
				"This object specifies the maximum number of concurrent PKM
				transactions that may be outstanding."
			REFERENCE
				"Section 11.7.6.6 in IEEE 802.16REVd/D5-2004"
			DEFVAL { 0 }
			::= { wmanIfBsRegisteredSsEntry 14 }

		
		-- 1.3.6.1.2.1.10.184.1.1.2.1.1.15
		wmanIfBsSsAuthorizationPolicyControl OBJECT-TYPE
			SYNTAX BITS
				{
				ieee802-16PrivacySupported(0),
				reserved1(1),
				reserved2(2),
				reserved3(3),
				reserved4(4),
				reserved5(5),
				reserved6(6),
				reserved7(7)
				}
			MAX-ACCESS read-only
			STATUS current
			DESCRIPTION
				"This object specifies authorization policy that both SS and
				BS need to negotiate and synchronize. A bit value of 0 = 
				not supported, 1 = upported. If this field is omitted, then
				both SS and BS shall use the IEEE 802.16 security,
				constituting X.509 digital certificates and the RSA public
				key encryption algorithm, as authorization policy."
			REFERENCE
				"Section 11.7.8.7 in IEEE 802.16REVd/D5-2004"
			::= { wmanIfBsRegisteredSsEntry 15 }

		
		-- 1.3.6.1.2.1.10.184.1.1.2.1.1.16
		wmanIfBsSsMaxNumOfSupportedSA OBJECT-TYPE
			SYNTAX INTEGER (0..255)
			MAX-ACCESS read-only
			STATUS current
			DESCRIPTION
				"This field specifies maximum number of supported security
				association of the SS."
			REFERENCE
				"Section 11.7.8.8 in IEEE 802.16REVd/D5-2004"
			DEFVAL { 1 }
			::= { wmanIfBsRegisteredSsEntry 16 }

		
		-- 1.3.6.1.2.1.10.184.1.1.2.1.1.17
		wmanIfBsSsIpVersion OBJECT-TYPE
			SYNTAX INTEGER
				{
				ipv4(1),
				ipv6(2)
				}
			MAX-ACCESS read-only
			STATUS current
			DESCRIPTION
				"This object indicates the version of IP used on the
				Secondary Management Connection. The valus should be numm
				if the 2nd management CID doesn't exist."
			REFERENCE
				"Section 11.7.2.1 in IEEE 802.16REVd/D5-2004"
			::= { wmanIfBsRegisteredSsEntry 17 }

		
		-- 1.3.6.1.2.1.10.184.1.1.2.1.1.18
		wmanIfBsSsMacCsSupportBitMap OBJECT-TYPE
			SYNTAX BITS
				{
				atm(0),
				packetIpv4(1),
				packetIpv6(2),
				packet802-3(3),
				packet802-1Q(4),
				packetIpv4Over802-3(5),
				packetIpv6Over802-3(6),
				packetIpv4Over802-1Q(7),
				packetIpv6Over802-1Q(8)
				}
			MAX-ACCESS read-only
			STATUS current
			DESCRIPTION
				"This object indicates the set of MAC convergence
				sublayer support. When a bit is set, it indicates
				the corresponding CS feature is supported."
			REFERENCE
				"Section 11.7.5.1 in IEEE 802.16REVd/D5-2004"
			::= { wmanIfBsRegisteredSsEntry 18 }

		
		-- 1.3.6.1.2.1.10.184.1.1.2.1.1.19
		wmanIfBsSsMaxNumOfClassifier OBJECT-TYPE
			SYNTAX INTEGER
			MAX-ACCESS read-only
			STATUS current
			DESCRIPTION
				"This object indicates the maximum number of admitted
				Classifiers that the SS is allowed to have."
			REFERENCE
				"Section 11.7.5.2 in IEEE 802.16REVd/D5-2004"
			DEFVAL { 0 }
			::= { wmanIfBsRegisteredSsEntry 19 }

		
		-- 1.3.6.1.2.1.10.184.1.1.2.1.1.20
		wmanIfBsSsPhsSupport OBJECT-TYPE
			SYNTAX INTEGER
				{
				noPhsSupport(0),
				atmPhsSupport(1),
				packetPhsSupport(2)
				}
			MAX-ACCESS read-only
			STATUS current
			DESCRIPTION
				"This object indicates indicates the level of PHS support."
			REFERENCE
				"Section 11.7.5.3 in IEEE 802.16REVd/D5-2004"
			DEFVAL { 0 }
			::= { wmanIfBsRegisteredSsEntry 20 }

		
		-- 1.3.6.1.2.1.10.184.1.1.2.1.1.21
		wmanIfBsSsIpManagementSupport OBJECT-TYPE
			SYNTAX INTEGER
				{
				unmanaged(0),
				ipManaged(1)
				}
			MAX-ACCESS read-only
			STATUS current
			DESCRIPTION
				"The IP management mode parameter dictates whether
				the provider intends to manage the SS on an ongoing
				basis via IP-based mechanisms."
			REFERENCE
				"Section 11.7.3 in IEEE 802.16REVd/D5-2004"
			::= { wmanIfBsRegisteredSsEntry 21 }

		
		-- 1.3.6.1.2.1.10.184.1.1.2.1.1.22
		wmanIfBsSs2ndMgmtArqEnable OBJECT-TYPE
			SYNTAX TruthValue
			MAX-ACCESS read-only
			STATUS current
			DESCRIPTION
				"True(1) ARQ enabling is requested for the 2nd
				management channel."
			REFERENCE
				"Section 11.13.20 in IEEE 802.16REVd/D5-2004"
			::= { wmanIfBsRegisteredSsEntry 22 }

		
		-- 1.3.6.1.2.1.10.184.1.1.2.1.1.23
		wmanIfBsSs2ndMgmtArqWindowSize OBJECT-TYPE
			SYNTAX INTEGER (1..1024)
			MAX-ACCESS read-only
			STATUS current
			DESCRIPTION
				"Indicates the maximum number of unacknowledged 
				fragments at any time for 2nd management channel."
			REFERENCE
				"Section 11.13.20 in IEEE 802.16REVd/D5-2004"
			::= { wmanIfBsRegisteredSsEntry 23 }

		
		-- 1.3.6.1.2.1.10.184.1.1.2.1.1.24
		wmanIfBsSs2ndMgmtArqFragmentLifetime OBJECT-TYPE
			SYNTAX INTEGER (0..65535)
			UNITS "10 us"
			MAX-ACCESS read-only
			STATUS current
			DESCRIPTION
				"The maximum time interval an ARQ fragment will be
				managed by the transmitter ARQ machine, once
				initial transmission of the fragment has occured.
				If transmission or retransmission of the fragment
				is not acknowledged by the receiver before the 
				time limit is reached, the fragmnet is discarded.
				A value of 0 means Infinite."
			REFERENCE
				"Section 11.13.20 in IEEE 802.16REVd/D5-2004"
			DEFVAL { 0 }
			::= { wmanIfBsRegisteredSsEntry 24 }

		
		-- 1.3.6.1.2.1.10.184.1.1.2.1.1.25
		wmanIfBsSs2ndMgmtArqSyncLossTimeout OBJECT-TYPE
			SYNTAX INTEGER (0..65535)
			UNITS "10 us"
			MAX-ACCESS read-only
			STATUS current
			DESCRIPTION
				"The maximum interval before declaring a loss
				of synchronization of the sender and receiver
				state machines. A value of 0 means Infinite."
			REFERENCE
				"Section 11.13.20 in IEEE 802.16REVd/D5-2004"
			DEFVAL { 0 }
			::= { wmanIfBsRegisteredSsEntry 25 }

		
		-- 1.3.6.1.2.1.10.184.1.1.2.1.1.26
		wmanIfBsSs2ndMgmtArqDeliverInOrder OBJECT-TYPE
			SYNTAX TruthValue
			MAX-ACCESS read-only
			STATUS current
			DESCRIPTION
				"Indicates whether or not data is to be delivered
				by the receiving MAC to its client application
				in the order in which data was handed off to the
				originating MAC."
			REFERENCE
				"Section 11.13.20 in IEEE 802.16REVd/D5-2004"
			::= { wmanIfBsRegisteredSsEntry 26 }

		
		-- 1.3.6.1.2.1.10.184.1.1.2.1.1.27
		wmanIfBsSs2ndMgmtArqRxPurgeTimeout OBJECT-TYPE
			SYNTAX INTEGER (0..65535)
			UNITS "10 us"
			MAX-ACCESS read-only
			STATUS current
			DESCRIPTION
				"Indicates the time interval the ARQ window is advanced
				after a fragment is received. A value of 0 means Infinite."
			REFERENCE
				"Section 11.13.20 in IEEE 802.16REVd/D5-2004"
			DEFVAL { 0 }
			::= { wmanIfBsRegisteredSsEntry 27 }

		
		-- 1.3.6.1.2.1.10.184.1.1.2.1.1.28
		wmanIfBsSsVendorIdEncoding OBJECT-TYPE
			SYNTAX OCTET STRING (SIZE (3))
			MAX-ACCESS read-only
			STATUS current
			DESCRIPTION
				"The value field contains the vendor identification
				specified by the 3 byte vendor-specific organizationally
				unique identifier of the SS or BS MAC address.A vendor ID
				used in a REG-REQ shall be the Vendor ID of the SS sending
				the request. A vendor ID used in a REG-RSP shall be the
				Vendor ID of the BS sending the response."
			REFERENCE
				"Section 11.1.5 in IEEE 802.16REVd/D5-2004"
			::= { wmanIfBsRegisteredSsEntry 28 }

		
--  wmanIfBsConfigurationTable contains global parameters common in BS 
-- 
		-- 1.3.6.1.2.1.10.184.1.1.2.2
		wmanIfBsConfigurationTable OBJECT-TYPE
			SYNTAX SEQUENCE OF WmanIfBsConfigurationEntry
			MAX-ACCESS not-accessible
			STATUS current
			DESCRIPTION
				"This table provides one row for each BS sector that
				contains the BS system parameters as defined in section
				10.1 of [3]."
			::= { wmanIfBsCps 2 }

		
		-- 1.3.6.1.2.1.10.184.1.1.2.2.1
		wmanIfBsConfigurationEntry OBJECT-TYPE
			SYNTAX WmanIfBsConfigurationEntry
			MAX-ACCESS not-accessible
			STATUS current
			DESCRIPTION
				"This table is indexed by ifIndex with an ifType of
				propBWAp2Mp."
			INDEX { ifIndex }
			::= { wmanIfBsConfigurationTable 1 }

		
		WmanIfBsConfigurationEntry ::=
			SEQUENCE { 
				wmanIfBsDcdInterval
					INTEGER,
				wmanIfBsUcdInterval
					INTEGER,
				wmanIfBsUcdTransition
					INTEGER,
				wmanIfBsDcdTransition
					INTEGER,
				wmanIfBsMaxMAPPending
					INTEGER,
				wmanIfBsInitialRangingInterval
					INTEGER,
				wmanIfBsClkCmpInterval
					INTEGER,
				wmanIfBsSsULMapProcTime
					Unsigned32,
				wmanIfBsSsRangRespProcTime
					Unsigned32,
				wmanIfBsT5Timeout
					INTEGER,
				wmanIfBsT9Timeout
					INTEGER,
				wmanIfBsT13Timeout
					INTEGER,
				wmanIfBsT15Timeout
					INTEGER,
				wmanIfBsT17Timeout
					INTEGER,
				wmanIfBsT27IdleTimer
					INTEGER,
				wmanIfBsT27ActiveTimer
					INTEGER
			 }

		-- 1.3.6.1.2.1.10.184.1.1.2.2.1.1
		wmanIfBsDcdInterval OBJECT-TYPE
			SYNTAX INTEGER (0..10000)
			UNITS "milliseconds"
			MAX-ACCESS read-write
			STATUS current
			DESCRIPTION
				"Time between transmission of DCD messages in ms."
			::= { wmanIfBsConfigurationEntry 1 }

		
		-- 1.3.6.1.2.1.10.184.1.1.2.2.1.2
		wmanIfBsUcdInterval OBJECT-TYPE
			SYNTAX INTEGER (0..10000)
			UNITS "milliseconds"
			MAX-ACCESS read-write
			STATUS current
			DESCRIPTION
				"Time between transmission of UCD messages in ms."
			::= { wmanIfBsConfigurationEntry 2 }

		
		-- 1.3.6.1.2.1.10.184.1.1.2.2.1.3
		wmanIfBsUcdTransition OBJECT-TYPE
			SYNTAX INTEGER
			UNITS "Number of MAC Frames"
			MAX-ACCESS read-write
			STATUS current
			DESCRIPTION
				"The time the BS shall wait after repeating a UCD message
				with an incremented Configuration Change Count before
				issuing a UL-MAP message referring to
				Downlink_Burst_Profiles defined in that UCD message."
			::= { wmanIfBsConfigurationEntry 3 }

		
		-- 1.3.6.1.2.1.10.184.1.1.2.2.1.4
		wmanIfBsDcdTransition OBJECT-TYPE
			SYNTAX INTEGER
			UNITS "Number of MAC Frames"
			MAX-ACCESS read-write
			STATUS current
			DESCRIPTION
				"The time the BS shall wait after repeating a DCD message
				with an incremented Configuration Change Count before
				issuing a DL-MAP message referring to Uplink_Burst_Profiles
				defined in that DCD message."
			::= { wmanIfBsConfigurationEntry 4 }

		
		-- 1.3.6.1.2.1.10.184.1.1.2.2.1.5
		wmanIfBsMaxMAPPending OBJECT-TYPE
			SYNTAX INTEGER
			MAX-ACCESS read-write
			STATUS current
			DESCRIPTION
				"Maximum validity of map."
			::= { wmanIfBsConfigurationEntry 5 }

		
		-- 1.3.6.1.2.1.10.184.1.1.2.2.1.6
		wmanIfBsInitialRangingInterval OBJECT-TYPE
			SYNTAX INTEGER (0..2000)
			UNITS "milliseconds"
			MAX-ACCESS read-write
			STATUS current
			DESCRIPTION
				"Time between Initial Ranging regions assigned by the BS
				in ms."
			::= { wmanIfBsConfigurationEntry 6 }

		
		-- 1.3.6.1.2.1.10.184.1.1.2.2.1.7
		wmanIfBsClkCmpInterval OBJECT-TYPE
			SYNTAX INTEGER (50)
			UNITS "milliseconds"
			MAX-ACCESS read-write
			STATUS current
			DESCRIPTION
				"Time between the clock compare measurements used for the
				generation of CLK-CMP messages."
			::= { wmanIfBsConfigurationEntry 7 }

		
		-- 1.3.6.1.2.1.10.184.1.1.2.2.1.8
		wmanIfBsSsULMapProcTime OBJECT-TYPE
			SYNTAX Unsigned32 (200..4294967295)
			UNITS "micro seconds"
			MAX-ACCESS read-write
			STATUS current
			DESCRIPTION
				"Time provided between arrival of the last bit of a UL-MAP
				at an SS and effectiveness of that map in us."
			::= { wmanIfBsConfigurationEntry 8 }

		
		-- 1.3.6.1.2.1.10.184.1.1.2.2.1.9
		wmanIfBsSsRangRespProcTime OBJECT-TYPE
			SYNTAX Unsigned32 (10000..4294967295)
			UNITS "micro seconds"
			MAX-ACCESS read-write
			STATUS current
			DESCRIPTION
				"Time allowed for an SS following receipt of a ranging
				response before it is expected to reply to an invited
				ranging request in us."
			::= { wmanIfBsConfigurationEntry 9 }

		
		-- 1.3.6.1.2.1.10.184.1.1.2.2.1.10
		wmanIfBsT5Timeout OBJECT-TYPE
			SYNTAX INTEGER (0..2000)
			UNITS "milliseconds"
			MAX-ACCESS read-write
			STATUS current
			DESCRIPTION
				"Wait for Uplink Channel Change Response in ms."
			::= { wmanIfBsConfigurationEntry 10 }

		
		-- 1.3.6.1.2.1.10.184.1.1.2.2.1.11
		wmanIfBsT9Timeout OBJECT-TYPE
			SYNTAX INTEGER (300..65535)
			UNITS "milliseconds"
			MAX-ACCESS read-write
			STATUS current
			DESCRIPTION
				"Registration Timeout, the time allowed between the BS
				sending a RNG-RSP (success) to an SS,	and receiving a
				SBC-REQ from that same SS in ms."
			::= { wmanIfBsConfigurationEntry 11 }

		
		-- 1.3.6.1.2.1.10.184.1.1.2.2.1.12
		wmanIfBsT13Timeout OBJECT-TYPE
			SYNTAX INTEGER (15..65535)
			UNITS "minutes"
			MAX-ACCESS read-write
			STATUS current
			DESCRIPTION
				"The time allowed for an SS, following receipt of a
				REG-RSP message to send a TFTP-CPLT message to the BS
				in min."
			::= { wmanIfBsConfigurationEntry 12 }

		
		-- 1.3.6.1.2.1.10.184.1.1.2.2.1.13
		wmanIfBsT15Timeout OBJECT-TYPE
			SYNTAX INTEGER (20..65535)
			UNITS "milliseconds"
			MAX-ACCESS read-write
			STATUS current
			DESCRIPTION
				"Wait for MCA-RSP in ms."
			::= { wmanIfBsConfigurationEntry 13 }

		
		-- 1.3.6.1.2.1.10.184.1.1.2.2.1.14
		wmanIfBsT17Timeout OBJECT-TYPE
			SYNTAX INTEGER (5..65535)
			UNITS "minutes"
			MAX-ACCESS read-write
			STATUS current
			DESCRIPTION
				"Time allowed for SS to complete SS Authorization and
				Key Exchange in minutes."
			::= { wmanIfBsConfigurationEntry 14 }

		
		-- 1.3.6.1.2.1.10.184.1.1.2.2.1.15
		wmanIfBsT27IdleTimer OBJECT-TYPE
			SYNTAX INTEGER
			UNITS "milliseconds"
			MAX-ACCESS read-write
			STATUS current
			DESCRIPTION
				"Maximum time between unicast grants to SS when BS believes 
				SS uplink transmission quality is good enough."
			::= { wmanIfBsConfigurationEntry 15 }

		
		-- 1.3.6.1.2.1.10.184.1.1.2.2.1.16
		wmanIfBsT27ActiveTimer OBJECT-TYPE
			SYNTAX INTEGER
			UNITS "milliseconds"
			MAX-ACCESS read-write
			STATUS current
			DESCRIPTION
				"Maximum time between unicast grants to SS when BS believes 
				SS uplink transmission quality is not good enough."
			::= { wmanIfBsConfigurationEntry 16 }

		
--  Base Station statistics counters
-- 
		-- 1.3.6.1.2.1.10.184.1.1.2.3
		wmanIfBsStatisticCounter OBJECT IDENTIFIER ::= { wmanIfBsCps 3 }

		
		-- 1.3.6.1.2.1.10.184.1.1.2.3.1
		wmanIfBsChMeasurementTable OBJECT-TYPE
			SYNTAX SEQUENCE OF WmanIfBsChMeasurementEntry
			MAX-ACCESS not-accessible
			STATUS deprecated
			DESCRIPTION
				"This table contains channel measurement information
				on the uplink signal received from SS. The table shall
				be maintained as FIFO to store measurement samples that
				can be used to create RSSI and CINR histogram report.
				When the measurement entry for a SS reaches the limit,
				the oldest entry shall be deleted as the new entry is
				added to the table.
				
				DEPRECATED: asmaxBsChannelMeasurementTable is based on the 
				Draft6 MIB and should be implemented instead."
			::= { wmanIfBsStatisticCounter 1 }

		
		-- 1.3.6.1.2.1.10.184.1.1.2.3.1.1
		wmanIfBsChMeasurementEntry OBJECT-TYPE
			SYNTAX WmanIfBsChMeasurementEntry
			MAX-ACCESS not-accessible
			STATUS deprecated
			DESCRIPTION
				"Each entry in the table contains RSSI and CINR
				signal quality measurement on signal received from the SS.
				The primary index is the ifIndex with ifType of propBWAp2Mp
				identifing the BS sector. wmanIfChSsIdIndex identifies
				the SS from which the signal was received.
				wmanIfBsHistogramIndex is the index to histogram samples.
				Since there is no time stamp in the table,
				wmanIfBsHistogramIndex should be increased monotonically,
				and warps around when it reaches the limit. "
			INDEX { ifIndex, wmanIfBsChSsIdIndex, wmanIfBsHistogramIndex }
			::= { wmanIfBsChMeasurementTable 1 }

		
		WmanIfBsChMeasurementEntry ::=
			SEQUENCE { 
				wmanIfBsChSsIdIndex
					Unsigned32,
				wmanIfBsHistogramIndex
					Unsigned32,
				wmanIfBsChannelNumber
					INTEGER,
				wmanIfBsStartFrame
					INTEGER,
				wmanIfBsDuration
					INTEGER,
				wmanIfBsBasicReport
					BITS,
				wmanIfBsMeanCinrReport
					INTEGER,
				wmanIfBsMeanRssiReport
					INTEGER,
				wmanIfBsStdDeviationCinrReport
					INTEGER,
				wmanIfBsStdDeviationRssiReport
					INTEGER
			 }

		-- 1.3.6.1.2.1.10.184.1.1.2.3.1.1.1
		wmanIfBsChSsIdIndex OBJECT-TYPE
			SYNTAX Unsigned32 (1..4294967295)
			MAX-ACCESS not-accessible
			STATUS deprecated
			DESCRIPTION
				"wmanIfBsChIdIndex identifies the SS providing the
				channel measurement."
			REFERENCE
				"Section 6.4.2.3.5 in IEEE 802.16REVd/D5-2004"
			::= { wmanIfBsChMeasurementEntry 1 }

		
		-- 1.3.6.1.2.1.10.184.1.1.2.3.1.1.2
		wmanIfBsHistogramIndex OBJECT-TYPE
			SYNTAX Unsigned32 (1..4294967295)
			MAX-ACCESS not-accessible
			STATUS deprecated
			DESCRIPTION
				"wmanIfBsHistogramIndex identifies the histogram samples
				in the table for each subscriber station."
			::= { wmanIfBsChMeasurementEntry 2 }

		
		-- 1.3.6.1.2.1.10.184.1.1.2.3.1.1.3
		wmanIfBsChannelNumber OBJECT-TYPE
			SYNTAX INTEGER
			MAX-ACCESS read-only
			STATUS deprecated
			DESCRIPTION
				"Physical channel number to be reported on is only
				applicable to licence exampt band. For licenced band,
				this parameter should be null."
			REFERENCE
				"Section 8.5.1 in IEEE 802.16REVd/D5-2004"
			::= { wmanIfBsChMeasurementEntry 3 }

		
		-- 1.3.6.1.2.1.10.184.1.1.2.3.1.1.4
		wmanIfBsStartFrame OBJECT-TYPE
			SYNTAX INTEGER
			MAX-ACCESS read-only
			STATUS deprecated
			DESCRIPTION
				"Frame number in which measurement for this channel
				started."
			REFERENCE
				"Section 11.12 in IEEE 802.16REVd/D5-2004"
			::= { wmanIfBsChMeasurementEntry 4 }

		
		-- 1.3.6.1.2.1.10.184.1.1.2.3.1.1.5
		wmanIfBsDuration OBJECT-TYPE
			SYNTAX INTEGER
			MAX-ACCESS read-only
			STATUS deprecated
			DESCRIPTION
				"Cumulative measurement duration on the channel in
				multiples of Ts. For any value exceeding 0xFFFFFF,
				report 0xFFFFFF."
			REFERENCE
				"Section 11.12 in IEEE 802.16REVd/D5-2004"
			::= { wmanIfBsChMeasurementEntry 5 }

		
		-- 1.3.6.1.2.1.10.184.1.1.2.3.1.1.6
		wmanIfBsBasicReport OBJECT-TYPE
			SYNTAX BITS
				{
				wirelessHuman(0),
				unknownTransmission(1),
				primaryUser(2),
				channegNotMeasured(3)
				}
			MAX-ACCESS read-only
			STATUS deprecated
			DESCRIPTION
				"Bit #0: WirelessHUMAN detected on the channel
				Bit #1: Unknown transmissions detected on the channel
				Bit #2: Primary User detected on the channel
				Bit #3: Unmeasured. Channel not measured"
			REFERENCE
				"Section 11.12 in IEEE 802.16REVd/D5-2004"
			::= { wmanIfBsChMeasurementEntry 6 }

		
		-- 1.3.6.1.2.1.10.184.1.1.2.3.1.1.7
		wmanIfBsMeanCinrReport OBJECT-TYPE
			SYNTAX INTEGER
			MAX-ACCESS read-only
			STATUS deprecated
			DESCRIPTION
				"Mean CINR report."
			REFERENCE
				"Section 8.2.2, 8.3.8, 8.4.1, 11.12 in IEEE
				802.16REVd/D5-2004"
			::= { wmanIfBsChMeasurementEntry 7 }

		
		-- 1.3.6.1.2.1.10.184.1.1.2.3.1.1.8
		wmanIfBsMeanRssiReport OBJECT-TYPE
			SYNTAX INTEGER
			MAX-ACCESS read-only
			STATUS deprecated
			DESCRIPTION
				"Mean RSSI report."
			REFERENCE
				"Section 8.2.2, 8.3.8, 8.4.1, 11.12 in IEEE
				802.16REVd/D5-2004"
			::= { wmanIfBsChMeasurementEntry 8 }

		
		-- 1.3.6.1.2.1.10.184.1.1.2.3.1.1.9
		wmanIfBsStdDeviationCinrReport OBJECT-TYPE
			SYNTAX INTEGER
			MAX-ACCESS read-only
			STATUS deprecated
			DESCRIPTION
				"Standard deviation CINR report."
			REFERENCE
				"Section 8.2.2, 8.3.8, 8.4.1, 11.12 in IEEE
				802.16REVd/D5-2004"
			::= { wmanIfBsChMeasurementEntry 9 }

		
		-- 1.3.6.1.2.1.10.184.1.1.2.3.1.1.10
		wmanIfBsStdDeviationRssiReport OBJECT-TYPE
			SYNTAX INTEGER
			MAX-ACCESS read-only
			STATUS deprecated
			DESCRIPTION
				"Standard deviation RSSI report."
			REFERENCE
				"Section 8.2.2, 8.3.8, 8.4.1, 11.12 in IEEE
				802.16REVd/D5-2004"
			::= { wmanIfBsChMeasurementEntry 10 }

		
		-- 1.3.6.1.2.1.10.184.1.1.2.3.2
		wmanIfBsFecCounterTable OBJECT-TYPE
			SYNTAX SEQUENCE OF WmanIfBsFecCounterEntry
			MAX-ACCESS not-accessible
			STATUS current
			DESCRIPTION
				"This table contains counters to capture corrected and
				uncorrected FEC errors detected on the upstream signal
				received from SSs."
			REFERENCE
				"Section 8.4.9 in IEEE 802.16REVd/D5-2004"
			::= { wmanIfBsStatisticCounter 2 }

		
		-- 1.3.6.1.2.1.10.184.1.1.2.3.2.1
		wmanIfBsFecCounterEntry OBJECT-TYPE
			SYNTAX WmanIfBsFecCounterEntry
			MAX-ACCESS not-accessible
			STATUS current
			DESCRIPTION
				"An entry will be created for each SS in the BS sector.
				The primary index is the ifIndex with ifType of propBWAp2Mp
				identifing the BS sector. wmanIfBsFecSsId identifies
				the SS from which the signal was received."
			INDEX { ifIndex, wmanIfBsFecSsId }
			::= { wmanIfBsFecCounterTable 1 }

		
		WmanIfBsFecCounterEntry ::=
			SEQUENCE { 
				wmanIfBsFecSsId
					Unsigned32,
				wmanIfBsFecCorrectedBytes
					Counter64,
				wmanIfBsFecUncorrectedBytes
					Counter64,
				wmanIfBsFecUncorrectedMacPdu
					Counter64,
				wmanIfBsFecResetCounter
					INTEGER
			 }

		-- 1.3.6.1.2.1.10.184.1.1.2.3.2.1.1
		wmanIfBsFecSsId OBJECT-TYPE
			SYNTAX Unsigned32 (1..4294967295)
			MAX-ACCESS not-accessible
			STATUS current
			DESCRIPTION
				"wmanIfBsFecIdIndex identifies the SS providing the
				FEC statistics."
			REFERENCE
				"Section 6.4.2.3.5 in IEEE 802.16REVd/D5-2004"
			::= { wmanIfBsFecCounterEntry 1 }

		
		-- 1.3.6.1.2.1.10.184.1.1.2.3.2.1.2
		wmanIfBsFecCorrectedBytes OBJECT-TYPE
			SYNTAX Counter64
			UNITS "bytes"
			MAX-ACCESS read-only
			STATUS current
			DESCRIPTION
				"Indicates the aggregation of corrected FEC errors in
				terms of the number of bytes."
			::= { wmanIfBsFecCounterEntry 2 }

		
		-- 1.3.6.1.2.1.10.184.1.1.2.3.2.1.3
		wmanIfBsFecUncorrectedBytes OBJECT-TYPE
			SYNTAX Counter64
			UNITS "bytes"
			MAX-ACCESS read-only
			STATUS current
			DESCRIPTION
				"Indicates the aggregation of uncorrected FEC errors in
				terms of the number of bytes."
			::= { wmanIfBsFecCounterEntry 3 }

		
		-- 1.3.6.1.2.1.10.184.1.1.2.3.2.1.4
		wmanIfBsFecUncorrectedMacPdu OBJECT-TYPE
			SYNTAX Counter64
			UNITS "MAC PDU"
			MAX-ACCESS read-only
			STATUS current
			DESCRIPTION
				"Indicates the aggregation of uncorrected MAC PDUs."
			::= { wmanIfBsFecCounterEntry 4 }

		
		-- 1.3.6.1.2.1.10.184.1.1.2.3.2.1.5
		wmanIfBsFecResetCounter OBJECT-TYPE
			SYNTAX INTEGER
				{
				null(0),
				resetCounter(1)
				}
			MAX-ACCESS read-write
			STATUS current
			DESCRIPTION
				"When SET this attribute to resetCounter(1), the
				corresponding entry of FEC counters will be reset.
				A GET operation performed on this object will always
				return null(0). The counter is normally reset after
				the packet count information is retrieved. "
			::= { wmanIfBsFecCounterEntry 5 }

		
--  Base station PKM group
-- wmanIfBsPkmObjects contain the Base Station Privacy Sublayer objects
		-- 1.3.6.1.2.1.10.184.1.1.3
		wmanIfBsPkmObjects OBJECT IDENTIFIER ::= { wmanIfBsObjects 3 }

		
--  Table wmanIfBsPkmBaseTable
-- 
		-- 1.3.6.1.2.1.10.184.1.1.3.1
		wmanIfBsPkmBaseTable OBJECT-TYPE
			SYNTAX SEQUENCE OF WmanIfBsPkmBaseEntry
			MAX-ACCESS not-accessible
			STATUS current
			DESCRIPTION
				"This table describes the basic PKM attributes of each Base
				Station wireless interface."
			::= { wmanIfBsPkmObjects 1 }

		
		-- 1.3.6.1.2.1.10.184.1.1.3.1.1
		wmanIfBsPkmBaseEntry OBJECT-TYPE
			SYNTAX WmanIfBsPkmBaseEntry
			MAX-ACCESS not-accessible
			STATUS current
			DESCRIPTION
				"Each entry contains objects describing attributes of one
				BS wireless interface."
			INDEX { ifIndex }
			::= { wmanIfBsPkmBaseTable 1 }

		
		WmanIfBsPkmBaseEntry ::=
			SEQUENCE { 
				wmanIfBsPkmDefaultAuthLifetime
					Integer32,
				wmanIfBsPkmDefaultTEKLifetime
					Integer32,
				wmanIfBsPkmDefaultSelfSigManufCertTrust
					INTEGER,
				wmanIfBsPkmCheckCertValidityPeriods
					TruthValue,
				wmanIfBsPkmAuthentInfos
					Counter32,
				wmanIfBsPkmAuthRequests
					Counter32,
				wmanIfBsPkmAuthReplies
					Counter32,
				wmanIfBsPkmAuthRejects
					Counter32,
				wmanIfBsPkmAuthInvalids
					Counter32
			 }

		-- 1.3.6.1.2.1.10.184.1.1.3.1.1.1
		wmanIfBsPkmDefaultAuthLifetime OBJECT-TYPE
			SYNTAX Integer32 (86400..6048000)
			UNITS "seconds"
			MAX-ACCESS read-write
			STATUS current
			DESCRIPTION
				"The value of this object is the default lifetime, in
				seconds, the BS assigns to a new authorization key."
			REFERENCE
				"Table 341 in IEEE 802.16REVd/D5-2004"
			DEFVAL { 604800 }
			::= { wmanIfBsPkmBaseEntry 1 }

		
		-- 1.3.6.1.2.1.10.184.1.1.3.1.1.2
		wmanIfBsPkmDefaultTEKLifetime OBJECT-TYPE
			SYNTAX Integer32 (1800..604800)
			UNITS "seconds"
			MAX-ACCESS read-write
			STATUS current
			DESCRIPTION
				"The value of this object is the default lifetime, in
				seconds, the BS assigns to a new Traffic Encryption
				Key(TEK)."
			REFERENCE
				"Table 341 in IEEE 802.16REVd/D5-2004"
			DEFVAL { 43200 }
			::= { wmanIfBsPkmBaseEntry 2 }

		
		-- 1.3.6.1.2.1.10.184.1.1.3.1.1.3
		wmanIfBsPkmDefaultSelfSigManufCertTrust OBJECT-TYPE
			SYNTAX INTEGER
				{
				trusted(1),
				untrusted(2)
				}
			MAX-ACCESS read-write
			STATUS current
			DESCRIPTION
				"This object determines the default trust of all (new)
				self-signed manufacturer certificates obtained after
				setting the object."
			::= { wmanIfBsPkmBaseEntry 3 }

		
		-- 1.3.6.1.2.1.10.184.1.1.3.1.1.4
		wmanIfBsPkmCheckCertValidityPeriods OBJECT-TYPE
			SYNTAX TruthValue
			MAX-ACCESS read-write
			STATUS current
			DESCRIPTION
				"Setting this object to TRUE causes all certificates
				received? thereafter to have their validity periods (and
				their chain's validity periods) checked against the current
				time of day. A FALSE setting will cause all certificates
				received? Thereafter to not have their validity periods
				(nor their chain's validity periods) checked against the
				current time of day."
			::= { wmanIfBsPkmBaseEntry 4 }

		
		-- 1.3.6.1.2.1.10.184.1.1.3.1.1.5
		wmanIfBsPkmAuthentInfos OBJECT-TYPE
			SYNTAX Counter32
			MAX-ACCESS read-only
			STATUS current
			DESCRIPTION
				"The value of this object is the count of times the BS has
				received an Authentication Information message from any
				SS."
			::= { wmanIfBsPkmBaseEntry 5 }

		
		-- 1.3.6.1.2.1.10.184.1.1.3.1.1.6
		wmanIfBsPkmAuthRequests OBJECT-TYPE
			SYNTAX Counter32
			MAX-ACCESS read-only
			STATUS current
			DESCRIPTION
				"The value of this object is the count of times the BS has
				received an Authorization Request message from any SS"
			::= { wmanIfBsPkmBaseEntry 6 }

		
		-- 1.3.6.1.2.1.10.184.1.1.3.1.1.7
		wmanIfBsPkmAuthReplies OBJECT-TYPE
			SYNTAX Counter32
			MAX-ACCESS read-only
			STATUS current
			DESCRIPTION
				"The value of this object is the count of times the BS has
				transmitted an Authorization Reply message to any SS."
			::= { wmanIfBsPkmBaseEntry 7 }

		
		-- 1.3.6.1.2.1.10.184.1.1.3.1.1.8
		wmanIfBsPkmAuthRejects OBJECT-TYPE
			SYNTAX Counter32
			MAX-ACCESS read-only
			STATUS current
			DESCRIPTION
				"The value of this object is the count of times the BS has
				transmitted an Authorization Reject message to any SS."
			::= { wmanIfBsPkmBaseEntry 8 }

		
		-- 1.3.6.1.2.1.10.184.1.1.3.1.1.9
		wmanIfBsPkmAuthInvalids OBJECT-TYPE
			SYNTAX Counter32
			MAX-ACCESS read-only
			STATUS current
			DESCRIPTION
				"The value of this object is the count of times the BS has
				transmitted an Authorization Invalid message to any SS."
			::= { wmanIfBsPkmBaseEntry 9 }

		
--  Table wmanIfBsPkmAuthTable
-- 
		-- 1.3.6.1.2.1.10.184.1.1.3.2
		wmanIfBsPkmAuthTable OBJECT-TYPE
			SYNTAX SEQUENCE OF WmanIfBsPkmAuthEntry
			MAX-ACCESS not-accessible
			STATUS current
			DESCRIPTION
				"This table describes the attributes of each SS
				authorization association. The BS maintains one
				authorization association with each Baseline 
				Privacy-enabled SS on each BS wireless interface."
			::= { wmanIfBsPkmObjects 2 }

		
		-- 1.3.6.1.2.1.10.184.1.1.3.2.1
		wmanIfBsPkmAuthEntry OBJECT-TYPE
			SYNTAX WmanIfBsPkmAuthEntry
			MAX-ACCESS not-accessible
			STATUS current
			DESCRIPTION
				"Each entry contains objects describing attributes of one
				authorization association. The BS MUST create one entry per
				SS per wireless interface, based on the receipt of an
				Authorization Request message, and MUST not delete the
				entry before the SS authorization permanently expires."
			INDEX { ifIndex, wmanIfBsPkmAuthSsMacAddress }
			::= { wmanIfBsPkmAuthTable 1 }

		
		WmanIfBsPkmAuthEntry ::=
			SEQUENCE { 
				wmanIfBsPkmAuthSsMacAddress
					VariableMacAddress,
				wmanIfBsPkmAuthSsPublicKey
					OCTET STRING,
				wmanIfBsPkmAuthSsKeySequenceNumber
					Integer32,
				wmanIfBsPkmAuthSsExpiresOld
					DateAndTime,
				wmanIfBsPkmAuthSsExpiresNew
					DateAndTime,
				wmanIfBsPkmAuthSsLifetime
					Integer32,
				wmanIfBsPkmAuthSsReset
					INTEGER,
				wmanIfBsPkmAuthSsInfos
					Counter64,
				wmanIfBsPkmAuthSsRequests
					Counter64,
				wmanIfBsPkmAuthSsReplies
					Counter64,
				wmanIfBsPkmAuthSsRejects
					Counter64,
				wmanIfBsPkmAuthSsInvalids
					Counter64,
				wmanIfBsPkmAuthRejectErrorCode
					INTEGER,
				wmanIfBsPkmAuthRejectErrorString
					SnmpAdminString,
				wmanIfBsPkmAuthInvalidErrorCode
					INTEGER,
				wmanIfBsPkmAuthInvalidErrorString
					SnmpAdminString,
				wmanIfBsPkmAuthPrimarySAId
					Integer32,
				wmanIfBsPkmAuthBpkmSsCertValid
					INTEGER,
				wmanIfBsPkmAuthBpkmSsCert
					OCTET STRING
			 }

		-- 1.3.6.1.2.1.10.184.1.1.3.2.1.1
		wmanIfBsPkmAuthSsMacAddress OBJECT-TYPE
			SYNTAX VariableMacAddress
			MAX-ACCESS not-accessible
			STATUS current
			DESCRIPTION
				"The value of this object is the physical address of the SS
				to which the authorization association applies."
			::= { wmanIfBsPkmAuthEntry 1 }

		
		-- 1.3.6.1.2.1.10.184.1.1.3.2.1.2
		wmanIfBsPkmAuthSsPublicKey OBJECT-TYPE
			SYNTAX OCTET STRING (SIZE (140))
			MAX-ACCESS read-only
			STATUS current
			DESCRIPTION
				"The value of this object is a DER-encoded RSAPublicKey
				ASN.1 type string, as defined in the RSA Encryption
				Standard (PKCS #1) [10], corresponding to the public key of
				the SS. The 74, 106, 140, 204, and 270 byte key encoding
				lengths correspond to 512 bit, 768 bit, 1024 bit, 1536 bit,
				and 2048 public moduli respectively. This is a zero-length
				string if the BS does not retain the public key."
			::= { wmanIfBsPkmAuthEntry 2 }

		
		-- 1.3.6.1.2.1.10.184.1.1.3.2.1.3
		wmanIfBsPkmAuthSsKeySequenceNumber OBJECT-TYPE
			SYNTAX Integer32 (0..15)
			MAX-ACCESS read-only
			STATUS current
			DESCRIPTION
				"The value of this object is the most recent authorization
				key sequence number for this SS."
			::= { wmanIfBsPkmAuthEntry 3 }

		
		-- 1.3.6.1.2.1.10.184.1.1.3.2.1.4
		wmanIfBsPkmAuthSsExpiresOld OBJECT-TYPE
			SYNTAX DateAndTime
			MAX-ACCESS read-only
			STATUS current
			DESCRIPTION
				"The value of this object is the actual clock time for
				expiration of the immediate predecessor of the most recent
				authorization key for this FSM. If this FSM has only one
				authorization key, then the value is the time of activation
				of this FSM."
			::= { wmanIfBsPkmAuthEntry 4 }

		
		-- 1.3.6.1.2.1.10.184.1.1.3.2.1.5
		wmanIfBsPkmAuthSsExpiresNew OBJECT-TYPE
			SYNTAX DateAndTime
			MAX-ACCESS read-only
			STATUS current
			DESCRIPTION
				"The value of this object is the actual clock time for
				expiration of the most recent authorization key for this
				FSM"
			::= { wmanIfBsPkmAuthEntry 5 }

		
		-- 1.3.6.1.2.1.10.184.1.1.3.2.1.6
		wmanIfBsPkmAuthSsLifetime OBJECT-TYPE
			SYNTAX Integer32 (86400..6048000)
			UNITS "seconds"
			MAX-ACCESS read-only
			STATUS current
			DESCRIPTION
				"The vaue of this object is the lifetime, in seconds, the
				BS assigns to an authorization key for this SS."
			REFERENCE
				"Table 341 in IEEE 802.16REVd/D5-2004"
			DEFVAL { 604800 }
			::= { wmanIfBsPkmAuthEntry 6 }

		
		-- 1.3.6.1.2.1.10.184.1.1.3.2.1.7
		wmanIfBsPkmAuthSsReset OBJECT-TYPE
			SYNTAX INTEGER
				{
				noResetRequested(1),
				invalidateAuth(2),
				sendAuthInvalid(3),
				invalidateTeks(4)
				}
			MAX-ACCESS read-write
			STATUS current
			DESCRIPTION
				"Setting this object to invalidateAuth(2) causes the BS to
				invalidate the current SS authorization key(s), but not to
				transmit an Authorization Invalid message nor to invalidate
				unicast TEKs. Setting this object to sendAuthInvalid(3)
				causes the BS to invalidate the current SS authorization
				key(s), and to transmit an Authorization Invalid message to
				the SS, but not to invalidate unicast TEKs. Setting this
				object to invalidateTeks(4) causes the BS to invalidate the
				current SS authorization key(s), to transmit an
				Authorization Invalid message to the SS, and to
				invalidate all unicast TEKs associated with this SS
				authorization. Reading this object returns the 
				most-recently-set value of this object, or returns
				noResetRequested(1) if the object has not been set since
				the last BS reboot."
			::= { wmanIfBsPkmAuthEntry 7 }

		
		-- 1.3.6.1.2.1.10.184.1.1.3.2.1.8
		wmanIfBsPkmAuthSsInfos OBJECT-TYPE
			SYNTAX Counter64
			MAX-ACCESS read-only
			STATUS current
			DESCRIPTION
				"The value of this object is the count of times the BS has
				received an Authentication Information message from this 
				SS."
			::= { wmanIfBsPkmAuthEntry 8 }

		
		-- 1.3.6.1.2.1.10.184.1.1.3.2.1.9
		wmanIfBsPkmAuthSsRequests OBJECT-TYPE
			SYNTAX Counter64
			MAX-ACCESS read-only
			STATUS current
			DESCRIPTION
				"The value of this object is the count of times the BS has
				received an Authorization Request message from this SS."
			::= { wmanIfBsPkmAuthEntry 9 }

		
		-- 1.3.6.1.2.1.10.184.1.1.3.2.1.10
		wmanIfBsPkmAuthSsReplies OBJECT-TYPE
			SYNTAX Counter64
			MAX-ACCESS read-only
			STATUS current
			DESCRIPTION
				"The value of this object is the count of times the BS has
				transmitted an Authorization Reply message to this SS."
			::= { wmanIfBsPkmAuthEntry 10 }

		
		-- 1.3.6.1.2.1.10.184.1.1.3.2.1.11
		wmanIfBsPkmAuthSsRejects OBJECT-TYPE
			SYNTAX Counter64
			MAX-ACCESS read-only
			STATUS current
			DESCRIPTION
				"The value of this object is the count of times the BS has
				transmitted an Authorization Reject message to this SS."
			::= { wmanIfBsPkmAuthEntry 11 }

		
		-- 1.3.6.1.2.1.10.184.1.1.3.2.1.12
		wmanIfBsPkmAuthSsInvalids OBJECT-TYPE
			SYNTAX Counter64
			MAX-ACCESS read-only
			STATUS current
			DESCRIPTION
				"The value of this object is the count of times the BS has
				transmitted an Authorization Invalid message to this SS."
			::= { wmanIfBsPkmAuthEntry 12 }

		
		-- 1.3.6.1.2.1.10.184.1.1.3.2.1.13
		wmanIfBsPkmAuthRejectErrorCode OBJECT-TYPE
			SYNTAX INTEGER
				{
				noInformation(0),
				unauthorizedSs(1),
				unauthorizedSaid(2),
				permanentAuthorizationFailure(6)
				}
			MAX-ACCESS read-only
			STATUS current
			DESCRIPTION
				"The value of this object is the enumerated description of
				the Error-Code in most recent Authorization Reject message
				transmitted to the SS."
			REFERENCE
				"IEEE 802.16 standard; Table 371"
			::= { wmanIfBsPkmAuthEntry 13 }

		
		-- 1.3.6.1.2.1.10.184.1.1.3.2.1.14
		wmanIfBsPkmAuthRejectErrorString OBJECT-TYPE
			SYNTAX SnmpAdminString (SIZE (0..128))
			MAX-ACCESS read-only
			STATUS current
			DESCRIPTION
				"The value of this object is the Display-String in most
				recent Authorization Reject message transmitted to the SS.
				This is a zero length string if no Authorization Reject
				message has been transmitted to the SS."
			::= { wmanIfBsPkmAuthEntry 14 }

		
		-- 1.3.6.1.2.1.10.184.1.1.3.2.1.15
		wmanIfBsPkmAuthInvalidErrorCode OBJECT-TYPE
			SYNTAX INTEGER
				{
				noInformation(0),
				unauthorizedSs(1),
				unsolicited(3),
				invalidKeySequence(4),
				keyRequestAuthenticationFailure(5)
				}
			MAX-ACCESS read-only
			STATUS current
			DESCRIPTION
				"The value of this object is the enumerated description of
				the Error-Code in most recent Authorization Invalid message
				transmitted to the SS."
			REFERENCE
				"IEEE 802.16 standard; Table 371"
			::= { wmanIfBsPkmAuthEntry 15 }

		
		-- 1.3.6.1.2.1.10.184.1.1.3.2.1.16
		wmanIfBsPkmAuthInvalidErrorString OBJECT-TYPE
			SYNTAX SnmpAdminString (SIZE (0..128))
			MAX-ACCESS read-only
			STATUS current
			DESCRIPTION
				"The value of this object is the Display-String in most
				recent Authorization Invalid message transmitted to the SS.
				This is a zero length string if no Authorization Invalid
				message has been transmitted to the SS."
			::= { wmanIfBsPkmAuthEntry 16 }

		
		-- 1.3.6.1.2.1.10.184.1.1.3.2.1.17
		wmanIfBsPkmAuthPrimarySAId OBJECT-TYPE
			SYNTAX Integer32 (0..65536)
			MAX-ACCESS read-only
			STATUS current
			DESCRIPTION
				"The value of this object is the Primary Security
				Association identifier."
			REFERENCE
				"IEEE 802.16 standard; 11.9.7"
			::= { wmanIfBsPkmAuthEntry 17 }

		
		-- 1.3.6.1.2.1.10.184.1.1.3.2.1.18
		wmanIfBsPkmAuthBpkmSsCertValid OBJECT-TYPE
			SYNTAX INTEGER
				{
				unknown(0),
				validSsChained(1),
				validSsTrusted(2),
				invalidSsUntrusted(3),
				invalidCAUntrusted(4),
				invalidSsOther(5),
				invalidCAOther(6)
				}
			MAX-ACCESS read-only
			STATUS current
			DESCRIPTION
				"Contains the reason why a SS's certificate is deemed valid
				or invalid. Return unknown if the SS is running PKM mode.
				ValidSsChained means the certificate is valid because it
				chains to a valid certificate. ValidSsTrusted means the
				certificate is valid because it has been provisioned to be
				trusted. InvalidSsUntrusted means the certificate is
				invalid because it has been provisioned to be untrusted.
				InvalidCAUntrusted means the certificate is invalid
				because   it chains to an untrusted certificate.
				InvalidSsOther and InvalidCAOther refer to errors in
				parsing, validity periods, etc, which are attributable to
				the SS certificate or its chain respectively."
			::= { wmanIfBsPkmAuthEntry 18 }

		
		-- 1.3.6.1.2.1.10.184.1.1.3.2.1.19
		wmanIfBsPkmAuthBpkmSsCert OBJECT-TYPE
			SYNTAX OCTET STRING
			MAX-ACCESS read-only
			STATUS current
			DESCRIPTION
				"The X509 SS Certificate sent as part of a PKM
				Authorization Request."
			::= { wmanIfBsPkmAuthEntry 19 }

		
--  Table wmanIfBsPkmTEKTable
		-- 1.3.6.1.2.1.10.184.1.1.3.3
		wmanIfBsPkmTEKTable OBJECT-TYPE
			SYNTAX SEQUENCE OF WmanIfBsPkmTEKEntry
			MAX-ACCESS not-accessible
			STATUS current
			DESCRIPTION
				"This table describes the attributes of each Traffic
				Encryption Key (TEK) association. The BS maintains one TEK
				association per SAID on each BS wireless interface."
			::= { wmanIfBsPkmObjects 3 }

		
		-- 1.3.6.1.2.1.10.184.1.1.3.3.1
		wmanIfBsPkmTEKEntry OBJECT-TYPE
			SYNTAX WmanIfBsPkmTEKEntry
			MAX-ACCESS not-accessible
			STATUS current
			DESCRIPTION
				"Each entry contains objects describing attributes of one
				TEK association on a particular BS wireless interface. The
				BS MUST create one entry per SAID per wireless interface,
				based on the receipt of a Key Request message, and MUST not
				delete the entry before the SS authorization for the SAID
				permanently expires."
			INDEX { ifIndex, wmanIfBsPkmTEKSAId }
			::= { wmanIfBsPkmTEKTable 1 }

		
		WmanIfBsPkmTEKEntry ::=
			SEQUENCE { 
				wmanIfBsPkmTEKSAId
					Integer32,
				wmanIfBsPkmTEKSAType
					INTEGER,
				wmanIfBsPkmTEKDataEncryptAlg
					INTEGER,
				wmanIfBsPkmTEKDataAuthentAlg
					INTEGER,
				wmanIfBsPkmTEKEncryptAlg
					INTEGER,
				wmanIfBsPkmTEKLifetime
					Integer32,
				wmanIfBsPkmTEKKeySequenceNumber
					Integer32,
				wmanIfBsPkmTEKExpiresOld
					DateAndTime,
				wmanIfBsPkmTEKExpiresNew
					DateAndTime,
				wmanIfBsPkmTEKReset
					TruthValue,
				wmanIfBsPkmKeyRequests
					Counter32,
				wmanIfBsPkmKeyReplies
					Counter32,
				wmanIfBsPkmKeyRejects
					Counter32,
				wmanIfBsPkmTEKInvalids
					Counter32,
				wmanIfBsPkmKeyRejectErrorCode
					INTEGER,
				wmanIfBsPkmKeyRejectErrorString
					SnmpAdminString,
				wmanIfBsPkmTEKInvalidErrorCode
					INTEGER,
				wmanIfBsPkmTEKInvalidErrorString
					SnmpAdminString
			 }

		-- 1.3.6.1.2.1.10.184.1.1.3.3.1.1
		wmanIfBsPkmTEKSAId OBJECT-TYPE
			SYNTAX Integer32 (0..65536)
			MAX-ACCESS not-accessible
			STATUS current
			DESCRIPTION
				"The value of this object is the WiMAX Security Association
				ID (SAID)."
			REFERENCE
				"IEEE 802.16 standard; 11.9.7"
			::= { wmanIfBsPkmTEKEntry 1 }

		
		-- 1.3.6.1.2.1.10.184.1.1.3.3.1.2
		wmanIfBsPkmTEKSAType OBJECT-TYPE
			SYNTAX INTEGER
				{
				primarySA(0),
				staticSA(1),
				dynamicSA(2)
				}
			MAX-ACCESS read-only
			STATUS current
			DESCRIPTION
				"The value of this object is the type of security
				association. Dynamic does not apply to SSs running in PKM
				mode."
			REFERENCE
				"IEEE 802.16 standard; 11.9.18"
			::= { wmanIfBsPkmTEKEntry 2 }

		
		-- 1.3.6.1.2.1.10.184.1.1.3.3.1.3
		wmanIfBsPkmTEKDataEncryptAlg OBJECT-TYPE
			SYNTAX INTEGER
				{
				none(0),
				des56CbcMode(1)
				}
			MAX-ACCESS read-only
			STATUS current
			DESCRIPTION
				"The value of this object is the data encryption algorithm
				being utilized."
			REFERENCE
				"IEEE 802.16 standard; Table 301"
			::= { wmanIfBsPkmTEKEntry 3 }

		
		-- 1.3.6.1.2.1.10.184.1.1.3.3.1.4
		wmanIfBsPkmTEKDataAuthentAlg OBJECT-TYPE
			SYNTAX INTEGER { none(0) }
			MAX-ACCESS read-only
			STATUS current
			DESCRIPTION
				"The value of this object is the data authentication
				algorithm being utilized."
			REFERENCE
				"IEEE 802.16 standard; Table 302"
			::= { wmanIfBsPkmTEKEntry 4 }

		
		-- 1.3.6.1.2.1.10.184.1.1.3.3.1.5
		wmanIfBsPkmTEKEncryptAlg OBJECT-TYPE
			SYNTAX INTEGER
				{
				tripleDES(0),
				rsa1024(1)
				}
			MAX-ACCESS read-only
			STATUS current
			DESCRIPTION
				"The value of this object is the TEK key encryption
				algorithm being utilized."
			REFERENCE
				"IEEE 802.16 standard; Table 303"
			::= { wmanIfBsPkmTEKEntry 5 }

		
		-- 1.3.6.1.2.1.10.184.1.1.3.3.1.6
		wmanIfBsPkmTEKLifetime OBJECT-TYPE
			SYNTAX Integer32 (1800..604800)
			UNITS "seconds"
			MAX-ACCESS read-only
			STATUS current
			DESCRIPTION
				"The value of this object is the lifetime, in seconds, the
				BS assigns to keys for this TEK association."
			REFERENCE
				"Table 341 in IEEE 802.16REVd/D5-2004"
			DEFVAL { 43200 }
			::= { wmanIfBsPkmTEKEntry 6 }

		
		-- 1.3.6.1.2.1.10.184.1.1.3.3.1.7
		wmanIfBsPkmTEKKeySequenceNumber OBJECT-TYPE
			SYNTAX Integer32 (0..3)
			MAX-ACCESS read-only
			STATUS current
			DESCRIPTION
				"The value of this object is the most recent TEK key
				sequence number for this SAID."
			REFERENCE
				"IEEE 802.16 standard; 11.9.5"
			::= { wmanIfBsPkmTEKEntry 7 }

		
		-- 1.3.6.1.2.1.10.184.1.1.3.3.1.8
		wmanIfBsPkmTEKExpiresOld OBJECT-TYPE
			SYNTAX DateAndTime
			MAX-ACCESS read-only
			STATUS current
			DESCRIPTION
				"The value of this object is the actual clock time for
				expiration of the immediate predecessor of the most recent
				TEK for this FSM. If this FSM has only one TEK, then the
				value is the time of activation of this FSM."
			::= { wmanIfBsPkmTEKEntry 8 }

		
		-- 1.3.6.1.2.1.10.184.1.1.3.3.1.9
		wmanIfBsPkmTEKExpiresNew OBJECT-TYPE
			SYNTAX DateAndTime
			MAX-ACCESS read-only
			STATUS current
			DESCRIPTION
				"The value of this object is the actual clock time for
				expiration of the most recent TEK for this FSM."
			::= { wmanIfBsPkmTEKEntry 9 }

		
		-- 1.3.6.1.2.1.10.184.1.1.3.3.1.10
		wmanIfBsPkmTEKReset OBJECT-TYPE
			SYNTAX TruthValue
			MAX-ACCESS read-write
			STATUS current
			DESCRIPTION
				"Setting this object to TRUE causes the BS to invalidate
				the current active TEK(s) (plural due to key transition
				periods), and to generate a new TEK for the associated
				SAID; the BS MAY also generate an unsolicited TEK Invalid
				message, to optimize the TEK synchronization between the BS
				and the SS. Reading this object always returns   FALSE."
			::= { wmanIfBsPkmTEKEntry 10 }

		
		-- 1.3.6.1.2.1.10.184.1.1.3.3.1.11
		wmanIfBsPkmKeyRequests OBJECT-TYPE
			SYNTAX Counter32
			MAX-ACCESS read-only
			STATUS current
			DESCRIPTION
				"The value of this object is the count of times the BS has
				received a Key Request message."
			::= { wmanIfBsPkmTEKEntry 11 }

		
		-- 1.3.6.1.2.1.10.184.1.1.3.3.1.12
		wmanIfBsPkmKeyReplies OBJECT-TYPE
			SYNTAX Counter32
			MAX-ACCESS read-only
			STATUS current
			DESCRIPTION
				"The value of this object is the count of times the BS has
				transmitted a Key Reply message."
			::= { wmanIfBsPkmTEKEntry 12 }

		
		-- 1.3.6.1.2.1.10.184.1.1.3.3.1.13
		wmanIfBsPkmKeyRejects OBJECT-TYPE
			SYNTAX Counter32
			MAX-ACCESS read-only
			STATUS current
			DESCRIPTION
				"The value of this object is the count of times the BS has
				transmitted a Key Reject message."
			::= { wmanIfBsPkmTEKEntry 13 }

		
		-- 1.3.6.1.2.1.10.184.1.1.3.3.1.14
		wmanIfBsPkmTEKInvalids OBJECT-TYPE
			SYNTAX Counter32
			MAX-ACCESS read-only
			STATUS current
			DESCRIPTION
				"The value of this object is the count of times the BS has
				transmitted a TEK Invalid message."
			::= { wmanIfBsPkmTEKEntry 14 }

		
		-- 1.3.6.1.2.1.10.184.1.1.3.3.1.15
		wmanIfBsPkmKeyRejectErrorCode OBJECT-TYPE
			SYNTAX INTEGER
				{
				noInformation(0),
				unauthorizedSaid(2)
				}
			MAX-ACCESS read-only
			STATUS current
			DESCRIPTION
				"The value of this object is the enumerated; description of
				the Error-Code in the most recent Key Reject message sent
				in response to a Key Request for this SAID."
			REFERENCE
				"IEEE 802.16 standard; Table 371"
			::= { wmanIfBsPkmTEKEntry 15 }

		
		-- 1.3.6.1.2.1.10.184.1.1.3.3.1.16
		wmanIfBsPkmKeyRejectErrorString OBJECT-TYPE
			SYNTAX SnmpAdminString (SIZE (0..128))
			MAX-ACCESS read-only
			STATUS current
			DESCRIPTION
				"The value of this object is the Display-String in the most
				recent Key Reject message sent in response to a Key Request
				for this SAID. This is a zero length string if no Key
				Reject message has been received since reboot."
			::= { wmanIfBsPkmTEKEntry 16 }

		
		-- 1.3.6.1.2.1.10.184.1.1.3.3.1.17
		wmanIfBsPkmTEKInvalidErrorCode OBJECT-TYPE
			SYNTAX INTEGER
				{
				noInformation(0),
				invalidKeySequence(4)
				}
			MAX-ACCESS read-only
			STATUS current
			DESCRIPTION
				"The value of this object is the enumerated description of
				the Error-Code in the most recent TEK Invalid message sent
				in association with this SAID."
			REFERENCE
				"IEEE 802.16 standard; Table 371"
			::= { wmanIfBsPkmTEKEntry 17 }

		
		-- 1.3.6.1.2.1.10.184.1.1.3.3.1.18
		wmanIfBsPkmTEKInvalidErrorString OBJECT-TYPE
			SYNTAX SnmpAdminString (SIZE (0..128))
			MAX-ACCESS read-only
			STATUS current
			DESCRIPTION
				"The value of this object is the Display-String in the most
				recent TEK Invalid message sent in association with this
				SAID.  This is a zero length string if no TEK Invalid
				message has been received since reboot."
			::= { wmanIfBsPkmTEKEntry 18 }

		
--  Base station Notification Group
-- wmanIfBsNotificationObjects contains the BS SNMP Trap objects
		-- 1.3.6.1.2.1.10.184.1.1.4
		wmanIfBsNotification OBJECT IDENTIFIER ::= { wmanIfBsObjects 4 }

		
		-- 1.3.6.1.2.1.10.184.1.1.4.1
		wmanIfBsTrapDefinitions OBJECT IDENTIFIER ::= { wmanIfBsNotification 1 }

		
--  BS threshold Definitions
		-- 1.3.6.1.2.1.10.184.1.1.4.1.1
		wmanIfBsThresholdConfigTable OBJECT-TYPE
			SYNTAX SEQUENCE OF WmanIfBsThresholdConfigEntry
			MAX-ACCESS not-accessible
			STATUS current
			DESCRIPTION
				"This table contains threshold objects that can be set
				to detect the threshold crossing events."
			::= { wmanIfBsTrapDefinitions 1 }

		
		-- 1.3.6.1.2.1.10.184.1.1.4.1.1.1
		wmanIfBsThresholdConfigEntry OBJECT-TYPE
			SYNTAX WmanIfBsThresholdConfigEntry
			MAX-ACCESS not-accessible
			STATUS current
			DESCRIPTION
				"This table provides one row for each BS sector, and is
				indexed by ifIndex."
			INDEX { ifIndex }
			::= { wmanIfBsThresholdConfigTable 1 }

		
		WmanIfBsThresholdConfigEntry ::=
			SEQUENCE { 
				wmanIfBsRssiLowThreshold
					INTEGER,
				wmanIfBsRssiHighThreshold
					INTEGER,
				wmanIfBsTempLowAlarmThreshold
					INTEGER,
				wmanIfBsTempLowAlarmRestoredThreshold
					INTEGER,
				wmanIfBsTempHighAlarmThreshold
					INTEGER,
				wmanIfBsTempHighAlarmRestoredThreshold
					INTEGER
			 }

		-- 1.3.6.1.2.1.10.184.1.1.4.1.1.1.1
		wmanIfBsRssiLowThreshold OBJECT-TYPE
			SYNTAX INTEGER
			UNITS "dBm"
			MAX-ACCESS read-write
			STATUS current
			DESCRIPTION
				"Low threshold for generating the RSSI alarm trap.
				The detection of RSSI alarm will be disabled until the
				RSSI goes above wmanIfBsRssiHighThreshold"
			::= { wmanIfBsThresholdConfigEntry 1 }

		
		-- 1.3.6.1.2.1.10.184.1.1.4.1.1.1.2
		wmanIfBsRssiHighThreshold OBJECT-TYPE
			SYNTAX INTEGER
			UNITS "dBm"
			MAX-ACCESS read-write
			STATUS current
			DESCRIPTION
				"High threshold for generating a trap indicating
				the the RSSI alarm is restored."
			::= { wmanIfBsThresholdConfigEntry 2 }

		
		-- 1.3.6.1.2.1.10.184.1.1.4.1.1.1.3
		wmanIfBsTempLowAlarmThreshold OBJECT-TYPE
			SYNTAX INTEGER
			UNITS "degreeF"
			MAX-ACCESS read-write
			STATUS current
			DESCRIPTION
				"Low threshold for generating the temperature low alarm
				trap. The detection of temperature low alarm will be
				disabled until the temperature goes above
				wmanIfBsTempLowAlarmRestoredThreshold"
			::= { wmanIfBsThresholdConfigEntry 3 }

		
		-- 1.3.6.1.2.1.10.184.1.1.4.1.1.1.4
		wmanIfBsTempLowAlarmRestoredThreshold OBJECT-TYPE
			SYNTAX INTEGER
			UNITS "degreeF"
			MAX-ACCESS read-write
			STATUS current
			DESCRIPTION
				"Low threshold for generating a trap indicating
				the temperature alarm is restored."
			::= { wmanIfBsThresholdConfigEntry 4 }

		
		-- 1.3.6.1.2.1.10.184.1.1.4.1.1.1.5
		wmanIfBsTempHighAlarmThreshold OBJECT-TYPE
			SYNTAX INTEGER
			UNITS "degreeF"
			MAX-ACCESS read-write
			STATUS current
			DESCRIPTION
				"Low threshold for generating the temperature low alarm
				trap. The detection of temperature low alarm will be
				disabled until the temperature goes above
				wmanIfBsTempLowAlarmRestoredThreshold"
			::= { wmanIfBsThresholdConfigEntry 5 }

		
		-- 1.3.6.1.2.1.10.184.1.1.4.1.1.1.6
		wmanIfBsTempHighAlarmRestoredThreshold OBJECT-TYPE
			SYNTAX INTEGER
			UNITS "degreeF"
			MAX-ACCESS read-write
			STATUS current
			DESCRIPTION
				"High threshold for generating a trap indicating
				the temperature alarm is restored."
			::= { wmanIfBsThresholdConfigEntry 6 }

		
--  Subscriber station Notification Objects Definitions
		-- 1.3.6.1.2.1.10.184.1.1.4.1.2
		wmanIfBsSsNotificationObjectsTable OBJECT-TYPE
			SYNTAX SEQUENCE OF WmanIfBsSsNotificationObjectsEntry
			MAX-ACCESS not-accessible
			STATUS current
			DESCRIPTION
				"This table contains SS notification objects that have been
				reported by the trap."
			::= { wmanIfBsTrapDefinitions 2 }

		
		-- 1.3.6.1.2.1.10.184.1.1.4.1.2.1
		wmanIfBsSsNotificationObjectsEntry OBJECT-TYPE
			SYNTAX WmanIfBsSsNotificationObjectsEntry
			MAX-ACCESS not-accessible
			STATUS current
			DESCRIPTION
				"This table provides one row for each SS that has
				generated traps, and is double indexed by
				wmanIfBsTrapSsId and ifIndex for BS sector."
			INDEX { ifIndex, wmanIfBsTrapSsId }
			::= { wmanIfBsSsNotificationObjectsTable 1 }

		
		WmanIfBsSsNotificationObjectsEntry ::=
			SEQUENCE { 
				wmanIfBsTrapSsId
					Unsigned32,
				wmanIfBsSsNotMacAddr
					MacAddress,
				wmanIfBsSsStatusValue
					INTEGER,
				wmanIfBsSsStatusInfo
					OCTET STRING,
				wmanIfBsDynamicServiceType
					INTEGER,
				wmanIfBsDynamicServiceFailReason
					OCTET STRING,
				wmanIfBsSsRssiStatus
					INTEGER,
				wmanIfBsSsRssiStatusInfo
					OCTET STRING
			 }

		-- 1.3.6.1.2.1.10.184.1.1.4.1.2.1.1
		wmanIfBsTrapSsId OBJECT-TYPE
			SYNTAX Unsigned32 (1..4294967295)
			MAX-ACCESS read-only
			STATUS current
			DESCRIPTION
				"wmanIfBsTrapSsId identifies the entry in
				wmanIfBsSsNotificationObjectsTable."
			::= { wmanIfBsSsNotificationObjectsEntry 1 }

		
		-- 1.3.6.1.2.1.10.184.1.1.4.1.2.1.2
		wmanIfBsSsNotMacAddr OBJECT-TYPE
			SYNTAX MacAddress
			MAX-ACCESS read-only
			STATUS current
			DESCRIPTION
				"The MAC address of the SS, reporing the notofiation."
			::= { wmanIfBsSsNotificationObjectsEntry 2 }

		
		-- 1.3.6.1.2.1.10.184.1.1.4.1.2.1.3
		wmanIfBsSsStatusValue OBJECT-TYPE
			SYNTAX INTEGER
				{
				ssInitRangingSucc(1),
				ssInitRangingFail(2),
				ssRegistered(3),
				ssRegistrationFail(4),
				ssDeregistered(5),
				ssBasicCapabilitySucc(6),
				ssBasicCapabilityFail(7),
				ssAuthorizationSucc(8),
				ssAuthorizationFail(9),
				tftpSucc(10),
				tftpFail(11),
				sfCreationSucc(12),
				sfCreationFail(13)
				}
			MAX-ACCESS read-only
			STATUS current
			DESCRIPTION
				"This object indicates the status of a SS, as it goes 
				through network entry and initialization procedure."
			::= { wmanIfBsSsNotificationObjectsEntry 3 }

		
		-- 1.3.6.1.2.1.10.184.1.1.4.1.2.1.4
		wmanIfBsSsStatusInfo OBJECT-TYPE
			SYNTAX OCTET STRING
			MAX-ACCESS read-only
			STATUS current
			DESCRIPTION
				"This object indicates the reason of SS's status change."
			::= { wmanIfBsSsNotificationObjectsEntry 4 }

		
		-- 1.3.6.1.2.1.10.184.1.1.4.1.2.1.5
		wmanIfBsDynamicServiceType OBJECT-TYPE
			SYNTAX INTEGER
				{
				bsSfCreationReq(1),
				bsSfCreationRsp(2),
				bsSfCreationAck(3)
				}
			MAX-ACCESS read-only
			STATUS current
			DESCRIPTION
				"This object indicates the dynamic service flow
				creation command type."
			::= { wmanIfBsSsNotificationObjectsEntry 5 }

		
		-- 1.3.6.1.2.1.10.184.1.1.4.1.2.1.6
		wmanIfBsDynamicServiceFailReason OBJECT-TYPE
			SYNTAX OCTET STRING
			MAX-ACCESS read-only
			STATUS current
			DESCRIPTION
				"This object indicates the reason why the service flow
				cration has failed."
			::= { wmanIfBsSsNotificationObjectsEntry 6 }

		
		-- 1.3.6.1.2.1.10.184.1.1.4.1.2.1.7
		wmanIfBsSsRssiStatus OBJECT-TYPE
			SYNTAX INTEGER
				{
				bsRssiAlarm(1),
				bsRssiNoAlarm(2)
				}
			MAX-ACCESS read-only
			STATUS current
			DESCRIPTION
				"A RSSI alarm is generated if the RSSI is lower than
				wmanIfBsLowRssiThreshold."
			::= { wmanIfBsSsNotificationObjectsEntry 7 }

		
		-- 1.3.6.1.2.1.10.184.1.1.4.1.2.1.8
		wmanIfBsSsRssiStatusInfo OBJECT-TYPE
			SYNTAX OCTET STRING
			MAX-ACCESS read-only
			STATUS current
			DESCRIPTION
				"This object indicates the reason why RSSI alarm is
				generated."
			::= { wmanIfBsSsNotificationObjectsEntry 8 }

		
--  Subscriber station Notification Trap Definitions        
		-- 1.3.6.1.2.1.10.184.1.1.4.1.3
		wmanBsSsStatusNotificationTrap NOTIFICATION-TYPE
			OBJECTS { ifIndex, wmanIfBsTrapSsId, wmanIfBsSsNotMacAddr, wmanIfBsSsStatusValue, wmanIfBsSsStatusInfo
				 }
			STATUS current
			DESCRIPTION 
				"This trap reports the status of a SS. Based on this
				notification the NMS will issue an alarm with certain
				severity depending on the status and the reason received."
			::= { wmanIfBsTrapDefinitions 3 }

		
		-- 1.3.6.1.2.1.10.184.1.1.4.1.4
		wmanBsSsDynamicServiceFailTrap NOTIFICATION-TYPE
			OBJECTS { ifIndex, wmanIfBsTrapSsId, wmanIfBsSsNotMacAddr, wmanIfBsDynamicServiceType, wmanIfBsDynamicServiceFailReason
				 }
			STATUS current
			DESCRIPTION 
				"An event to report the failure of a dynamic service
				operation happened during the dynamic services process
				and detected in the Bs side."
			::= { wmanIfBsTrapDefinitions 4 }

		
		-- 1.3.6.1.2.1.10.184.1.1.4.1.5
		wmanBsSsRssiStatusChangeTrap NOTIFICATION-TYPE
			OBJECTS { ifIndex, wmanIfBsTrapSsId, wmanIfBsSsNotMacAddr, wmanIfBsSsRssiStatus, wmanIfBsSsRssiStatusInfo
				 }
			STATUS current
			DESCRIPTION 
				"An event to report that the uplink RSSI is below
				wmanIfBsLowRssiThreshold, or above
				wmanIfBsHighRssiThreshold after restore."
			::= { wmanIfBsTrapDefinitions 5 }

		
		-- 1.3.6.1.2.1.10.184.1.1.4.1.6
		wmanBsSsBPKMFailTrap NOTIFICATION-TYPE
			OBJECTS { wmanIfBsSsNotMacAddr }
			STATUS current
			DESCRIPTION 
				"An event to report the failure of a BPKM operation."
			::= { wmanIfBsTrapDefinitions 6 }

		
--  Base station Notification Object Definitions
		-- 1.3.6.1.2.1.10.184.1.1.4.1.7
		wmanIfBsNotificationObjectsTable OBJECT-TYPE
			SYNTAX SEQUENCE OF WmanIfBsNotificationObjectsEntry
			MAX-ACCESS not-accessible
			STATUS current
			DESCRIPTION
				"This table contains BS notification objects that have been 
				reported by the trap."
			::= { wmanIfBsTrapDefinitions 7 }

		
		-- 1.3.6.1.2.1.10.184.1.1.4.1.7.1
		wmanIfBsNotificationObjectsEntry OBJECT-TYPE
			SYNTAX WmanIfBsNotificationObjectsEntry
			MAX-ACCESS not-accessible
			STATUS current
			DESCRIPTION
				"This table provides one row for each BS sector that has
				generated traps, and is indexed by ifIndex."
			INDEX { ifIndex }
			::= { wmanIfBsNotificationObjectsTable 1 }

		
		WmanIfBsNotificationObjectsEntry ::=
			SEQUENCE { 
				wmanIfBsPowerStatus
					INTEGER,
				wmanIfBsFanStatus
					INTEGER,
				wmanIfBsTemperatureStatus
					INTEGER,
				wmanIfBsPowerStatusInfo
					OCTET STRING,
				wmanIfBsFanStatusInfo
					OCTET STRING,
				wmanIfBsTemperatureStatusInfo
					OCTET STRING
			 }

		-- 1.3.6.1.2.1.10.184.1.1.4.1.7.1.1
		wmanIfBsPowerStatus OBJECT-TYPE
			SYNTAX INTEGER
				{
				priOnSecStandby(0),
				secOnPriStandby(1),
				priOnSecFailed(2),
				secOnPriFailed(3)
				}
			MAX-ACCESS read-only
			STATUS current
			DESCRIPTION
				"Describes the status of the power supply in BS."
			::= { wmanIfBsNotificationObjectsEntry 1 }

		
		-- 1.3.6.1.2.1.10.184.1.1.4.1.7.1.2
		wmanIfBsFanStatus OBJECT-TYPE
			SYNTAX INTEGER
				{
				fanFail(1),
				fanSucc(2)
				}
			MAX-ACCESS read-only
			STATUS current
			DESCRIPTION
				"Describes the status of the fan in BS."
			::= { wmanIfBsNotificationObjectsEntry 2 }

		
		-- 1.3.6.1.2.1.10.184.1.1.4.1.7.1.3
		wmanIfBsTemperatureStatus OBJECT-TYPE
			SYNTAX INTEGER
				{
				lowTempReached(1),
				highTempReached(2),
				temperatureNormal(3)
				}
			MAX-ACCESS read-only
			STATUS current
			DESCRIPTION
				"lowTempReached event is generated when temperature goes
				below wmanIfBsTempLowAlarmThreshold.
				temperatureNormal event is generated when temperature
				goes above wmanIfBsTempLowAlarmRestoredThreshold or
				below wmanIfBsTempHighAlarmRestoredThreshold after alarm.
				highTempReached event is generated when temperature goes
				above wmanIfBsTempHighAlarmThreshold."
			::= { wmanIfBsNotificationObjectsEntry 3 }

		
		-- 1.3.6.1.2.1.10.184.1.1.4.1.7.1.4
		wmanIfBsPowerStatusInfo OBJECT-TYPE
			SYNTAX OCTET STRING
			MAX-ACCESS read-only
			STATUS current
			DESCRIPTION
				"Display the power supply ststus in text form."
			::= { wmanIfBsNotificationObjectsEntry 4 }

		
		-- 1.3.6.1.2.1.10.184.1.1.4.1.7.1.5
		wmanIfBsFanStatusInfo OBJECT-TYPE
			SYNTAX OCTET STRING
			MAX-ACCESS read-only
			STATUS current
			DESCRIPTION
				"Display the fan ststus in text form."
			::= { wmanIfBsNotificationObjectsEntry 5 }

		
		-- 1.3.6.1.2.1.10.184.1.1.4.1.7.1.6
		wmanIfBsTemperatureStatusInfo OBJECT-TYPE
			SYNTAX OCTET STRING
			MAX-ACCESS read-only
			STATUS current
			DESCRIPTION
				"Display the temperature ststus in text form."
			::= { wmanIfBsNotificationObjectsEntry 6 }

		
--  Base station Notification Trap Definitions
		-- 1.3.6.1.2.1.10.184.1.1.4.1.8
		wmanBsPowerStatusChangeTrap NOTIFICATION-TYPE
			OBJECTS { wmanIfBsPowerStatus, wmanIfBsPowerStatusInfo }
			STATUS current
			DESCRIPTION 
				"An event to report a change in the status of the power
				supply in BS. Typically it represents a failure."
			::= { wmanIfBsTrapDefinitions 8 }

		
		-- 1.3.6.1.2.1.10.184.1.1.4.1.9
		wmanBsFanStatusTrap NOTIFICATION-TYPE
			OBJECTS { wmanIfBsFanStatus, wmanIfBsFanStatusInfo }
			STATUS current
			DESCRIPTION 
				"An event to report the status of the fan inside the BS."
			::= { wmanIfBsTrapDefinitions 9 }

		
		-- 1.3.6.1.2.1.10.184.1.1.4.1.10
		wmanBsTemperatureChangeTrap NOTIFICATION-TYPE
			OBJECTS { wmanIfBsTemperatureStatus, wmanIfBsTemperatureStatusInfo }
			STATUS current
			DESCRIPTION 
				"An alarm event will be generated when the temperature goes
				above wmanIfBsTempHighAlarmThreshold or below
				wmanIfBsTempLowAlarmThreshold. An event reporting the alarm
				has disappeared when the temperature goes below
				wmanIfBsTempHighAlarmRestoredThreshold or above
				wmanIfBsTempLowAlarmRestoredThreshold."
			::= { wmanIfBsTrapDefinitions 10 }

		
		-- 1.3.6.1.2.1.10.184.1.1.4.2
		wmanIfBsTrapControl OBJECT IDENTIFIER ::= { wmanIfBsNotification 2 }

		
		-- 1.3.6.1.2.1.10.184.1.1.4.2.1
		wmanIfBsTrapControlRegister OBJECT-TYPE
			SYNTAX BITS
				{
				wmanBsSsStatusNotification(0),
				wmanBsSsDynamicServiceFail(1),
				wmanBsPowerStatusChange(2),
				wmanBsFanStatusChange(3),
				wmanBsTemperatureChange(4),
				wmanBsSsRssiStatusChange(5),
				wmanBsSsBPKMFail(6)
				}
			MAX-ACCESS read-write
			STATUS current
			DESCRIPTION
				"The object is used to enable Base Station traps. From left
				to right, the set bit indicates the corresponding Base 
				Station trap is enabled."
			::= { wmanIfBsTrapControl 1 }

		
		-- 1.3.6.1.2.1.10.184.1.2
		wmanIfSsObjects OBJECT IDENTIFIER ::= { wmanIfMibObjects 2 }

		
--  SS object group – containing tables and objects to be implemented in 
-- the Subscriber station
-- 
-- wmanIfSsCps contain the Base Station Common Part Sublayer objects
		-- 1.3.6.1.2.1.10.184.1.2.1
		wmanIfSsCps OBJECT IDENTIFIER ::= { wmanIfSsObjects 1 }

		
		-- 1.3.6.1.2.1.10.184.1.2.1.1
		wmanIfSsConfigFileEncodingTable OBJECT-TYPE
			SYNTAX SEQUENCE OF WmanIfSsConfigFileEncodingEntry
			MAX-ACCESS not-accessible
			STATUS current
			DESCRIPTION
				"This table contains configuration file encoding
				information of the SS."
			REFERENCE
				"Section 11.2 in IEEE 802.16REVd/D5-2004"
			::= { wmanIfSsCps 1 }

		
		-- 1.3.6.1.2.1.10.184.1.2.1.1.1
		wmanIfSsConfigFileEncodingEntry OBJECT-TYPE
			SYNTAX WmanIfSsConfigFileEncodingEntry
			MAX-ACCESS not-accessible
			STATUS current
			DESCRIPTION
				"This table has only one entry, and is indexed
				by ifIndex."
			INDEX { ifIndex }
			::= { wmanIfSsConfigFileEncodingTable 1 }

		
		WmanIfSsConfigFileEncodingEntry ::=
			SEQUENCE { 
				wmanIfSsMicConfigSetting
					OCTET STRING,
				wmanIfSsVendorId
					OCTET STRING,
				wmanIfSsHwId
					OCTET STRING,
				wmanIfSsSwVersion
					OCTET STRING,
				wmanIfSsUpgradeFileName
					OCTET STRING,
				wmanIfSsSwUpgradeTftpServer
					InetAddress,
				wmanIfSsTftpServerTimeStamp
					DateAndTime
			 }

		-- 1.3.6.1.2.1.10.184.1.2.1.1.1.1
		wmanIfSsMicConfigSetting OBJECT-TYPE
			SYNTAX OCTET STRING (SIZE (20))
			MAX-ACCESS read-only
			STATUS current
			DESCRIPTION
				"The value field contains the SS MIC code. This is used
				to detect unauthorized modification or corruption of
				the configuration file."
			::= { wmanIfSsConfigFileEncodingEntry 1 }

		
		-- 1.3.6.1.2.1.10.184.1.2.1.1.1.2
		wmanIfSsVendorId OBJECT-TYPE
			SYNTAX OCTET STRING (SIZE (3))
			MAX-ACCESS read-only
			STATUS current
			DESCRIPTION
				"This value identifies the managed SS vendor to which the
				software upgrade is to be applied."
			::= { wmanIfSsConfigFileEncodingEntry 2 }

		
		-- 1.3.6.1.2.1.10.184.1.2.1.1.1.3
		wmanIfSsHwId OBJECT-TYPE
			SYNTAX OCTET STRING
			MAX-ACCESS read-only
			STATUS current
			DESCRIPTION
				"This value identifies the hardware version to which the
				software upgrade is to be applied."
			::= { wmanIfSsConfigFileEncodingEntry 3 }

		
		-- 1.3.6.1.2.1.10.184.1.2.1.1.1.4
		wmanIfSsSwVersion OBJECT-TYPE
			SYNTAX OCTET STRING
			MAX-ACCESS read-only
			STATUS current
			DESCRIPTION
				"This value identifies the software version of the software
				upgrade file. The value is administered by the vendor
				identifed in the Vendor ID field. It should be defined by
				the vendor to be unique with respect to a given hardware
				ID."
			::= { wmanIfSsConfigFileEncodingEntry 4 }

		
		-- 1.3.6.1.2.1.10.184.1.2.1.1.1.5
		wmanIfSsUpgradeFileName OBJECT-TYPE
			SYNTAX OCTET STRING
			MAX-ACCESS read-only
			STATUS current
			DESCRIPTION
				"The filename is a fully qualified directory path
				name which is in a format appropriate to the server."
			::= { wmanIfSsConfigFileEncodingEntry 5 }

		
		-- 1.3.6.1.2.1.10.184.1.2.1.1.1.6
		wmanIfSsSwUpgradeTftpServer OBJECT-TYPE
			SYNTAX InetAddress
			MAX-ACCESS read-only
			STATUS current
			DESCRIPTION
				"This object is the IP address of the TFTP server on
				which the software upgrade file for the SS resides."
			::= { wmanIfSsConfigFileEncodingEntry 6 }

		
		-- 1.3.6.1.2.1.10.184.1.2.1.1.1.7
		wmanIfSsTftpServerTimeStamp OBJECT-TYPE
			SYNTAX DateAndTime
			MAX-ACCESS read-only
			STATUS current
			DESCRIPTION
				"This is the sending time of the configuration file in
				seconds. The definition of time is as in IETF RFC 868."
			::= { wmanIfSsConfigFileEncodingEntry 7 }

		
--  wmanIfSsConfigurationTable contains global parameters for SS      
		-- 1.3.6.1.2.1.10.184.1.2.1.2
		wmanIfSsConfigurationTable OBJECT-TYPE
			SYNTAX SEQUENCE OF WmanIfSsConfigurationEntry
			MAX-ACCESS not-accessible
			STATUS current
			DESCRIPTION
				"This table contains one row for the SS system
				parameters."
			::= { wmanIfSsCps 2 }

		
		-- 1.3.6.1.2.1.10.184.1.2.1.2.1
		wmanIfSsConfigurationEntry OBJECT-TYPE
			SYNTAX WmanIfSsConfigurationEntry
			MAX-ACCESS not-accessible
			STATUS current
			DESCRIPTION
				"This table is indexed by ifIndex."
			INDEX { ifIndex }
			::= { wmanIfSsConfigurationTable 1 }

		
		WmanIfSsConfigurationEntry ::=
			SEQUENCE { 
				wmanIfSsLostDLMapInterval
					INTEGER,
				wmanIfSsLostULMapInterval
					INTEGER,
				wmanIfSsContentionRangRetries
					INTEGER,
				wmanIfSsRequestRetries
					INTEGER,
				wmanIfSsRegRequestRetries
					INTEGER,
				wmanIfSsTftpBackoffStart
					INTEGER,
				wmanIfSsTftpBackoffEnd
					INTEGER,
				wmanIfSsTftpRequestRetries
					INTEGER,
				wmanIfSsTftpDownloadRetries
					INTEGER,
				wmanIfSsTftpWait
					INTEGER,
				wmanIfSsToDRetries
					INTEGER,
				wmanIfSsToDRetryPeriod
					INTEGER,
				wmanIfSsT1Timeout
					INTEGER,
				wmanIfSsT2Timeout
					INTEGER,
				wmanIfSsT3Timeout
					INTEGER,
				wmanIfSsT4Timeout
					INTEGER,
				wmanIfSsT6Timeout
					INTEGER,
				wmanIfSsT12Timeout
					INTEGER,
				wmanIfSsT14Timeout
					INTEGER,
				wmanIfSsT16Timeout
					INTEGER,
				wmanIfSsT18Timeout
					INTEGER,
				wmanIfSsT19Timeout
					INTEGER,
				wmanIfSsT20Timeout
					INTEGER,
				wmanIfSsT21Timeout
					INTEGER,
				wmanIfSsSBCRequestRetries
					INTEGER,
				wmanIfSsTftpCpltRetries
					INTEGER,
				wmanIfSsT26Timeout
					INTEGER,
				wmanIfSsDLManagProcTime
					INTEGER
			 }

		-- 1.3.6.1.2.1.10.184.1.2.1.2.1.1
		wmanIfSsLostDLMapInterval OBJECT-TYPE
			SYNTAX INTEGER (0..600)
			UNITS "milliseconds"
			MAX-ACCESS read-write
			STATUS current
			DESCRIPTION
				"Time since last received DL-MAP message before downlink
				synchronization is considered lost in ms."
			::= { wmanIfSsConfigurationEntry 1 }

		
		-- 1.3.6.1.2.1.10.184.1.2.1.2.1.2
		wmanIfSsLostULMapInterval OBJECT-TYPE
			SYNTAX INTEGER (0..600)
			UNITS "milliseconds"
			MAX-ACCESS read-write
			STATUS current
			DESCRIPTION
				"Time since last received UL-MAP message before downlink
				synchronization is considered lost in ms."
			::= { wmanIfSsConfigurationEntry 2 }

		
		-- 1.3.6.1.2.1.10.184.1.2.1.2.1.3
		wmanIfSsContentionRangRetries OBJECT-TYPE
			SYNTAX INTEGER (16..65535)
			MAX-ACCESS read-write
			STATUS current
			DESCRIPTION
				"Number of retries on contention Ranging Requests."
			::= { wmanIfSsConfigurationEntry 3 }

		
		-- 1.3.6.1.2.1.10.184.1.2.1.2.1.4
		wmanIfSsRequestRetries OBJECT-TYPE
			SYNTAX INTEGER (16..65535)
			MAX-ACCESS read-write
			STATUS current
			DESCRIPTION
				"Number of retries on bandwidth allocation requests."
			::= { wmanIfSsConfigurationEntry 4 }

		
		-- 1.3.6.1.2.1.10.184.1.2.1.2.1.5
		wmanIfSsRegRequestRetries OBJECT-TYPE
			SYNTAX INTEGER (3..65535)
			MAX-ACCESS read-write
			STATUS current
			DESCRIPTION
				"Number of retries on registration requests."
			::= { wmanIfSsConfigurationEntry 5 }

		
		-- 1.3.6.1.2.1.10.184.1.2.1.2.1.6
		wmanIfSsTftpBackoffStart OBJECT-TYPE
			SYNTAX INTEGER (1..65535)
			UNITS "seconds"
			MAX-ACCESS read-write
			STATUS current
			DESCRIPTION
				"Initial value for TFTP backoff in second."
			::= { wmanIfSsConfigurationEntry 6 }

		
		-- 1.3.6.1.2.1.10.184.1.2.1.2.1.7
		wmanIfSsTftpBackoffEnd OBJECT-TYPE
			SYNTAX INTEGER (16..65535)
			UNITS "seconds"
			MAX-ACCESS read-write
			STATUS current
			DESCRIPTION
				"Last value for TFTP backoff in s."
			::= { wmanIfSsConfigurationEntry 7 }

		
		-- 1.3.6.1.2.1.10.184.1.2.1.2.1.8
		wmanIfSsTftpRequestRetries OBJECT-TYPE
			SYNTAX INTEGER (16..65535)
			MAX-ACCESS read-write
			STATUS current
			DESCRIPTION
				"Number of retries on TFTP request."
			::= { wmanIfSsConfigurationEntry 8 }

		
		-- 1.3.6.1.2.1.10.184.1.2.1.2.1.9
		wmanIfSsTftpDownloadRetries OBJECT-TYPE
			SYNTAX INTEGER (3..65535)
			MAX-ACCESS read-write
			STATUS current
			DESCRIPTION
				"Number of retries on entire TFTP downloads."
			::= { wmanIfSsConfigurationEntry 9 }

		
		-- 1.3.6.1.2.1.10.184.1.2.1.2.1.10
		wmanIfSsTftpWait OBJECT-TYPE
			SYNTAX INTEGER (2..65535)
			UNITS "minutes"
			MAX-ACCESS read-write
			STATUS current
			DESCRIPTION
				"The duration between two consecutive TFTP retries in min."
			::= { wmanIfSsConfigurationEntry 10 }

		
		-- 1.3.6.1.2.1.10.184.1.2.1.2.1.11
		wmanIfSsToDRetries OBJECT-TYPE
			SYNTAX INTEGER (3..65535)
			MAX-ACCESS read-write
			STATUS current
			DESCRIPTION
				"Number of Retries per Time of Day Retry Period."
			::= { wmanIfSsConfigurationEntry 11 }

		
		-- 1.3.6.1.2.1.10.184.1.2.1.2.1.12
		wmanIfSsToDRetryPeriod OBJECT-TYPE
			SYNTAX INTEGER (5..65535)
			UNITS "minutes"
			MAX-ACCESS read-write
			STATUS current
			DESCRIPTION
				"Time of Day Retry Period."
			::= { wmanIfSsConfigurationEntry 12 }

		
		-- 1.3.6.1.2.1.10.184.1.2.1.2.1.13
		wmanIfSsT1Timeout OBJECT-TYPE
			SYNTAX INTEGER (0..50000)
			UNITS "milliseconds"
			MAX-ACCESS read-write
			STATUS current
			DESCRIPTION
				"Wait for DCD timeout in ms."
			::= { wmanIfSsConfigurationEntry 13 }

		
		-- 1.3.6.1.2.1.10.184.1.2.1.2.1.14
		wmanIfSsT2Timeout OBJECT-TYPE
			SYNTAX INTEGER (0..10000)
			UNITS "milliseconds"
			MAX-ACCESS read-write
			STATUS current
			DESCRIPTION
				"Wait for broadcast ranging timeout in ms."
			::= { wmanIfSsConfigurationEntry 14 }

		
		-- 1.3.6.1.2.1.10.184.1.2.1.2.1.15
		wmanIfSsT3Timeout OBJECT-TYPE
			SYNTAX INTEGER (0..200)
			UNITS "milliseconds"
			MAX-ACCESS read-write
			STATUS current
			DESCRIPTION
				"Ranging Response reception timeout following the 
				transmission of a Ranging Request in ms."
			::= { wmanIfSsConfigurationEntry 15 }

		
		-- 1.3.6.1.2.1.10.184.1.2.1.2.1.16
		wmanIfSsT4Timeout OBJECT-TYPE
			SYNTAX INTEGER (30..35)
			UNITS "seconds"
			MAX-ACCESS read-write
			STATUS current
			DESCRIPTION
				"Wait for unicast ranging opportunity. If the pending until
				complete field was used earlier by this SS, then the value
				of that field shall be added to this interval in s."
			::= { wmanIfSsConfigurationEntry 16 }

		
		-- 1.3.6.1.2.1.10.184.1.2.1.2.1.17
		wmanIfSsT6Timeout OBJECT-TYPE
			SYNTAX INTEGER (0..3000)
			UNITS "milliseconds"
			MAX-ACCESS read-write
			STATUS current
			DESCRIPTION
				"Wait for registration response in ms."
			::= { wmanIfSsConfigurationEntry 17 }

		
		-- 1.3.6.1.2.1.10.184.1.2.1.2.1.18
		wmanIfSsT12Timeout OBJECT-TYPE
			SYNTAX INTEGER (0..50000)
			UNITS "milliseconds"
			MAX-ACCESS read-write
			STATUS current
			DESCRIPTION
				"Wait for UCD descriptor in ms."
			::= { wmanIfSsConfigurationEntry 18 }

		
		-- 1.3.6.1.2.1.10.184.1.2.1.2.1.19
		wmanIfSsT14Timeout OBJECT-TYPE
			SYNTAX INTEGER (0..200)
			UNITS "milliseconds"
			MAX-ACCESS read-write
			STATUS current
			DESCRIPTION
				"Wait for DSX-RVD Timeout in ms."
			::= { wmanIfSsConfigurationEntry 19 }

		
		-- 1.3.6.1.2.1.10.184.1.2.1.2.1.20
		wmanIfSsT16Timeout OBJECT-TYPE
			SYNTAX INTEGER (10..65535)
			UNITS "milliseconds"
			MAX-ACCESS read-write
			STATUS current
			DESCRIPTION
				"wait for bandwidth request grant in ms."
			::= { wmanIfSsConfigurationEntry 20 }

		
		-- 1.3.6.1.2.1.10.184.1.2.1.2.1.21
		wmanIfSsT18Timeout OBJECT-TYPE
			SYNTAX INTEGER (0..65535)
			UNITS "milliseconds"
			MAX-ACCESS read-write
			STATUS current
			DESCRIPTION
				"wait for SBC-RSP timeout in ms."
			::= { wmanIfSsConfigurationEntry 21 }

		
		-- 1.3.6.1.2.1.10.184.1.2.1.2.1.22
		wmanIfSsT19Timeout OBJECT-TYPE
			SYNTAX INTEGER (0..65535)
			UNITS "seconds"
			MAX-ACCESS read-write
			STATUS current
			DESCRIPTION
				"Time DL-channel remains unusable in ms."
			::= { wmanIfSsConfigurationEntry 22 }

		
		-- 1.3.6.1.2.1.10.184.1.2.1.2.1.23
		wmanIfSsT20Timeout OBJECT-TYPE
			SYNTAX INTEGER (0..65535)
			UNITS "milliseconds"
			MAX-ACCESS read-write
			STATUS current
			DESCRIPTION
				"Time SS searches for preambles on a given channel in ms."
			::= { wmanIfSsConfigurationEntry 23 }

		
		-- 1.3.6.1.2.1.10.184.1.2.1.2.1.24
		wmanIfSsT21Timeout OBJECT-TYPE
			SYNTAX INTEGER (0..10000)
			UNITS "milliseconds"
			MAX-ACCESS read-write
			STATUS current
			DESCRIPTION
				"Time SS searches for DL-MAP on a given channel in ms."
			::= { wmanIfSsConfigurationEntry 24 }

		
		-- 1.3.6.1.2.1.10.184.1.2.1.2.1.25
		wmanIfSsSBCRequestRetries OBJECT-TYPE
			SYNTAX INTEGER (3..16)
			MAX-ACCESS read-write
			STATUS current
			DESCRIPTION
				"Number of retries on SBC Request."
			::= { wmanIfSsConfigurationEntry 25 }

		
		-- 1.3.6.1.2.1.10.184.1.2.1.2.1.26
		wmanIfSsTftpCpltRetries OBJECT-TYPE
			SYNTAX INTEGER (3..16)
			MAX-ACCESS read-write
			STATUS current
			DESCRIPTION
				"Number of retries on TFTP-CPLT."
			::= { wmanIfSsConfigurationEntry 26 }

		
		-- 1.3.6.1.2.1.10.184.1.2.1.2.1.27
		wmanIfSsT26Timeout OBJECT-TYPE
			SYNTAX INTEGER (10..200)
			UNITS "milliseconds"
			MAX-ACCESS read-write
			STATUS current
			DESCRIPTION
				"Wait for TFTP-RSP in ms."
			::= { wmanIfSsConfigurationEntry 27 }

		
		-- 1.3.6.1.2.1.10.184.1.2.1.2.1.28
		wmanIfSsDLManagProcTime OBJECT-TYPE
			SYNTAX INTEGER (0..200)
			UNITS "micro seconds"
			MAX-ACCESS read-write
			STATUS current
			DESCRIPTION
				"Max. time between reception of Fast Power Control 
				management message and compliance to its instructions
				by SS in us."
			::= { wmanIfSsConfigurationEntry 28 }

		
--  Subscriber station PKM group
-- wmanIfSsPkmObjects contain the Subscriber Station Privacy Sublayer
-- objects
		-- 1.3.6.1.2.1.10.184.1.2.2
		wmanIfSsPkmObjects OBJECT IDENTIFIER ::= { wmanIfSsObjects 2 }

		
--  Table wmanIfSsPkmBaseTable
-- 
		-- 1.3.6.1.2.1.10.184.1.2.2.1
		wmanIfSsPkmBaseTable OBJECT-TYPE
			SYNTAX SEQUENCE OF WmanIfSsPkmBaseEntry
			MAX-ACCESS not-accessible
			STATUS current
			DESCRIPTION
				"This table describes the basic PKM attributes of each
				SS wireless interface."
			::= { wmanIfSsPkmObjects 1 }

		
		-- 1.3.6.1.2.1.10.184.1.2.2.1.1
		wmanIfSsPkmBaseEntry OBJECT-TYPE
			SYNTAX WmanIfSsPkmBaseEntry
			MAX-ACCESS not-accessible
			STATUS current
			DESCRIPTION
				"Each entry contains objects describing attributes of one
				SS wireless interface."
			INDEX { ifIndex }
			::= { wmanIfSsPkmBaseTable 1 }

		
		WmanIfSsPkmBaseEntry ::=
			SEQUENCE { 
				wmanIfSsPkmPrivacyEnable
					TruthValue,
				wmanIfSsPkmPublicKey
					OCTET STRING,
				wmanIfSsPkmAuthGraceTime
					Integer32,
				wmanIfSsPkmTEKGraceTime
					Integer32,
				wmanIfSsPkmAuthWaitTimeout
					Integer32,
				wmanIfSsPkmReauthWaitTimeout
					Integer32,
				wmanIfSsPkmOpWaitTimeout
					Integer32,
				wmanIfSsPkmRekeyWaitTimeout
					Integer32,
				wmanIfSsPkmAuthRejectWaitTimeout
					Integer32
			 }

		-- 1.3.6.1.2.1.10.184.1.2.2.1.1.1
		wmanIfSsPkmPrivacyEnable OBJECT-TYPE
			SYNTAX TruthValue
			MAX-ACCESS read-only
			STATUS current
			DESCRIPTION
				"This object identifies whether this SS is provisioned to
				run Baseline Privacy Plus."
			::= { wmanIfSsPkmBaseEntry 1 }

		
		-- 1.3.6.1.2.1.10.184.1.2.2.1.1.2
		wmanIfSsPkmPublicKey OBJECT-TYPE
			SYNTAX OCTET STRING (SIZE (140))
			MAX-ACCESS read-only
			STATUS current
			DESCRIPTION
				"The value of this object is a DER-encoded RSAPublicKey
				ASN.1 type string, as defined in the RSA Encryption
				Standard (PKCS#1) [10], corresponding to the public key of
				the SS. The 74, 106, 140, 204, and 270 byte key encoding
				lengths correspond to 512 bit, 768 bit, 1024 bit, 1536 bit,
				and 2048 public moduli respectively."
			::= { wmanIfSsPkmBaseEntry 2 }

		
		-- 1.3.6.1.2.1.10.184.1.2.2.1.1.3
		wmanIfSsPkmAuthGraceTime OBJECT-TYPE
			SYNTAX Integer32 (300..3024000)
			UNITS "seconds"
			MAX-ACCESS read-only
			STATUS current
			DESCRIPTION
				"The value of this object is the grace time for an
				authorization key.  A SS is expected to start trying to get
				a new authorization key beginning AuthGraceTime seconds
				before the authorization key actually expires."
			REFERENCE
				"Table 341 in IEEE 802.16REVd/D5-2004"
			DEFVAL { 600 }
			::= { wmanIfSsPkmBaseEntry 3 }

		
		-- 1.3.6.1.2.1.10.184.1.2.2.1.1.4
		wmanIfSsPkmTEKGraceTime OBJECT-TYPE
			SYNTAX Integer32 (300..302399)
			UNITS "seconds"
			MAX-ACCESS read-only
			STATUS current
			DESCRIPTION
				"The value of this object is the grace time for the TEK in
				seconds. The SS is expected to start trying to acquire a
				new TEK beginning TEK GraceTime seconds before the
				expiration of the most recent TEK."
			REFERENCE
				"Table 341 in IEEE 802.16REVd/D5-2004"
			DEFVAL { 3600 }
			::= { wmanIfSsPkmBaseEntry 4 }

		
		-- 1.3.6.1.2.1.10.184.1.2.2.1.1.5
		wmanIfSsPkmAuthWaitTimeout OBJECT-TYPE
			SYNTAX Integer32 (2..30)
			UNITS "seconds"
			MAX-ACCESS read-only
			STATUS current
			DESCRIPTION
				"The value of this object is the Authorize Wait Timeout."
			REFERENCE
				"Table 341 in IEEE 802.16REVd/D5-2004"
			DEFVAL { 10 }
			::= { wmanIfSsPkmBaseEntry 5 }

		
		-- 1.3.6.1.2.1.10.184.1.2.2.1.1.6
		wmanIfSsPkmReauthWaitTimeout OBJECT-TYPE
			SYNTAX Integer32 (2..30)
			UNITS "seconds"
			MAX-ACCESS read-only
			STATUS current
			DESCRIPTION
				"The value of this object is the Reauthorize Wait Timeout
				in seconds."
			REFERENCE
				"Table 341 in IEEE 802.16REVd/D5-2004"
			DEFVAL { 10 }
			::= { wmanIfSsPkmBaseEntry 6 }

		
		-- 1.3.6.1.2.1.10.184.1.2.2.1.1.7
		wmanIfSsPkmOpWaitTimeout OBJECT-TYPE
			SYNTAX Integer32 (1..10)
			UNITS "seconds"
			MAX-ACCESS read-only
			STATUS current
			DESCRIPTION
				"The value of this object is the Operational Wait Timeout
				in seconds."
			REFERENCE
				"Table 341 in IEEE 802.16REVd/D5-2004"
			DEFVAL { 1 }
			::= { wmanIfSsPkmBaseEntry 7 }

		
		-- 1.3.6.1.2.1.10.184.1.2.2.1.1.8
		wmanIfSsPkmRekeyWaitTimeout OBJECT-TYPE
			SYNTAX Integer32 (1..10)
			UNITS "seconds"
			MAX-ACCESS read-only
			STATUS current
			DESCRIPTION
				"The value of this object is the Rekey Wait Timeout in
				seconds."
			REFERENCE
				"Table 341 in IEEE 802.16REVd/D5-2004"
			DEFVAL { 1 }
			::= { wmanIfSsPkmBaseEntry 8 }

		
		-- 1.3.6.1.2.1.10.184.1.2.2.1.1.9
		wmanIfSsPkmAuthRejectWaitTimeout OBJECT-TYPE
			SYNTAX Integer32 (10..600)
			UNITS "seconds"
			MAX-ACCESS read-only
			STATUS current
			DESCRIPTION
				"The value of this object is the Authorization Reject Wait
				Timeout in seconds."
			REFERENCE
				"Table 341 in IEEE 802.16REVd/D5-2004"
			DEFVAL { 60 }
			::= { wmanIfSsPkmBaseEntry 9 }

		
--  Table wmanIfSsPkmAuthTable
-- 
		-- 1.3.6.1.2.1.10.184.1.2.2.2
		wmanIfSsPkmAuthTable OBJECT-TYPE
			SYNTAX SEQUENCE OF WmanIfSsPkmAuthEntry
			MAX-ACCESS not-accessible
			STATUS current
			DESCRIPTION
				"This table describes the PKM attributes related
				to the authorization for each SS wireless interface."
			::= { wmanIfSsPkmObjects 2 }

		
		-- 1.3.6.1.2.1.10.184.1.2.2.2.1
		wmanIfSsPkmAuthEntry OBJECT-TYPE
			SYNTAX WmanIfSsPkmAuthEntry
			MAX-ACCESS not-accessible
			STATUS current
			DESCRIPTION
				"Each entry contains objects describing attributes of one
				SS wireless interface."
			INDEX { ifIndex }
			::= { wmanIfSsPkmAuthTable 1 }

		
		WmanIfSsPkmAuthEntry ::=
			SEQUENCE { 
				wmanIfSsPkmAuthState
					INTEGER,
				wmanIfSsPkmAuthKeySequenceNumber
					Integer32,
				wmanIfSsPkmAuthExpiresOld
					DateAndTime,
				wmanIfSsPkmAuthExpiresNew
					DateAndTime,
				wmanIfSsPkmAuthReset
					TruthValue,
				wmanIfSsPkmAuthentInfos
					Counter32,
				wmanIfSsPkmAuthRequests
					Counter32,
				wmanIfSsPkmAuthReplies
					Counter32,
				wmanIfSsPkmAuthRejects
					Counter32,
				wmanIfSsPkmAuthInvalids
					Counter32,
				wmanIfSsPkmAuthRejectErrorCode
					INTEGER,
				wmanIfSsPkmAuthRejectErrorString
					SnmpAdminString,
				wmanIfSsPkmAuthInvalidErrorCode
					INTEGER,
				wmanIfSsPkmAuthInvalidErrorString
					SnmpAdminString
			 }

		-- 1.3.6.1.2.1.10.184.1.2.2.2.1.1
		wmanIfSsPkmAuthState OBJECT-TYPE
			SYNTAX INTEGER
				{
				start(1),
				authWait(2),
				authorized(3),
				reauthWait(4),
				authRejectWait(5),
				silent(6)
				}
			MAX-ACCESS read-only
			STATUS current
			DESCRIPTION
				"The value of this object is the state of the SS
				authorization FSM.  The start state indicates that FSM is
				in its initial state."
			::= { wmanIfSsPkmAuthEntry 1 }

		
		-- 1.3.6.1.2.1.10.184.1.2.2.2.1.2
		wmanIfSsPkmAuthKeySequenceNumber OBJECT-TYPE
			SYNTAX Integer32 (0..15)
			MAX-ACCESS read-only
			STATUS current
			DESCRIPTION
				"The value of this object is the most recent authorization
				key sequence number for this FSM."
			::= { wmanIfSsPkmAuthEntry 2 }

		
		-- 1.3.6.1.2.1.10.184.1.2.2.2.1.3
		wmanIfSsPkmAuthExpiresOld OBJECT-TYPE
			SYNTAX DateAndTime
			MAX-ACCESS read-only
			STATUS current
			DESCRIPTION
				"The value of this object is the actual clock time for
				expiration of the immediate predecessor of the most recent
				authorization key for this FSM.  If this FSM has only one
				authorization key, then the value is the time of activation
				of this FSM."
			::= { wmanIfSsPkmAuthEntry 3 }

		
		-- 1.3.6.1.2.1.10.184.1.2.2.2.1.4
		wmanIfSsPkmAuthExpiresNew OBJECT-TYPE
			SYNTAX DateAndTime
			MAX-ACCESS read-only
			STATUS current
			DESCRIPTION
				"The value of this object is the actual clock time for
				expiration of the most recent authorization key for this
				FSM."
			::= { wmanIfSsPkmAuthEntry 4 }

		
		-- 1.3.6.1.2.1.10.184.1.2.2.2.1.5
		wmanIfSsPkmAuthReset OBJECT-TYPE
			SYNTAX TruthValue
			MAX-ACCESS read-write
			STATUS current
			DESCRIPTION
				"Setting this object to TRUE generates a Reauthorize event
				in the authorization FSM. Reading this object always
				returns FALSE."
			::= { wmanIfSsPkmAuthEntry 5 }

		
		-- 1.3.6.1.2.1.10.184.1.2.2.2.1.6
		wmanIfSsPkmAuthentInfos OBJECT-TYPE
			SYNTAX Counter32
			MAX-ACCESS read-only
			STATUS current
			DESCRIPTION
				"The value of this object is the count of times the SS has
				transmitted an Authentication Information message."
			::= { wmanIfSsPkmAuthEntry 6 }

		
		-- 1.3.6.1.2.1.10.184.1.2.2.2.1.7
		wmanIfSsPkmAuthRequests OBJECT-TYPE
			SYNTAX Counter32
			MAX-ACCESS read-only
			STATUS current
			DESCRIPTION
				"The value of this object is the count of times the SS has
				transmitted an Authorization Request message."
			::= { wmanIfSsPkmAuthEntry 7 }

		
		-- 1.3.6.1.2.1.10.184.1.2.2.2.1.8
		wmanIfSsPkmAuthReplies OBJECT-TYPE
			SYNTAX Counter32
			MAX-ACCESS read-only
			STATUS current
			DESCRIPTION
				"The value of this object is the count of times the SS has
				received an Authorization Reply message."
			::= { wmanIfSsPkmAuthEntry 8 }

		
		-- 1.3.6.1.2.1.10.184.1.2.2.2.1.9
		wmanIfSsPkmAuthRejects OBJECT-TYPE
			SYNTAX Counter32
			MAX-ACCESS read-only
			STATUS current
			DESCRIPTION
				"The value of this object is the count of times the SS has
				received an Authorization Reject message."
			::= { wmanIfSsPkmAuthEntry 9 }

		
		-- 1.3.6.1.2.1.10.184.1.2.2.2.1.10
		wmanIfSsPkmAuthInvalids OBJECT-TYPE
			SYNTAX Counter32
			MAX-ACCESS read-only
			STATUS current
			DESCRIPTION
				"The value of this object is the count of times the SS has
				received an Authorization Invalid message."
			::= { wmanIfSsPkmAuthEntry 10 }

		
		-- 1.3.6.1.2.1.10.184.1.2.2.2.1.11
		wmanIfSsPkmAuthRejectErrorCode OBJECT-TYPE
			SYNTAX INTEGER
				{
				none(1),
				unknown(2),
				unauthorizedSs(3),
				unauthorizedSaid(4),
				permanentAuthorizationFailure(8),
				timeOfDayNotAcquired(11)
				}
			MAX-ACCESS read-only
			STATUS current
			DESCRIPTION
				"The value of this object is the enumerated description of
				the Error-Code in most recent Authorization Reject message
				received by the SS.  This has value unknown(2)if the last
				Error-Code value was 0, and none(1) if no Authorization
				Reject message has been received since reboot."
			::= { wmanIfSsPkmAuthEntry 11 }

		
		-- 1.3.6.1.2.1.10.184.1.2.2.2.1.12
		wmanIfSsPkmAuthRejectErrorString OBJECT-TYPE
			SYNTAX SnmpAdminString (SIZE (0..128))
			MAX-ACCESS read-only
			STATUS current
			DESCRIPTION
				"The value of this object is the Display-String in most
				recent Authorization Reject message received by the SS.
				This is a zero length string if no Authorization Reject
				message has been received since reboot."
			::= { wmanIfSsPkmAuthEntry 12 }

		
		-- 1.3.6.1.2.1.10.184.1.2.2.2.1.13
		wmanIfSsPkmAuthInvalidErrorCode OBJECT-TYPE
			SYNTAX INTEGER
				{
				none(1),
				unknown(2),
				unauthorizedSs(3),
				unsolicited(5),
				invalidKeySequence(6),
				keyRequestAuthenticationFailure(7)
				}
			MAX-ACCESS read-only
			STATUS current
			DESCRIPTION
				"The value of this object is the enumerated description of
				the Error-Code in most recent Authorization Invald message
				received by the SS.  This has value unknown(2) if the last
				Error-Code value was 0, and none(1) if no Authorization
				Invalid message has been received since reboot."
			::= { wmanIfSsPkmAuthEntry 13 }

		
		-- 1.3.6.1.2.1.10.184.1.2.2.2.1.14
		wmanIfSsPkmAuthInvalidErrorString OBJECT-TYPE
			SYNTAX SnmpAdminString (SIZE (0..128))
			MAX-ACCESS read-only
			STATUS current
			DESCRIPTION
				"The value of this object is the Display-String in most
				recent Authorization Invalid message received by the SS.
				This is a zero length string if no Authorization Invalid
				message has been received since reboot."
			::= { wmanIfSsPkmAuthEntry 14 }

		
--  Table wmanIfSsPkmTEKTable
-- 
		-- 1.3.6.1.2.1.10.184.1.2.2.3
		wmanIfSsPkmTEKTable OBJECT-TYPE
			SYNTAX SEQUENCE OF WmanIfSsPkmTEKEntry
			MAX-ACCESS not-accessible
			STATUS current
			DESCRIPTION
				"This table describes the attributes of each SS Traffic
				Encryption Key(TEK) association. The SS maintains (no more
				than) one TEK association per SAID per SS wireless
				interface."
			::= { wmanIfSsPkmObjects 3 }

		
		-- 1.3.6.1.2.1.10.184.1.2.2.3.1
		wmanIfSsPkmTEKEntry OBJECT-TYPE
			SYNTAX WmanIfSsPkmTEKEntry
			MAX-ACCESS not-accessible
			STATUS current
			DESCRIPTION
				"Each entry contains objects describing the TEK association
				attributes of one SAID. The SS MUST create one entry per
				SAID, regardless of whether the SAID was obtained from a
				Registration Response message, from an Authorization Reply
				message, or from any dynamic SAID establishment
				mechanisms."
			INDEX { ifIndex, wmanIfSsPkmTEKSAId }
			::= { wmanIfSsPkmTEKTable 1 }

		
		WmanIfSsPkmTEKEntry ::=
			SEQUENCE { 
				wmanIfSsPkmTEKSAId
					Integer32,
				wmanIfSsPkmTEKSAType
					INTEGER,
				wmanIfSsPkmTEKDataEncryptAlg
					INTEGER,
				wmanIfSsPkmTEKDataAuthentAlg
					INTEGER,
				wmanIfSsPkmTEKEncryptAlg
					INTEGER,
				wmanIfSsPkmTEKState
					INTEGER,
				wmanIfSsPkmTEKKeySequenceNumber
					Integer32,
				wmanIfSsPkmTEKExpiresOld
					DateAndTime,
				wmanIfSsPkmTEKExpiresNew
					DateAndTime,
				wmanIfSsPkmTEKKeyRequests
					Counter32,
				wmanIfSsPkmTEKKeyReplies
					Counter32,
				wmanIfSsPkmTEKKeyRejects
					Counter32,
				wmanIfSsPkmTEKInvalids
					Counter32,
				wmanIfSsPkmTEKAuthPends
					Counter32,
				wmanIfSsPkmTEKKeyRejectErrorCode
					INTEGER,
				wmanIfSsPkmTEKKeyRejectErrorString
					SnmpAdminString,
				wmanIfSsPkmTEKInvalidErrorCode
					INTEGER,
				wmanIfSsPkmTEKInvalidErrorString
					SnmpAdminString
			 }

		-- 1.3.6.1.2.1.10.184.1.2.2.3.1.1
		wmanIfSsPkmTEKSAId OBJECT-TYPE
			SYNTAX Integer32 (1..16383)
			MAX-ACCESS not-accessible
			STATUS current
			DESCRIPTION
				"The value of this object is the WiMAX Security Association
				ID (SAID)."
			::= { wmanIfSsPkmTEKEntry 1 }

		
		-- 1.3.6.1.2.1.10.184.1.2.2.3.1.2
		wmanIfSsPkmTEKSAType OBJECT-TYPE
			SYNTAX INTEGER
				{
				primarySA(0),
				staticSA(1),
				dynamicSA(2)
				}
			MAX-ACCESS read-only
			STATUS current
			DESCRIPTION
				"The value of this object is the type of security
				association."
			REFERENCE
				"IEEE 802.16 standard; 11.9.18"
			::= { wmanIfSsPkmTEKEntry 2 }

		
		-- 1.3.6.1.2.1.10.184.1.2.2.3.1.3
		wmanIfSsPkmTEKDataEncryptAlg OBJECT-TYPE
			SYNTAX INTEGER
				{
				none(0),
				des56CbcMode(1)
				}
			MAX-ACCESS read-only
			STATUS current
			DESCRIPTION
				"The value of this object is the data encryption algorithm
				being utilized."
			REFERENCE
				"IEEE 802.16 standard; Table 301"
			::= { wmanIfSsPkmTEKEntry 3 }

		
		-- 1.3.6.1.2.1.10.184.1.2.2.3.1.4
		wmanIfSsPkmTEKDataAuthentAlg OBJECT-TYPE
			SYNTAX INTEGER { none(0) }
			MAX-ACCESS read-only
			STATUS current
			DESCRIPTION
				"The value of this object is the data authentication
				algorithm being utilized."
			REFERENCE
				"IEEE 802.16 standard; Table 302"
			::= { wmanIfSsPkmTEKEntry 4 }

		
		-- 1.3.6.1.2.1.10.184.1.2.2.3.1.5
		wmanIfSsPkmTEKEncryptAlg OBJECT-TYPE
			SYNTAX INTEGER
				{
				tripleDES(0),
				rsa1024(1)
				}
			MAX-ACCESS read-only
			STATUS current
			DESCRIPTION
				"The value of this object is the TEK key encryption
				algorithm for this cryptographic suite capability."
			REFERENCE
				"IEEE 802.16 standard; Table 303"
			::= { wmanIfSsPkmTEKEntry 5 }

		
		-- 1.3.6.1.2.1.10.184.1.2.2.3.1.6
		wmanIfSsPkmTEKState OBJECT-TYPE
			SYNTAX INTEGER
				{
				start(1),
				opWait(2),
				opReauthWait(3),
				operational(4),
				rekeyWait(5),
				rekeyReauthWait(6)
				}
			MAX-ACCESS read-only
			STATUS current
			DESCRIPTION
				"The value of this object is the state of the indicated TEK
				FSM. The start(1) state indicates that FSM is in its
				initial state."
			::= { wmanIfSsPkmTEKEntry 6 }

		
		-- 1.3.6.1.2.1.10.184.1.2.2.3.1.7
		wmanIfSsPkmTEKKeySequenceNumber OBJECT-TYPE
			SYNTAX Integer32 (0..3)
			MAX-ACCESS read-only
			STATUS current
			DESCRIPTION
				"The value of this object is the most recent TEK key
				sequence number for this TEK FSM."
			REFERENCE
				"IEEE 802.16 standard; 11.9.5"
			::= { wmanIfSsPkmTEKEntry 7 }

		
		-- 1.3.6.1.2.1.10.184.1.2.2.3.1.8
		wmanIfSsPkmTEKExpiresOld OBJECT-TYPE
			SYNTAX DateAndTime
			MAX-ACCESS read-only
			STATUS current
			DESCRIPTION
				"The value of this object is the actual clock time for
				expiration of the immediate predecessor of the most recent
				TEK for this FSM.  If this FSM has only one TEK, then the
				value is the time of activation of this FSM."
			::= { wmanIfSsPkmTEKEntry 8 }

		
		-- 1.3.6.1.2.1.10.184.1.2.2.3.1.9
		wmanIfSsPkmTEKExpiresNew OBJECT-TYPE
			SYNTAX DateAndTime
			MAX-ACCESS read-only
			STATUS current
			DESCRIPTION
				"The value of this object is the actual clock time for
				expiration of the most recent TEK for this FSM."
			::= { wmanIfSsPkmTEKEntry 9 }

		
		-- 1.3.6.1.2.1.10.184.1.2.2.3.1.10
		wmanIfSsPkmTEKKeyRequests OBJECT-TYPE
			SYNTAX Counter32
			MAX-ACCESS read-only
			STATUS current
			DESCRIPTION
				"The value of this object is the count of times the SS has
				transmitted a Key Request message."
			::= { wmanIfSsPkmTEKEntry 10 }

		
		-- 1.3.6.1.2.1.10.184.1.2.2.3.1.11
		wmanIfSsPkmTEKKeyReplies OBJECT-TYPE
			SYNTAX Counter32
			MAX-ACCESS read-only
			STATUS current
			DESCRIPTION
				"The value of this object is the count of times the SS has
				received a Key Reply message, including a message whose
				authentication failed."
			::= { wmanIfSsPkmTEKEntry 11 }

		
		-- 1.3.6.1.2.1.10.184.1.2.2.3.1.12
		wmanIfSsPkmTEKKeyRejects OBJECT-TYPE
			SYNTAX Counter32
			MAX-ACCESS read-only
			STATUS current
			DESCRIPTION
				"The value of this object is the count of times the SS has
				received a Key Reject message, including a message whose
				authentication failed."
			::= { wmanIfSsPkmTEKEntry 12 }

		
		-- 1.3.6.1.2.1.10.184.1.2.2.3.1.13
		wmanIfSsPkmTEKInvalids OBJECT-TYPE
			SYNTAX Counter32
			MAX-ACCESS read-only
			STATUS current
			DESCRIPTION
				"The value of this object is the count of times the SS has
				received a TEK Invalid message, including a message whose
				authentication failed."
			::= { wmanIfSsPkmTEKEntry 13 }

		
		-- 1.3.6.1.2.1.10.184.1.2.2.3.1.14
		wmanIfSsPkmTEKAuthPends OBJECT-TYPE
			SYNTAX Counter32
			MAX-ACCESS read-only
			STATUS current
			DESCRIPTION
				"The value of this object is the count of times an
				Authorization Pending (Auth Pend) event occurred in this
				FSM."
			::= { wmanIfSsPkmTEKEntry 14 }

		
		-- 1.3.6.1.2.1.10.184.1.2.2.3.1.15
		wmanIfSsPkmTEKKeyRejectErrorCode OBJECT-TYPE
			SYNTAX INTEGER
				{
				none(1),
				unknown(2),
				unauthorizedSaid(4)
				}
			MAX-ACCESS read-only
			STATUS current
			DESCRIPTION
				"The value of this object is the enumerated description of
				the Error-Code in most recent Key Reject message received
				by the SS. This has value unknown(2) if the last Error-Code
				value was 0, and none(1) if no Key Reject message has been
				received since reboot."
			::= { wmanIfSsPkmTEKEntry 15 }

		
		-- 1.3.6.1.2.1.10.184.1.2.2.3.1.16
		wmanIfSsPkmTEKKeyRejectErrorString OBJECT-TYPE
			SYNTAX SnmpAdminString (SIZE (0..128))
			MAX-ACCESS read-only
			STATUS current
			DESCRIPTION
				"The value of this object is the Display-String in most
				recent Key Reject message received by the SS. This is a
				zero length string if no Key Reject message has been
				received since reboot."
			::= { wmanIfSsPkmTEKEntry 16 }

		
		-- 1.3.6.1.2.1.10.184.1.2.2.3.1.17
		wmanIfSsPkmTEKInvalidErrorCode OBJECT-TYPE
			SYNTAX INTEGER
				{
				none(1),
				unknown(2),
				invalidKeySequence(6)
				}
			MAX-ACCESS read-only
			STATUS current
			DESCRIPTION
				"The value of this object is the enumerated description of
				the Error-Code in most recent TEK Invalid message received
				by the SS.  This has value unknown(2) if the last
				Error-Code value was 0, and  none(1) if no TEK Invalid
				message has been received since reboot."
			::= { wmanIfSsPkmTEKEntry 17 }

		
		-- 1.3.6.1.2.1.10.184.1.2.2.3.1.18
		wmanIfSsPkmTEKInvalidErrorString OBJECT-TYPE
			SYNTAX SnmpAdminString (SIZE (0..128))
			MAX-ACCESS read-only
			STATUS current
			DESCRIPTION
				"The value of this object is the Display-String in most
				recent TEK Invalid message received by the SS. This is a
				zero length string if no TEK Invalid message has been
				received since reboot."
			::= { wmanIfSsPkmTEKEntry 18 }

		
--  Table wmanIfSsDeviceCertTable
-- 
		-- 1.3.6.1.2.1.10.184.1.2.2.4
		wmanIfSsDeviceCertTable OBJECT-TYPE
			SYNTAX SEQUENCE OF WmanIfSsDeviceCertEntry
			MAX-ACCESS not-accessible
			STATUS current
			DESCRIPTION
				"This table describes the PKM device certificates for each
				SS wireless interface."
			::= { wmanIfSsPkmObjects 4 }

		
		-- 1.3.6.1.2.1.10.184.1.2.2.4.1
		wmanIfSsDeviceCertEntry OBJECT-TYPE
			SYNTAX WmanIfSsDeviceCertEntry
			MAX-ACCESS not-accessible
			STATUS current
			DESCRIPTION
				"Each entry contains the device certificate of one SS."
			INDEX { ifIndex }
			::= { wmanIfSsDeviceCertTable 1 }

		
		WmanIfSsDeviceCertEntry ::=
			SEQUENCE { 
				wmanIfSsDeviceCert
					OCTET STRING,
				wmanIfSsDeviceManufCert
					OCTET STRING
			 }

		-- 1.3.6.1.2.1.10.184.1.2.2.4.1.1
		wmanIfSsDeviceCert OBJECT-TYPE
			SYNTAX OCTET STRING
			MAX-ACCESS read-only
			STATUS current
			DESCRIPTION
				"The X509 DER-encoded subscriber station certificate."
			::= { wmanIfSsDeviceCertEntry 1 }

		
		-- 1.3.6.1.2.1.10.184.1.2.2.4.1.2
		wmanIfSsDeviceManufCert OBJECT-TYPE
			SYNTAX OCTET STRING
			MAX-ACCESS read-only
			STATUS current
			DESCRIPTION
				"The X509 DER-encoded manufacturer certificate which is
				signed by the CA root authority certificate."
			::= { wmanIfSsDeviceCertEntry 2 }

		
--  Subscriber station Notification Group
-- wmanIfSsNotificationObjects contains the SS SNMP Trap objects
-- 
		-- 1.3.6.1.2.1.10.184.1.2.3
		wmanIfSsNotification OBJECT IDENTIFIER ::= { wmanIfSsObjects 3 }

		
		-- 1.3.6.1.2.1.10.184.1.2.3.1
		wmanIfSsTrapDefinitions OBJECT IDENTIFIER ::= { wmanIfSsNotification 1 }

		
		-- 1.3.6.1.2.1.10.184.1.2.3.1.1
		wmanSsTLVUnknownTrap NOTIFICATION-TYPE
			OBJECTS { wmanIfSsMacAddress, wmanIfSsUnknownTlv }
			STATUS current
			DESCRIPTION 
				"Event that notifies detection of unknown TLV during
				the TLV parsing process."
			::= { wmanIfSsTrapDefinitions 1 }

		
		-- 1.3.6.1.2.1.10.184.1.2.3.1.2
		wmanSsDynamicServiceFailTrap NOTIFICATION-TYPE
			OBJECTS { wmanIfSsMacAddress, wmanIfSsDynamicServiceType, wmanIfSsDynamicServiceFailReason }
			STATUS current
			DESCRIPTION 
				"An event to report the failure of a dynamic service
				operation happened during the dynamic services process
				and detected in the Bs side."
			::= { wmanIfSsTrapDefinitions 2 }

		
		-- 1.3.6.1.2.1.10.184.1.2.3.1.3
		wmanSsDHCPSuccessTrap NOTIFICATION-TYPE
			OBJECTS { wmanIfSsMacAddress }
			STATUS current
			DESCRIPTION 
				"An event to report a successful DHCP Handshake for
				the SS."
			::= { wmanIfSsTrapDefinitions 3 }

		
		-- 1.3.6.1.2.1.10.184.1.2.3.1.4
		wmanSsRssiStatusChangeTrap NOTIFICATION-TYPE
			OBJECTS { wmanIfSsMacAddress, wmanIfSsRssiStatus, wmanIfSsRssiStatusInfo }
			STATUS current
			DESCRIPTION 
				"An event to report that the uplink RSSI is below
				wmanIfSsRssiLowThreshold, or above
				wmanIfSsRssiHighThreshold after restore."
			::= { wmanIfSsTrapDefinitions 4 }

		
		-- 1.3.6.1.2.1.10.184.1.2.3.1.5
		wmanIfSsNotificationObjectsTable OBJECT-TYPE
			SYNTAX SEQUENCE OF WmanIfSsNotificationObjectsEntry
			MAX-ACCESS not-accessible
			STATUS current
			DESCRIPTION
				"This table contains SS notification objects that have been
				reported by the trap."
			::= { wmanIfSsTrapDefinitions 5 }

		
		-- 1.3.6.1.2.1.10.184.1.2.3.1.5.1
		wmanIfSsNotificationObjectsEntry OBJECT-TYPE
			SYNTAX WmanIfSsNotificationObjectsEntry
			MAX-ACCESS not-accessible
			STATUS current
			DESCRIPTION
				"This table provides one row for each SS that has
				generated traps, and is double indexed by
				wmanIfBsTrapSsId and ifIndex for BS sector."
			INDEX { ifIndex }
			::= { wmanIfSsNotificationObjectsTable 1 }

		
		WmanIfSsNotificationObjectsEntry ::=
			SEQUENCE { 
				wmanIfSsMacAddress
					MacAddress,
				wmanIfSsUnknownTlv
					OCTET STRING,
				wmanIfSsDynamicServiceType
					INTEGER,
				wmanIfSsDynamicServiceFailReason
					OCTET STRING,
				wmanIfSsRssiStatus
					INTEGER,
				wmanIfSsRssiStatusInfo
					OCTET STRING
			 }

		-- 1.3.6.1.2.1.10.184.1.2.3.1.5.1.1
		wmanIfSsMacAddress OBJECT-TYPE
			SYNTAX MacAddress
			MAX-ACCESS read-only
			STATUS current
			DESCRIPTION
				"The MAC address of the SS generating the trap."
			::= { wmanIfSsNotificationObjectsEntry 1 }

		
		-- 1.3.6.1.2.1.10.184.1.2.3.1.5.1.2
		wmanIfSsUnknownTlv OBJECT-TYPE
			SYNTAX OCTET STRING
			MAX-ACCESS read-only
			STATUS current
			DESCRIPTION
				"Indicating the value of the unknown TLV."
			::= { wmanIfSsNotificationObjectsEntry 2 }

		
		-- 1.3.6.1.2.1.10.184.1.2.3.1.5.1.3
		wmanIfSsDynamicServiceType OBJECT-TYPE
			SYNTAX INTEGER
				{
				ssSfCreationReq(1),
				ssSfCreationRsp(2),
				ssSfCreationAck(3)
				}
			MAX-ACCESS read-only
			STATUS current
			DESCRIPTION
				"This object indicates the dynamic service flow
				creation command type."
			::= { wmanIfSsNotificationObjectsEntry 3 }

		
		-- 1.3.6.1.2.1.10.184.1.2.3.1.5.1.4
		wmanIfSsDynamicServiceFailReason OBJECT-TYPE
			SYNTAX OCTET STRING
			MAX-ACCESS read-only
			STATUS current
			DESCRIPTION
				"This object indicates the reason why the service flow
				cration has failed."
			::= { wmanIfSsNotificationObjectsEntry 4 }

		
		-- 1.3.6.1.2.1.10.184.1.2.3.1.5.1.5
		wmanIfSsRssiStatus OBJECT-TYPE
			SYNTAX INTEGER
				{
				ssRssiAlarm(1),
				ssRssiNoAlarm(2)
				}
			MAX-ACCESS read-only
			STATUS current
			DESCRIPTION
				"A RSSI alarm is generated if the RSSI is lower than
				wmanIfSsRssiLowThreshold, or above
				wmanIfSsRssiHighThreshold after alarm is restored."
			::= { wmanIfSsNotificationObjectsEntry 5 }

		
		-- 1.3.6.1.2.1.10.184.1.2.3.1.5.1.6
		wmanIfSsRssiStatusInfo OBJECT-TYPE
			SYNTAX OCTET STRING
			MAX-ACCESS read-only
			STATUS current
			DESCRIPTION
				"This object indicates the reason why RSSI event is
				generated."
			::= { wmanIfSsNotificationObjectsEntry 6 }

		
		-- 1.3.6.1.2.1.10.184.1.2.3.2
		wmanIfSsTrapControl OBJECT IDENTIFIER ::= { wmanIfSsNotification 2 }

		
		-- 1.3.6.1.2.1.10.184.1.2.3.2.1
		wmanIfSsTrapControlRegister OBJECT-TYPE
			SYNTAX BITS
				{
				wmanSsTLVUnknown(0),
				wmanSsDynamicServiceFail(1),
				wmanSsDHCPSuccess(2),
				wmanSsRssiStatusChange(3)
				}
			MAX-ACCESS read-write
			STATUS current
			DESCRIPTION
				"The object is used to enable Subscriber Station traps.
				From left to right, the set bit indicates the corresponding
				Subscriber Station trap is enabled."
			::= { wmanIfSsTrapControl 1 }

		
		-- 1.3.6.1.2.1.10.184.1.2.3.2.2
		wmanIfSsThresholdConfigTable OBJECT-TYPE
			SYNTAX SEQUENCE OF WmanIfSsThresholdConfigEntry
			MAX-ACCESS not-accessible
			STATUS current
			DESCRIPTION
				"This table contains threshold objects that can be set to
				detect the threshold crossing events."
			::= { wmanIfSsTrapControl 2 }

		
		-- 1.3.6.1.2.1.10.184.1.2.3.2.2.1
		wmanIfSsThresholdConfigEntry OBJECT-TYPE
			SYNTAX WmanIfSsThresholdConfigEntry
			MAX-ACCESS not-accessible
			STATUS current
			DESCRIPTION
				"This table provides one row for each BS sector, and is
				indexed by ifIndex."
			INDEX { ifIndex }
			::= { wmanIfSsThresholdConfigTable 1 }

		
		WmanIfSsThresholdConfigEntry ::=
			SEQUENCE { 
				wmanIfSsRssiLowThreshold
					INTEGER,
				wmanIfSsRssiHighThreshold
					INTEGER
			 }

		-- 1.3.6.1.2.1.10.184.1.2.3.2.2.1.1
		wmanIfSsRssiLowThreshold OBJECT-TYPE
			SYNTAX INTEGER
			UNITS "dBm"
			MAX-ACCESS read-write
			STATUS current
			DESCRIPTION
				"Low RSSI threshold for generating the RSSI alarm trap."
			::= { wmanIfSsThresholdConfigEntry 1 }

		
		-- 1.3.6.1.2.1.10.184.1.2.3.2.2.1.2
		wmanIfSsRssiHighThreshold OBJECT-TYPE
			SYNTAX INTEGER
			UNITS "dBm"
			MAX-ACCESS read-write
			STATUS current
			DESCRIPTION
				"High RSSI threshold for generating a trap to indicate
				the RSSI is restored."
			::= { wmanIfSsThresholdConfigEntry 2 }

		
		-- 1.3.6.1.2.1.10.184.1.3
		wmanIfCommonObjects OBJECT IDENTIFIER ::= { wmanIfMibObjects 3 }

		
--  Common object group – containing common tables and objects to be 
-- implemented in both Base Station and Subscriber Station
-- 
-- wmanIfCmnPacketCs contain the Packet Convergence Sublayer objects
-- that are common to both Base Station and Subscriber Station 
		-- 1.3.6.1.2.1.10.184.1.3.1
		wmanIfCmnPacketCs OBJECT IDENTIFIER ::= { wmanIfCommonObjects 1 }

		
		-- 1.3.6.1.2.1.10.184.1.3.1.1
		wmanIfCmnClassifierRuleTable OBJECT-TYPE
			SYNTAX SEQUENCE OF WmanIfCmnClassifierRuleEntry
			MAX-ACCESS not-accessible
			STATUS current
			DESCRIPTION
				"This table contains packet classifier rules associated
				with service flows."
			::= { wmanIfCmnPacketCs 1 }

		
		-- 1.3.6.1.2.1.10.184.1.3.1.1.1
		wmanIfCmnClassifierRuleEntry OBJECT-TYPE
			SYNTAX WmanIfCmnClassifierRuleEntry
			MAX-ACCESS not-accessible
			STATUS current
			DESCRIPTION
				"This table provides one row for each packet classifier 
				rule, and is indexed by wmanIfCmnCpsSfIndex and
				wmanIfCmnClassifierRuleIndex. wmanIfCmnCpsSfIndex identifies
				the service flow, and wmanIfCmnClassifierRuleIndexAn
				identifies the packet classifier rule."
			INDEX { wmanIfCmnClassifierRuleIndex, wmanIfCmnCpsSfIndex }
			::= { wmanIfCmnClassifierRuleTable 1 }

		
		WmanIfCmnClassifierRuleEntry ::=
			SEQUENCE { 
				wmanIfCmnClassifierRuleIndex
					Unsigned32,
				wmanIfCmnCpsSfIndex
					Unsigned32,
				wmanIfCmnClassifierRulePriority
					INTEGER,
				wmanIfCmnClassifierRuleIpTosLow
					OCTET STRING,
				wmanIfCmnClassifierRuleIpTosHigh
					OCTET STRING,
				wmanIfCmnClassifierRuleIpTosMask
					OCTET STRING,
				wmanIfCmnClassifierRuleIpProtocol
					Integer32,
				wmanIfCmnClassifierRuleIpAddressType
					InetAddressType,
				wmanIfCmnClassifierRuleIpSourceAddr
					InetAddress,
				wmanIfCmnClassifierRuleIpSourceMask
					InetAddress,
				wmanIfCmnClassifierRuleIpDestAddr
					InetAddress,
				wmanIfCmnClassifierRuleIpDestMask
					InetAddress,
				wmanIfCmnClassifierRuleSourcePortStart
					Integer32,
				wmanIfCmnClassifierRuleSourcePortEnd
					Integer32,
				wmanIfCmnClassifierRuleDestPortStart
					Integer32,
				wmanIfCmnClassifierRuleDestPortEnd
					Integer32,
				wmanIfCmnClassifierRuleDestMacAddr
					MacAddress,
				wmanIfCmnClassifierRuleDestMacMask
					MacAddress,
				wmanIfCmnClassifierRuleSourceMacAddr
					MacAddress,
				wmanIfCmnClassifierRuleSourceMacMask
					MacAddress,
				wmanIfCmnClassifierRuleEnetProtocolType
					INTEGER,
				wmanIfCmnClassifierRuleEnetProtocol
					Integer32,
				wmanIfCmnClassifierRuleUserPriLow
					Integer32,
				wmanIfCmnClassifierRuleUserPriHigh
					Integer32,
				wmanIfCmnClassifierRuleVlanId
					Integer32,
				wmanIfCmnClassifierRuleState
					INTEGER,
				wmanIfCmnClassifierRulePkts
					Counter64,
				wmanIfCmnClassifierRuleBitMap
					WmanIfClassifierBitMap
			 }

		-- 1.3.6.1.2.1.10.184.1.3.1.1.1.1
		wmanIfCmnClassifierRuleIndex OBJECT-TYPE
			SYNTAX Unsigned32 (1..4294967295)
			MAX-ACCESS not-accessible
			STATUS current
			DESCRIPTION
				"An index is assigned to each classifier in the classifiers
				table"
			::= { wmanIfCmnClassifierRuleEntry 1 }

		
		-- 1.3.6.1.2.1.10.184.1.3.1.1.1.2
		wmanIfCmnCpsSfIndex OBJECT-TYPE
			SYNTAX Unsigned32 (1..4294967295)
			MAX-ACCESS not-accessible
			STATUS current
			DESCRIPTION
				"A 32 bit quantity that uniquely identifies a service flow
				to both the subscriber station and base station (BS)."
			::= { wmanIfCmnClassifierRuleEntry 2 }

		
		-- 1.3.6.1.2.1.10.184.1.3.1.1.1.3
		wmanIfCmnClassifierRulePriority OBJECT-TYPE
			SYNTAX INTEGER (0..255)
			MAX-ACCESS read-only
			STATUS current
			DESCRIPTION
				"The value specifies the order of evaluation of the
				classifiers. The higher the value the higher the 
				priority. The value of 0 is used as default in
				provisioned service flows classifiers. The default
				value of 64 is used for dynamic service flow classifiers.
				If the referenced parameter is not present in a classifier,
				this object reports the default value as defined above"
			REFERENCE
				"Section 11.13.19.3.4.1 in IEEE 802.16REVd/D5-2004"
			DEFVAL { 0 }
			::= { wmanIfCmnClassifierRuleEntry 3 }

		
		-- 1.3.6.1.2.1.10.184.1.3.1.1.1.4
		wmanIfCmnClassifierRuleIpTosLow OBJECT-TYPE
			SYNTAX OCTET STRING (SIZE (1))
			MAX-ACCESS read-only
			STATUS current
			DESCRIPTION
				"The low value of a range of TOS byte values. If the
				referenced parameter is not present in a classifier, this
				object reports the value of 0."
			REFERENCE
				"Section 11.13.19.3.4.2 in IEEE 802.16REVd/D5-2004"
			::= { wmanIfCmnClassifierRuleEntry 4 }

		
		-- 1.3.6.1.2.1.10.184.1.3.1.1.1.5
		wmanIfCmnClassifierRuleIpTosHigh OBJECT-TYPE
			SYNTAX OCTET STRING (SIZE (1))
			MAX-ACCESS read-only
			STATUS current
			DESCRIPTION
				"The 8-bit high value of a range of TOS byte values.
				If the referenced parameter is not present in a classifier,
				this object reports the value of 0."
			REFERENCE
				"Section 11.13.19.3.4.2 in IEEE 802.16REVd/D5-2004"
			::= { wmanIfCmnClassifierRuleEntry 5 }

		
		-- 1.3.6.1.2.1.10.184.1.3.1.1.1.6
		wmanIfCmnClassifierRuleIpTosMask OBJECT-TYPE
			SYNTAX OCTET STRING (SIZE (1))
			MAX-ACCESS read-only
			STATUS current
			DESCRIPTION
				"The mask value is bitwise ANDed with TOS byte in an IP
				packet and this value is used check range checking of
				TosLow and TosHigh. If the referenced parameter is not
				present in a classifier, this object reports the value
				of 0."
			REFERENCE
				"Section 11.13.19.3.4.2 in IEEE 802.16REVd/D5-2004"
			::= { wmanIfCmnClassifierRuleEntry 6 }

		
		-- 1.3.6.1.2.1.10.184.1.3.1.1.1.7
		wmanIfCmnClassifierRuleIpProtocol OBJECT-TYPE
			SYNTAX Integer32 (0..255)
			MAX-ACCESS read-only
			STATUS current
			DESCRIPTION
				"This object indicates the value of the IP Protocol field
				required for IP packets to match this rule. If the
				referenced parameter is not present in a classifier, this
				object reports the value of 0."
			REFERENCE
				"Section 11.13.19.3.4.3 in IEEE 802.16REVd/D5-2004"
			::= { wmanIfCmnClassifierRuleEntry 7 }

		
		-- 1.3.6.1.2.1.10.184.1.3.1.1.1.8
		wmanIfCmnClassifierRuleIpAddressType OBJECT-TYPE
			SYNTAX InetAddressType
			MAX-ACCESS read-only
			STATUS current
			DESCRIPTION
				"The type of the internet address for
				wmanIfCmnClassifierRuleIpSourceAddr,
				wmanIfCmnClassifierRuleIpSourceMask,
				wmanIfCmnClassifierRuleIpDestAddr, and
				wmanIfCmnClassifierRuleIpDestMask.
				If the referenced parameter is not present in a classifier,
				this object reports the value of ipv4(1)."
			REFERENCE
				"Section 11.13.19.3.4.4 in IEEE 802.16REVd/D5-2004"
			::= { wmanIfCmnClassifierRuleEntry 8 }

		
		-- 1.3.6.1.2.1.10.184.1.3.1.1.1.9
		wmanIfCmnClassifierRuleIpSourceAddr OBJECT-TYPE
			SYNTAX InetAddress
			MAX-ACCESS read-only
			STATUS current
			DESCRIPTION
				"This object specifies the value of the IP Source Address
				required for packets to match this rule. An IP packet
				matches the rule when the packet ip source address bitwise
				ANDed with the wmanIfCmnClassifierRuleIpSourceMask value
				equals the wmanIfCmnClassifierRuleIpSourceAddr value.
				If the referenced parameter is not present n a classifier,
				this object reports the value of 0.0.0.0."
			REFERENCE
				"Section 11.13.19.3.4.4 in IEEE 802.16REVd/D5-2004"
			::= { wmanIfCmnClassifierRuleEntry 9 }

		
		-- 1.3.6.1.2.1.10.184.1.3.1.1.1.10
		wmanIfCmnClassifierRuleIpSourceMask OBJECT-TYPE
			SYNTAX InetAddress
			MAX-ACCESS read-only
			STATUS current
			DESCRIPTION
				"This object specifies which bits of a packet's IP Source
				Address that are compared to match this rule. An IP packet
				matches the rule when the packet source address bitwise
				ANDed with the
				wmanIfCmnClassifierRuleIpSourceMask value equals the
				wmanIfCmnClassifierRuleIpSourceAddr value.
				If the referenced parameter is not present in a classifier,
				this object reports the value of 0.0.0.0."
			REFERENCE
				"Section 11.13.19.3.4.4 in IEEE 802.16REVd/D5-2004"
			::= { wmanIfCmnClassifierRuleEntry 10 }

		
		-- 1.3.6.1.2.1.10.184.1.3.1.1.1.11
		wmanIfCmnClassifierRuleIpDestAddr OBJECT-TYPE
			SYNTAX InetAddress
			MAX-ACCESS read-only
			STATUS current
			DESCRIPTION
				"This object specifies the value of the IP Destination
				Address required for packets to match this rule. An IP
				packet matches the rule when the packet IP destination
				address bitwise ANDed with the
				wmanIfCmnClassifierRuleIpDestMask value equals the
				wmanIfCmnClassifierRuleIpDestAddr value.
				If the referenced parameter is not present in a 
				classifier, this object reports the value of 0.0.0.0."
			REFERENCE
				"Section 11.13.19.3.4.5 in IEEE 802.16REVd/D5-2004"
			::= { wmanIfCmnClassifierRuleEntry 11 }

		
		-- 1.3.6.1.2.1.10.184.1.3.1.1.1.12
		wmanIfCmnClassifierRuleIpDestMask OBJECT-TYPE
			SYNTAX InetAddress
			MAX-ACCESS read-only
			STATUS current
			DESCRIPTION
				"This object specifies which bits of a packet's IP 
				Destination Address that are compared to match this rule.
				An IP packet matches the rule when the packet destination
				address bitwise ANDed with the
				wmanIfCmnClassifierRuleIpDestMask value equals the
				wmanIfCmnClassifierRuleIpDestAddr value.
				If the referenced parameter is not present in a classifier
				, this object reports the value of 0.0.0.0."
			REFERENCE
				"Section 11.13.19.3.4.5 in IEEE 802.16REVd/D5-2004"
			::= { wmanIfCmnClassifierRuleEntry 12 }

		
		-- 1.3.6.1.2.1.10.184.1.3.1.1.1.13
		wmanIfCmnClassifierRuleSourcePortStart OBJECT-TYPE
			SYNTAX Integer32 (0..65535)
			MAX-ACCESS read-only
			STATUS current
			DESCRIPTION
				"This object specifies the low end inclusive range of
				TCP/UDP source port numbers to which a packet is compared
				. This object is irrelevant for non-TCP/UDP IP packets.
				If the referenced parameter is not present in a
				classifier, this object reports the value of 0."
			REFERENCE
				"Section 11.13.19.3.4.6 in IEEE 802.16REVd/D5-2004"
			::= { wmanIfCmnClassifierRuleEntry 13 }

		
		-- 1.3.6.1.2.1.10.184.1.3.1.1.1.14
		wmanIfCmnClassifierRuleSourcePortEnd OBJECT-TYPE
			SYNTAX Integer32 (0..65535)
			MAX-ACCESS read-only
			STATUS current
			DESCRIPTION
				"This object specifies the high end inclusive range of
				TCP/UDP source port numbers to which a packet is compared.
				This object is irrelevant for non-TCP/UDP IP packets.
				If the referenced parameter is not present in a classifier,
				this object reports the value of 65535."
			REFERENCE
				"Section 11.13.19.3.4.6 in IEEE 802.16REVd/D5-2004"
			::= { wmanIfCmnClassifierRuleEntry 14 }

		
		-- 1.3.6.1.2.1.10.184.1.3.1.1.1.15
		wmanIfCmnClassifierRuleDestPortStart OBJECT-TYPE
			SYNTAX Integer32 (0..65535)
			MAX-ACCESS read-only
			STATUS current
			DESCRIPTION
				"This object specifies the low end inclusive range of
				TCP/UDP destination port numbers to which a packet is
				compared. If the referenced parameter is not present
				in a classifier, this object reports the value of 0."
			REFERENCE
				"Section 11.13.19.3.4.7 in IEEE 802.16REVd/D5-2004"
			::= { wmanIfCmnClassifierRuleEntry 15 }

		
		-- 1.3.6.1.2.1.10.184.1.3.1.1.1.16
		wmanIfCmnClassifierRuleDestPortEnd OBJECT-TYPE
			SYNTAX Integer32 (0..65535)
			MAX-ACCESS read-only
			STATUS current
			DESCRIPTION
				"This object specifies the high end inclusive range of
				TCP/UDP destination port numbers to which a packet is
				compared. If the referenced parameter is not present
				in a classifier, this object reports the value of
				65535."
			REFERENCE
				"Section 11.13.19.3.4.7 in IEEE 802.16REVd/D5-2004"
			::= { wmanIfCmnClassifierRuleEntry 16 }

		
		-- 1.3.6.1.2.1.10.184.1.3.1.1.1.17
		wmanIfCmnClassifierRuleDestMacAddr OBJECT-TYPE
			SYNTAX MacAddress
			MAX-ACCESS read-only
			STATUS current
			DESCRIPTION
				"An Ethernet packet matches an entry when its destination
				MAC address bitwise ANDed with 
				wmanIfCmnClassifierRuleDestMacMask equals the value of
				wmanIfCmnClassifierRuleDestMacAddr. If the referenced
				parameter is not present in a classifier, this object
				reports the value of '000000000000'H."
			REFERENCE
				"Section 11.13.19.3.4.8 in IEEE 802.16REVd/D5-2004"
			::= { wmanIfCmnClassifierRuleEntry 17 }

		
		-- 1.3.6.1.2.1.10.184.1.3.1.1.1.18
		wmanIfCmnClassifierRuleDestMacMask OBJECT-TYPE
			SYNTAX MacAddress
			MAX-ACCESS read-only
			STATUS current
			DESCRIPTION
				"An Ethernet packet matches an entry when its destination
				MAC address bitwise ANDed with
				wmanIfCmnClassifierRuleDestMacMask equals the value of
				wmanIfCmnClassifierRuleDestMacAddr. If the referenced
				parameter is not present in a classifier, this object
				reports the value of '000000000000'H."
			REFERENCE
				"Section 11.13.19.3.4.8 in IEEE 802.16REVd/D5-2004"
			::= { wmanIfCmnClassifierRuleEntry 18 }

		
		-- 1.3.6.1.2.1.10.184.1.3.1.1.1.19
		wmanIfCmnClassifierRuleSourceMacAddr OBJECT-TYPE
			SYNTAX MacAddress
			MAX-ACCESS read-only
			STATUS current
			DESCRIPTION
				"An Ethernet packet matches this entry when its source
				MAC address  bitwise ANDed with
				wmanIfCmnClassifierRuleSourceMacMask equals the value
				of wmanIfCmnClassifierRuleSourceMacAddr. If the
				referenced parameter is not present in a classifier,
				this object reports the value of '000000000000'H."
			REFERENCE
				"Section 11.13.19.3.4.9 in IEEE 802.16REVd/D5-2004"
			::= { wmanIfCmnClassifierRuleEntry 19 }

		
		-- 1.3.6.1.2.1.10.184.1.3.1.1.1.20
		wmanIfCmnClassifierRuleSourceMacMask OBJECT-TYPE
			SYNTAX MacAddress
			MAX-ACCESS read-only
			STATUS current
			DESCRIPTION
				"An Ethernet packet matches an entry when its destination
				MAC address bitwise ANDed with
				wmanIfCmnClassifierRuleSourceMacMask equals the value of
				wmanIfCmnClassifierRuleSourceMacAddr. If the referenced
				parameter is not present in a classifier, this object
				reports the value of '000000000000'H."
			REFERENCE
				"Section 11.13.19.3.4.9 in IEEE 802.16REVd/D5-2004"
			::= { wmanIfCmnClassifierRuleEntry 20 }

		
		-- 1.3.6.1.2.1.10.184.1.3.1.1.1.21
		wmanIfCmnClassifierRuleEnetProtocolType OBJECT-TYPE
			SYNTAX INTEGER
				{
				none(0),
				ethertype(1),
				dsap(2)
				}
			MAX-ACCESS read-only
			STATUS current
			DESCRIPTION
				"This object indicates the format of the layer 3 protocol
				id in the Ethernet packet. A value of none(0) means that
				the rule does not use the layer 3 protocol type as a
				matching criteria. A value of ethertype(1) means that the
				rule applies only to frames which contains an EtherType
				value. Ethertype values are contained in packets using
				the Dec-Intel-Xerox (DIX) encapsulation or the RFC1042
				Sub-Network Access Protocol (SNAP) encapsulation formats.
				A value of dsap(2) means that the rule applies only to
				frames using the IEEE802.3 encapsulation format with a
				Destination Service Access Point (DSAP) other than 0xAA
				(which is reserved for SNAP). If the Ethernet frame
				contains an 802.1P/Q Tag header (i.e. EtherType 0x8100),
				this object applies to the embedded EtherType field within
				the 802.1P/Q header. If the referenced parameter is not
				present in a classifier, this object reports the value of
				0."
			REFERENCE
				"Section 11.13.19.3.4.10 in IEEE 802.16REVd/D5-2004"
			::= { wmanIfCmnClassifierRuleEntry 21 }

		
		-- 1.3.6.1.2.1.10.184.1.3.1.1.1.22
		wmanIfCmnClassifierRuleEnetProtocol OBJECT-TYPE
			SYNTAX Integer32 (0..65535)
			MAX-ACCESS read-only
			STATUS current
			DESCRIPTION
				"If wmanIfCmnClassifierRuleEnetProtocolType is none(0),
				this object is ignored when considering whether a packet
				matches the current rule.
				If wmanIfCmnClassifierRuleEnetProtocolType is ethertype(1),
				this object gives the 16-bit value of the EtherType that
				the packet must match in order to match the rule.
				If wmanIfCmnClassifierRuleEnetProtocolType is dsap(2), the
				lower 8 bits of this object's value must match the DSAP
				byte of the packet in order to match the rule.
				If the Ethernet frame contains an 802.1P/Q Tag header
				(i.e. EtherType 0x8100), this object applies to the
				embedded EtherType field within the 802.1P/Q header.
				If the referenced parameter is not present in the
				classifier, the value of this object is reported as 0."
			REFERENCE
				"Section 11.13.19.3.4.10 in IEEE 802.16REVd/D5-2004"
			::= { wmanIfCmnClassifierRuleEntry 22 }

		
		-- 1.3.6.1.2.1.10.184.1.3.1.1.1.23
		wmanIfCmnClassifierRuleUserPriLow OBJECT-TYPE
			SYNTAX Integer32 (0..7)
			MAX-ACCESS read-only
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority field
				within the range of wmanIfCmnClassifierRulePriLow and
				wmanIfCmnClassifierRulePriHigh in order to match this
				rule.
				If the referenced parameter is not present in the
				classifier, the value of this object is reported as 0."
			REFERENCE
				"Section 11.13.19.3.4.11 in IEEE 802.16REVd/D5-2004"
			::= { wmanIfCmnClassifierRuleEntry 23 }

		
		-- 1.3.6.1.2.1.10.184.1.3.1.1.1.24
		wmanIfCmnClassifierRuleUserPriHigh OBJECT-TYPE
			SYNTAX Integer32 (0..7)
			MAX-ACCESS read-only
			STATUS current
			DESCRIPTION
				"This object applies only to Ethernet frames using the
				802.1P/Q tag header (indicated with EtherType 0x8100).
				Such frames include a 16-bit Tag that contains a 3 bit
				Priority field and a 12 bit VLAN number.
				Tagged Ethernet packets must have a 3-bit Priority
				field within the range of wmanIfCmnClassifierRulePriLow
				and wmanIfCmnClassifierRulePriHigh in order to match
				this rule.
				If the referenced parameter is not present in the 
				classifier, the value of this object is reported as 7."
			REFERENCE
				"Section 11.13.19.3.4.11 in IEEE 802.16REVd/D5-2004"
			::= { wmanIfCmnClassifierRuleEntry 24 }

		
		-- 1.3.6.1.2.1.10.184.1.3.1.1.1.25
		wmanIfCmnClassifierRuleVlanId OBJECT-TYPE
			SYNTAX Integer32 (0..4095)
			MAX-ACCESS read-only
			STATUS current
			DESCRIPTION
				"This object applies only to Ethernet frames using the
				802.1P/Q tag header.
				If this object's value is nonzero, tagged packets must
				have a VLAN Identifier that matches the value in order
				to match the rule.
				Only the least significant 12 bits of this object's
				value are valid.
				If the referenced parameter is not present in the
				classifier, the value of this object is reported as 0."
			REFERENCE
				"Section 11.13.19.3.4.12 in IEEE 802.16REVd/D5-2004"
			::= { wmanIfCmnClassifierRuleEntry 25 }

		
		-- 1.3.6.1.2.1.10.184.1.3.1.1.1.26
		wmanIfCmnClassifierRuleState OBJECT-TYPE
			SYNTAX INTEGER
				{
				active(1),
				inactive(2)
				}
			MAX-ACCESS read-only
			STATUS current
			DESCRIPTION
				"This object indicates whether or not the classifier is
				enabled to classify packets to a Service Flow.
				If the referenced parameter is not present in the
				classifier, the value of this object is reported
				as active(1)."
			::= { wmanIfCmnClassifierRuleEntry 26 }

		
		-- 1.3.6.1.2.1.10.184.1.3.1.1.1.27
		wmanIfCmnClassifierRulePkts OBJECT-TYPE
			SYNTAX Counter64
			MAX-ACCESS read-only
			STATUS current
			DESCRIPTION
				"This object counts the number of packets that have
				been classified using this entry."
			::= { wmanIfCmnClassifierRuleEntry 27 }

		
		-- 1.3.6.1.2.1.10.184.1.3.1.1.1.28
		wmanIfCmnClassifierRuleBitMap OBJECT-TYPE
			SYNTAX WmanIfClassifierBitMap
			MAX-ACCESS read-only
			STATUS current
			DESCRIPTION
				"This object indicates which parameter encodings were
				actually present in the entry. A bit set to '1' indicates
				the corresponding classifier encoding is present, and '0'
				means otherwise"
			::= { wmanIfCmnClassifierRuleEntry 28 }

		
--  wmanIfCmnCps contain the Common Part Sublayer objects that are
-- common to both Base Station and Subscriber Station
		-- 1.3.6.1.2.1.10.184.1.3.2
		wmanIfCmnCps OBJECT IDENTIFIER ::= { wmanIfCommonObjects 2 }

		
		-- 1.3.6.1.2.1.10.184.1.3.2.1
		wmanIfCmnCpsServiceFlowTable OBJECT-TYPE
			SYNTAX SEQUENCE OF WmanIfCmnCpsServiceFlowEntry
			MAX-ACCESS not-accessible
			STATUS deprecated
			DESCRIPTION
				"This table contains Service Flows that are created in
				both BS and SS.
				
				DEPRECATED: asmaxCmnCpsServiceFlowTable is based on the 
				Draft6 MIB and should be implemented instead."
			::= { wmanIfCmnCps 1 }

		
		-- 1.3.6.1.2.1.10.184.1.3.2.1.1
		wmanIfCmnCpsServiceFlowEntry OBJECT-TYPE
			SYNTAX WmanIfCmnCpsServiceFlowEntry
			MAX-ACCESS not-accessible
			STATUS deprecated
			DESCRIPTION
				"This table provides one row for each service flow, and is
				indexed by wmanIfCmnCpsSfId. The value of wmanIfCmnCpsSfId
				is obtained from wmanIfBsSfId."
			INDEX { wmanIfCmnCpsSfId }
			::= { wmanIfCmnCpsServiceFlowTable 1 }

		
		WmanIfCmnCpsServiceFlowEntry ::=
			SEQUENCE { 
				wmanIfCmnCpsSfId
					Unsigned32,
				wmanIfCmnCpsSfCid
					INTEGER,
				wmanIfCmnCpsSfDirection
					INTEGER,
				wmanIfCmnCpsSfState
					INTEGER,
				wmanIfCmnCpsServiceClassName
					DisplayString,
				wmanIfCmnCpsTrafficPriority
					INTEGER,
				wmanIfCmnCpsMaxSustainedRate
					INTEGER,
				wmanIfCmnCpsMaxTrafficBurst
					INTEGER,
				wmanIfCmnCpsMinReservedRate
					INTEGER,
				wmanIfCmnCpsToleratedJitter
					INTEGER,
				wmanIfCmnCpsMaxLatency
					INTEGER,
				wmanIfCmnCpsFixedVsVariableSduInd
					INTEGER,
				wmanIfCmnCpsSduSize
					INTEGER,
				wmanIfCmnCpsSfSchedulingType
					WmanIfSfSchedulingType,
				wmanIfCmnCpsArqEnable
					TruthValue,
				wmanIfCmnCpsArqWindowSize
					INTEGER,
				wmanIfCmnCpsArqFragmentLifetime
					INTEGER,
				wmanIfCmnCpsArqSyncLossTimeout
					INTEGER,
				wmanIfCmnCpsArqDeliverInOrder
					TruthValue,
				wmanIfCmnCpsArqRxPurgeTimeout
					INTEGER,
				wmanIfCmnCpsArqBlockSize
					INTEGER,
				wmanIfCmnCpsMinRsvdTolerableRate
					INTEGER,
				wmanIfCmnCpsReqTxPolicy
					BITS
			 }

		-- 1.3.6.1.2.1.10.184.1.3.2.1.1.1
		wmanIfCmnCpsSfId OBJECT-TYPE
			SYNTAX Unsigned32 (1..4294967295)
			MAX-ACCESS not-accessible
			STATUS deprecated
			DESCRIPTION
				"A 32 bit quantity that uniquely identifies a service flow
				to both the subscriber station and base station (BS)."
			::= { wmanIfCmnCpsServiceFlowEntry 1 }

		
		-- 1.3.6.1.2.1.10.184.1.3.2.1.1.2
		wmanIfCmnCpsSfCid OBJECT-TYPE
			SYNTAX INTEGER
			MAX-ACCESS read-only
			STATUS deprecated
			DESCRIPTION
				"A 16 bit channel identifier to identify the connection
				being created by DSA."
			::= { wmanIfCmnCpsServiceFlowEntry 2 }

		
		-- 1.3.6.1.2.1.10.184.1.3.2.1.1.3
		wmanIfCmnCpsSfDirection OBJECT-TYPE
			SYNTAX INTEGER
				{
				downstream(1),
				upstream(2)
				}
			MAX-ACCESS read-only
			STATUS deprecated
			DESCRIPTION
				"An attribute indiating the service flow is downstream or
				upstream."
			::= { wmanIfCmnCpsServiceFlowEntry 3 }

		
		-- 1.3.6.1.2.1.10.184.1.3.2.1.1.4
		wmanIfCmnCpsSfState OBJECT-TYPE
			SYNTAX INTEGER
				{
				provisioned(1),
				admitted(2),
				active(3)
				}
			MAX-ACCESS read-only
			STATUS deprecated
			DESCRIPTION
				"wmanIfCmnCpsSfState indicates the service flow state:
				Provisioned, AdmittedState(2), and Active service flow
				state."
			REFERENCE
				"Section 6.4.13.6, in IEEE 802.16REVd/D5-2004"
			::= { wmanIfCmnCpsServiceFlowEntry 4 }

		
		-- 1.3.6.1.2.1.10.184.1.3.2.1.1.5
		wmanIfCmnCpsServiceClassName OBJECT-TYPE
			SYNTAX DisplayString
			MAX-ACCESS read-only
			STATUS deprecated
			DESCRIPTION
				"Refers to the Service Class Name"
			REFERENCE
				"Section 11.13.3 in IEEE 802.16REVd/D5-2004"
			::= { wmanIfCmnCpsServiceFlowEntry 5 }

		
		-- 1.3.6.1.2.1.10.184.1.3.2.1.1.6
		wmanIfCmnCpsTrafficPriority OBJECT-TYPE
			SYNTAX INTEGER
			MAX-ACCESS read-only
			STATUS deprecated
			DESCRIPTION
				"The value of this parameter specifies the priority
				assigned to a service flow. For uplink service flows,
				the BS should use this parameter when determining
				precedence in request service and grant generation,
				and the SS shall preferentially select contention
				Request opportunities for Priority Request CIDs
				based on this priority"
			REFERENCE
				"Section 11.13.7 in IEEE 802.16REVd/D5-2004"
			::= { wmanIfCmnCpsServiceFlowEntry 6 }

		
		-- 1.3.6.1.2.1.10.184.1.3.2.1.1.7
		wmanIfCmnCpsMaxSustainedRate OBJECT-TYPE
			SYNTAX INTEGER
			UNITS "bps"
			MAX-ACCESS read-only
			STATUS deprecated
			DESCRIPTION
				"This parameter defines the peak information rate
				of the service. The rate is expressed in bits per
				second and pertains to the SDUs at the input to
				the system."
			REFERENCE
				"Section 11.13.8 in IEEE 802.16REVd/D5-2004"
			::= { wmanIfCmnCpsServiceFlowEntry 7 }

		
		-- 1.3.6.1.2.1.10.184.1.3.2.1.1.8
		wmanIfCmnCpsMaxTrafficBurst OBJECT-TYPE
			SYNTAX INTEGER
			UNITS "byte"
			MAX-ACCESS read-only
			STATUS deprecated
			DESCRIPTION
				"This parameter defines the maximum burst size that
				must be accommodated for the service."
			REFERENCE
				"Section 11.13.9 in IEEE 802.16REVd/D5-2004"
			::= { wmanIfCmnCpsServiceFlowEntry 8 }

		
		-- 1.3.6.1.2.1.10.184.1.3.2.1.1.9
		wmanIfCmnCpsMinReservedRate OBJECT-TYPE
			SYNTAX INTEGER
			UNITS "byte"
			MAX-ACCESS read-only
			STATUS deprecated
			DESCRIPTION
				"This parameter specifies the minimum rate reserved
				for this service flow."
			REFERENCE
				"Section 11.13.10 in IEEE 802.16REVd/D5-2004"
			::= { wmanIfCmnCpsServiceFlowEntry 9 }

		
		-- 1.3.6.1.2.1.10.184.1.3.2.1.1.10
		wmanIfCmnCpsToleratedJitter OBJECT-TYPE
			SYNTAX INTEGER
			UNITS "millisecond"
			MAX-ACCESS read-only
			STATUS deprecated
			DESCRIPTION
				"This parameter defines the Maximum delay 
				variation (jitter) for the connection."
			REFERENCE
				"Section 11.13.15 in IEEE 802.16REVd/D5-2004"
			::= { wmanIfCmnCpsServiceFlowEntry 10 }

		
		-- 1.3.6.1.2.1.10.184.1.3.2.1.1.11
		wmanIfCmnCpsMaxLatency OBJECT-TYPE
			SYNTAX INTEGER
			UNITS "millisecond"
			MAX-ACCESS read-only
			STATUS deprecated
			DESCRIPTION
				"The value of this parameter specifies the maximum
				latency between the reception of a packet by the BS
				or SS on its network interface and the forwarding
				of the packet to its RF Interface."
			REFERENCE
				"Section 11.13.16 in IEEE 802.16REVd/D5-2004"
			::= { wmanIfCmnCpsServiceFlowEntry 11 }

		
		-- 1.3.6.1.2.1.10.184.1.3.2.1.1.12
		wmanIfCmnCpsFixedVsVariableSduInd OBJECT-TYPE
			SYNTAX INTEGER
				{
				variableLengthSdu(0),
				fixedLengthSdu(1)
				}
			MAX-ACCESS read-only
			STATUS deprecated
			DESCRIPTION
				"The value of this parameter specifies whether the SDUs
				on the service flow are variable-length (0) or 
				fixed-length (1). The parameter is used only if
				packing is on for the service flow. The default value
				is 0, i.e.,variable-length SDUs."
			REFERENCE
				"Section 11.13.15 in IEEE 802.16REVd/D5-2004"
			DEFVAL { 0 }
			::= { wmanIfCmnCpsServiceFlowEntry 12 }

		
		-- 1.3.6.1.2.1.10.184.1.3.2.1.1.13
		wmanIfCmnCpsSduSize OBJECT-TYPE
			SYNTAX INTEGER
			UNITS "byte"
			MAX-ACCESS read-only
			STATUS deprecated
			DESCRIPTION
				"The value of this parameter specifies the length of the
				SDU for a fixed-length SDU service flow. This parameter
				is used only if packing is on and the service flow is
				indicated as carrying fixed-length SDUs. The default
				value is 49 bytes, i.e., VC-switched ATM cells with PHS.
				The parameter is relevant for both ATM and Packet
				Convergence Sublayers."
			REFERENCE
				"Section 11.13.17 in IEEE 802.16REVd/D5-2004"
			DEFVAL { 49 }
			::= { wmanIfCmnCpsServiceFlowEntry 13 }

		
		-- 1.3.6.1.2.1.10.184.1.3.2.1.1.14
		wmanIfCmnCpsSfSchedulingType OBJECT-TYPE
			SYNTAX WmanIfSfSchedulingType
			MAX-ACCESS read-only
			STATUS deprecated
			DESCRIPTION
				"Specifies the upstream scheduling service used for
				upstream service flow. If the referenced parameter
				is not present in the corresponding 802.16 QOS
				Parameter Set of an upstream service flow, the
				default value of this object is bestEffort(2)."
			REFERENCE
				"Section 11.13.11 in IEEE 802.16REVd/D5-2004"
			DEFVAL { 2 }
			::= { wmanIfCmnCpsServiceFlowEntry 14 }

		
		-- 1.3.6.1.2.1.10.184.1.3.2.1.1.15
		wmanIfCmnCpsArqEnable OBJECT-TYPE
			SYNTAX TruthValue
			MAX-ACCESS read-only
			STATUS deprecated
			DESCRIPTION
				"True(1) ARQ enabling is requested for the connection."
			::= { wmanIfCmnCpsServiceFlowEntry 15 }

		
		-- 1.3.6.1.2.1.10.184.1.3.2.1.1.16
		wmanIfCmnCpsArqWindowSize OBJECT-TYPE
			SYNTAX INTEGER (1..1024)
			MAX-ACCESS read-only
			STATUS deprecated
			DESCRIPTION
				"Indicates the maximum number of unacknowledged 
				fragments at any time."
			::= { wmanIfCmnCpsServiceFlowEntry 16 }

		
		-- 1.3.6.1.2.1.10.184.1.3.2.1.1.17
		wmanIfCmnCpsArqFragmentLifetime OBJECT-TYPE
			SYNTAX INTEGER (0..65535)
			UNITS "10 us"
			MAX-ACCESS read-only
			STATUS deprecated
			DESCRIPTION
				"The maximum time interval an ARQ fragment will be
				managed by the transmitter ARQ machine, once
				initial transmission of the fragment has occured.
				If transmission or retransmission of the fragment
				is not acknowledged by the receiver before the 
				time limit is reached, the fragmnet is discarded.
				A value of 0 means Infinite."
			::= { wmanIfCmnCpsServiceFlowEntry 17 }

		
		-- 1.3.6.1.2.1.10.184.1.3.2.1.1.18
		wmanIfCmnCpsArqSyncLossTimeout OBJECT-TYPE
			SYNTAX INTEGER (0..65535)
			UNITS "10 us"
			MAX-ACCESS read-only
			STATUS deprecated
			DESCRIPTION
				"The maximum interval before declaring a loss
				of synchronization of the sender and receiver
				state machines. A value of 0 means Infinite."
			::= { wmanIfCmnCpsServiceFlowEntry 18 }

		
		-- 1.3.6.1.2.1.10.184.1.3.2.1.1.19
		wmanIfCmnCpsArqDeliverInOrder OBJECT-TYPE
			SYNTAX TruthValue
			MAX-ACCESS read-only
			STATUS deprecated
			DESCRIPTION
				"Indicates whether or not data is to be delivered
				by the receiving MAC to its client application
				in the order in which data was handed off to the
				originating MAC."
			::= { wmanIfCmnCpsServiceFlowEntry 19 }

		
		-- 1.3.6.1.2.1.10.184.1.3.2.1.1.20
		wmanIfCmnCpsArqRxPurgeTimeout OBJECT-TYPE
			SYNTAX INTEGER (0..65535)
			UNITS "10 us"
			MAX-ACCESS read-only
			STATUS deprecated
			DESCRIPTION
				"Indicates the time interval the ARQ window is advanced
				after a fragment is received. A value of 0 means
				Infinite."
			::= { wmanIfCmnCpsServiceFlowEntry 20 }

		
		-- 1.3.6.1.2.1.10.184.1.3.2.1.1.21
		wmanIfCmnCpsArqBlockSize OBJECT-TYPE
			SYNTAX INTEGER (1..2040)
			UNITS "byte"
			MAX-ACCESS read-only
			STATUS deprecated
			DESCRIPTION
				"This value of this parameter specifies the size of an
				ARQ block. This parameter shall be established by
				negotiation during the connection creation dialog."
			REFERENCE
				"Section 11.13.18.8 in IEEE 802.16REVd/D5-2004"
			::= { wmanIfCmnCpsServiceFlowEntry 21 }

		
		-- 1.3.6.1.2.1.10.184.1.3.2.1.1.22
		wmanIfCmnCpsMinRsvdTolerableRate OBJECT-TYPE
			SYNTAX INTEGER
			UNITS "bps"
			MAX-ACCESS read-only
			STATUS deprecated
			DESCRIPTION
				"Minimum Tolerable Traffic Rate = R (bits/sec) with
				time base T(sec) means the following. Let S denote
				additional demand accumulated at the MAC SAP of the
				transmitter during an arbitrary time interval of the
				length T. Then the amount of data forwarded at the
				receiver to CS (in bits) during this interval should
				be not less than min {S, R * T}."
			REFERENCE
				"Section 11.13.11 in IEEE 802.16REVd/D5-2004"
			::= { wmanIfCmnCpsServiceFlowEntry 22 }

		
		-- 1.3.6.1.2.1.10.184.1.3.2.1.1.23
		wmanIfCmnCpsReqTxPolicy OBJECT-TYPE
			SYNTAX BITS
				{
				noBroadcastBwReq(0),
				reserved1(1),
				noPiggybackReq(2),
				noFragmentData(3),
				noPHS(4),
				noSduPacking(5),
				noCrc(6),
				reserved2(7)
				}
			MAX-ACCESS read-only
			STATUS deprecated
			DESCRIPTION
				"The value of this parameter provides the capability to
				specify certain attributes for the associated service
				flow. An attribute is enabled by setting the
				corresponding bit position to 1."
			REFERENCE
				"Section 11.13.12 in IEEE 802.16REVd/D5-2004"
			::= { wmanIfCmnCpsServiceFlowEntry 23 }

		
--  wmanIfCmnBsSsConfigurationTable contains global parameters
-- common in BS and SS         
		-- 1.3.6.1.2.1.10.184.1.3.2.2
		wmanIfCmnBsSsConfigurationTable OBJECT-TYPE
			SYNTAX SEQUENCE OF WmanIfCmnBsSsConfigurationEntry
			MAX-ACCESS not-accessible
			STATUS current
			DESCRIPTION
				"This table provides one row for each BS sector that
				contains the system parameters common in both SS and
				BS. All SSs shall have the same parameters as the BS
				to which the SSs are associated."
			::= { wmanIfCmnCps 2 }

		
		-- 1.3.6.1.2.1.10.184.1.3.2.2.1
		wmanIfCmnBsSsConfigurationEntry OBJECT-TYPE
			SYNTAX WmanIfCmnBsSsConfigurationEntry
			MAX-ACCESS not-accessible
			STATUS current
			DESCRIPTION
				"This table is indexed by ifIndex, indicating BS
				sector."
			INDEX { ifIndex }
			::= { wmanIfCmnBsSsConfigurationTable 1 }

		
		WmanIfCmnBsSsConfigurationEntry ::=
			SEQUENCE { 
				wmanIfCmnInvitedRangRetries
					INTEGER,
				wmanIfCmnMinislotSize
					INTEGER,
				wmanIfCmnDSxReqRetries
					INTEGER,
				wmanIfCmnDSxRespRetries
					INTEGER,
				wmanIfCmnT7Timeout
					INTEGER,
				wmanIfCmnT8Timeout
					INTEGER,
				wmanIfCmnT10Timeout
					INTEGER,
				wmanIfCmnT22Timeout
					INTEGER
			 }

		-- 1.3.6.1.2.1.10.184.1.3.2.2.1.1
		wmanIfCmnInvitedRangRetries OBJECT-TYPE
			SYNTAX INTEGER (16..65535)
			MAX-ACCESS read-write
			STATUS current
			DESCRIPTION
				"Number of retries on inviting Ranging Requests."
			::= { wmanIfCmnBsSsConfigurationEntry 1 }

		
		-- 1.3.6.1.2.1.10.184.1.3.2.2.1.2
		wmanIfCmnMinislotSize OBJECT-TYPE
			SYNTAX INTEGER (1..100)
			MAX-ACCESS read-write
			STATUS current
			DESCRIPTION
				"Size of minislot for uplink transmission. Shall be a power
				of 2 (in units of PS)."
			::= { wmanIfCmnBsSsConfigurationEntry 2 }

		
		-- 1.3.6.1.2.1.10.184.1.3.2.2.1.3
		wmanIfCmnDSxReqRetries OBJECT-TYPE
			SYNTAX INTEGER
			MAX-ACCESS read-write
			STATUS current
			DESCRIPTION
				"Number of Timeout Retries on DSA/DSC/DSD Requests."
			DEFVAL { 3 }
			::= { wmanIfCmnBsSsConfigurationEntry 3 }

		
		-- 1.3.6.1.2.1.10.184.1.3.2.2.1.4
		wmanIfCmnDSxRespRetries OBJECT-TYPE
			SYNTAX INTEGER
			MAX-ACCESS read-write
			STATUS current
			DESCRIPTION
				"Number of Timeout Retries on DSA/DSC/DSD Responses."
			DEFVAL { 3 }
			::= { wmanIfCmnBsSsConfigurationEntry 4 }

		
		-- 1.3.6.1.2.1.10.184.1.3.2.2.1.5
		wmanIfCmnT7Timeout OBJECT-TYPE
			SYNTAX INTEGER (0..1000)
			UNITS "milliseconds"
			MAX-ACCESS read-write
			STATUS current
			DESCRIPTION
				"Wait for DSA/DSC/DSD Response Timeout in ms."
			::= { wmanIfCmnBsSsConfigurationEntry 5 }

		
		-- 1.3.6.1.2.1.10.184.1.3.2.2.1.6
		wmanIfCmnT8Timeout OBJECT-TYPE
			SYNTAX INTEGER (0..300)
			UNITS "milliseconds"
			MAX-ACCESS read-write
			STATUS current
			DESCRIPTION
				"Wait for DSA/DSC/DSD Acknowledge Timeout in ms."
			::= { wmanIfCmnBsSsConfigurationEntry 6 }

		
		-- 1.3.6.1.2.1.10.184.1.3.2.2.1.7
		wmanIfCmnT10Timeout OBJECT-TYPE
			SYNTAX INTEGER (0..3000)
			UNITS "milliseconds"
			MAX-ACCESS read-write
			STATUS current
			DESCRIPTION
				"Wait for Transaction End timeout in ms."
			::= { wmanIfCmnBsSsConfigurationEntry 7 }

		
		-- 1.3.6.1.2.1.10.184.1.3.2.2.1.8
		wmanIfCmnT22Timeout OBJECT-TYPE
			SYNTAX INTEGER (0..500)
			UNITS "milliseconds"
			MAX-ACCESS read-write
			STATUS current
			DESCRIPTION
				"Wait for ARQ Reset in ms."
			::= { wmanIfCmnBsSsConfigurationEntry 8 }

		
--  wmanIfCmnSsStatCounter contain the performance statistics information
		-- 1.3.6.1.2.1.10.184.1.3.2.3
		wmanIfCmnSsStatCounter OBJECT IDENTIFIER ::= { wmanIfCmnCps 3 }

		
		-- 1.3.6.1.2.1.10.184.1.3.2.3.1
		wmanIfCmnSsChMeasurementTable OBJECT-TYPE
			SYNTAX SEQUENCE OF WmanIfCmnSsChMeasurementEntry
			MAX-ACCESS not-accessible
			STATUS current
			DESCRIPTION
				"This table contains channel measurement information
				for each SS. BS retrieves the channel measurement
				information from REP-REQ/RSP messages. This table contains
				channel measurement information on the downlink signal 
				sent to SS."
			::= { wmanIfCmnSsStatCounter 1 }

		
		-- 1.3.6.1.2.1.10.184.1.3.2.3.1.1
		wmanIfCmnSsChMeasurementEntry OBJECT-TYPE
			SYNTAX WmanIfCmnSsChMeasurementEntry
			MAX-ACCESS not-accessible
			STATUS current
			DESCRIPTION
				"Each entry in the table contains RSSI and CINR
				signal quality measurement taken from the SS. The primary
				index is teh ifIndex with ifType propBWAp2Mp identifing
				the BS sector. The primary index is the ifIndex with ifType
				of propBWAp2Mp identifing the BS sector. wmanIfCmnSsIdIndex
				identifies the SS where th emeasurement taking place.
				wmanIfCmnHistogramIndex is the index to histogram samples.
				Since there is no time stamp in the table,
				wmanIfCmnHistogramIndex should be increased monotonically,
				and warps around when it reaches the limit.
				be maintained as FIFO to store measurement samples that
				can be used to create RSSI and CINR histogram report.
				When the measurement entry for a SS reaches the limit,
				the oldest entry shall be deleted as the new entry is
				added to the table."
			INDEX { ifIndex, wmanIfCmnSsIdIndex, wmanIfCmnHistogramIndex }
			::= { wmanIfCmnSsChMeasurementTable 1 }

		
		WmanIfCmnSsChMeasurementEntry ::=
			SEQUENCE { 
				wmanIfCmnSsIdIndex
					Unsigned32,
				wmanIfCmnHistogramIndex
					Unsigned32,
				wmanIfCmnChannelNumber
					INTEGER,
				wmanIfCmnStartFrame
					INTEGER,
				wmanIfCmnDuration
					INTEGER,
				wmanIfCmnBasicReport
					BITS,
				wmanIfCmnMeanCinrReport
					INTEGER,
				wmanIfCmnStdDeviationCinrReport
					INTEGER,
				wmanIfCmnMeanRssiReport
					INTEGER,
				wmanIfCmnStdDeviationRssiReport
					INTEGER
			 }

		-- 1.3.6.1.2.1.10.184.1.3.2.3.1.1.1
		wmanIfCmnSsIdIndex OBJECT-TYPE
			SYNTAX Unsigned32 (1..4294967295)
			MAX-ACCESS not-accessible
			STATUS current
			DESCRIPTION
				"wmanIfCmnSsIdIndex identifies the SS providing the
				channel measurement."
			REFERENCE
				"Section 6.4.2.3.5 in IEEE 802.16REVd/D5-2004"
			::= { wmanIfCmnSsChMeasurementEntry 1 }

		
		-- 1.3.6.1.2.1.10.184.1.3.2.3.1.1.2
		wmanIfCmnHistogramIndex OBJECT-TYPE
			SYNTAX Unsigned32 (1..4294967295)
			MAX-ACCESS not-accessible
			STATUS current
			DESCRIPTION
				"wmanIfBsHistogramIndex identifies the histogram samples
				in the table for each subscriber station."
			::= { wmanIfCmnSsChMeasurementEntry 2 }

		
		-- 1.3.6.1.2.1.10.184.1.3.2.3.1.1.3
		wmanIfCmnChannelNumber OBJECT-TYPE
			SYNTAX INTEGER
			MAX-ACCESS read-only
			STATUS current
			DESCRIPTION
				"Physical channel number to be reported on."
			REFERENCE
				"Section 8.5.1 in IEEE 802.16REVd/D5-2004"
			::= { wmanIfCmnSsChMeasurementEntry 3 }

		
		-- 1.3.6.1.2.1.10.184.1.3.2.3.1.1.4
		wmanIfCmnStartFrame OBJECT-TYPE
			SYNTAX INTEGER
			MAX-ACCESS read-only
			STATUS current
			DESCRIPTION
				"Frame number in which measurement for this channel
				started."
			REFERENCE
				"Section 11.12 in IEEE 802.16REVd/D5-2004"
			::= { wmanIfCmnSsChMeasurementEntry 4 }

		
		-- 1.3.6.1.2.1.10.184.1.3.2.3.1.1.5
		wmanIfCmnDuration OBJECT-TYPE
			SYNTAX INTEGER
			MAX-ACCESS read-only
			STATUS current
			DESCRIPTION
				"Cumulative measurement duration on the channel in
				multiples of Ts. For any value exceeding 0xFFFFFF,
				report 0xFFFFFF."
			REFERENCE
				"Section 11.12 in IEEE 802.16REVd/D5-2004"
			::= { wmanIfCmnSsChMeasurementEntry 5 }

		
		-- 1.3.6.1.2.1.10.184.1.3.2.3.1.1.6
		wmanIfCmnBasicReport OBJECT-TYPE
			SYNTAX BITS
				{
				wirelessHuman(0),
				unknownTransmission(1),
				primaryUser(2),
				channegNotMeasured(3)
				}
			MAX-ACCESS read-only
			STATUS current
			DESCRIPTION
				"Bit #0: WirelessHUMAN detected on the channel
				Bit #1: Unknown transmissions detected on the channel
				Bit #2: Primary User detected on the channel
				Bit #3: Unmeasured. Channel not measured"
			REFERENCE
				"Section 11.12 in IEEE 802.16REVd/D5-2004"
			::= { wmanIfCmnSsChMeasurementEntry 6 }

		
		-- 1.3.6.1.2.1.10.184.1.3.2.3.1.1.7
		wmanIfCmnMeanCinrReport OBJECT-TYPE
			SYNTAX INTEGER
			MAX-ACCESS read-only
			STATUS current
			DESCRIPTION
				"Mean CINR report."
			REFERENCE
				"Section 8.2.2, 8.3.8, 8.4.1, 11.12 in IEEE
				802.16REVd/D5-2004"
			::= { wmanIfCmnSsChMeasurementEntry 7 }

		
		-- 1.3.6.1.2.1.10.184.1.3.2.3.1.1.8
		wmanIfCmnStdDeviationCinrReport OBJECT-TYPE
			SYNTAX INTEGER
			MAX-ACCESS read-only
			STATUS current
			DESCRIPTION
				"Standard deviation CINR report."
			REFERENCE
				"Section 8.2.2, 8.3.8, 8.4.1, 11.12 in IEEE
				802.16REVd/D5-2004"
			::= { wmanIfCmnSsChMeasurementEntry 8 }

		
		-- 1.3.6.1.2.1.10.184.1.3.2.3.1.1.9
		wmanIfCmnMeanRssiReport OBJECT-TYPE
			SYNTAX INTEGER
			MAX-ACCESS read-only
			STATUS current
			DESCRIPTION
				"Mean RSSI report."
			REFERENCE
				"Section 8.2.2, 8.3.8, 8.4.1, 11.12 in IEEE
				802.16REVd/D5-2004"
			::= { wmanIfCmnSsChMeasurementEntry 9 }

		
		-- 1.3.6.1.2.1.10.184.1.3.2.3.1.1.10
		wmanIfCmnStdDeviationRssiReport OBJECT-TYPE
			SYNTAX INTEGER
			MAX-ACCESS read-only
			STATUS current
			DESCRIPTION
				"Standard deviation RSSI report."
			REFERENCE
				"Section 8.2.2, 8.3.8, 8.4.1, 11.12 in IEEE
				802.16REVd/D5-2004"
			::= { wmanIfCmnSsChMeasurementEntry 10 }

		
		-- 1.3.6.1.2.1.10.184.1.3.2.3.2
		wmanIfCmnSsFecCounterTable OBJECT-TYPE
			SYNTAX SEQUENCE OF WmanIfCmnSsFecCounterEntry
			MAX-ACCESS not-accessible
			STATUS current
			DESCRIPTION
				"This table contains counters to capture corrected and
				uncorrected FEC errors detected on the downstream signal
				received from BS."
			REFERENCE
				"Section 8.4.9 in IEEE 802.16REVd/D5-2004"
			::= { wmanIfCmnSsStatCounter 2 }

		
		-- 1.3.6.1.2.1.10.184.1.3.2.3.2.1
		wmanIfCmnSsFecCounterEntry OBJECT-TYPE
			SYNTAX WmanIfCmnSsFecCounterEntry
			MAX-ACCESS not-accessible
			STATUS current
			DESCRIPTION
				"An entry will be created for each SS in the BS sector.
				The primary index is the ifIndex with ifType of propBWAp2Mp
				identifing the BS sector. wmanIfCmnFecSsId identifies
				the SS from which the signal was received."
			INDEX { ifIndex, wmanIfCmnSsFecSsId }
			::= { wmanIfCmnSsFecCounterTable 1 }

		
		WmanIfCmnSsFecCounterEntry ::=
			SEQUENCE { 
				wmanIfCmnSsFecSsId
					Unsigned32,
				wmanIfCmnSsFecCorrectedBytes
					Counter64,
				wmanIfCmnSsFecUncorrectedBytes
					Counter64,
				wmanIfCmnSsFecUncorrectedMacPdu
					Counter64,
				wmanIfCmnSsFecResetCounter
					INTEGER
			 }

		-- 1.3.6.1.2.1.10.184.1.3.2.3.2.1.1
		wmanIfCmnSsFecSsId OBJECT-TYPE
			SYNTAX Unsigned32 (1..4294967295)
			MAX-ACCESS not-accessible
			STATUS current
			DESCRIPTION
				"wmanIfCmnSsFecIdIndex identifies the SS providing the
				FEC statistics."
			REFERENCE
				"Section 6.4.2.3.5 in IEEE 802.16REVd/D5-2004"
			::= { wmanIfCmnSsFecCounterEntry 1 }

		
		-- 1.3.6.1.2.1.10.184.1.3.2.3.2.1.2
		wmanIfCmnSsFecCorrectedBytes OBJECT-TYPE
			SYNTAX Counter64
			UNITS "bytes"
			MAX-ACCESS read-only
			STATUS current
			DESCRIPTION
				"Indicates the aggregation of corrected FEC errors in
				terms of the number of bytes."
			::= { wmanIfCmnSsFecCounterEntry 2 }

		
		-- 1.3.6.1.2.1.10.184.1.3.2.3.2.1.3
		wmanIfCmnSsFecUncorrectedBytes OBJECT-TYPE
			SYNTAX Counter64
			UNITS "bytes"
			MAX-ACCESS read-only
			STATUS current
			DESCRIPTION
				"Indicates the aggregation of uncorrected FEC errors in
				terms of the number of bytes."
			::= { wmanIfCmnSsFecCounterEntry 3 }

		
		-- 1.3.6.1.2.1.10.184.1.3.2.3.2.1.4
		wmanIfCmnSsFecUncorrectedMacPdu OBJECT-TYPE
			SYNTAX Counter64
			UNITS "MAC PDU"
			MAX-ACCESS read-only
			STATUS current
			DESCRIPTION
				"Indicates the aggregation of uncorrected MAC PDUs."
			::= { wmanIfCmnSsFecCounterEntry 4 }

		
		-- 1.3.6.1.2.1.10.184.1.3.2.3.2.1.5
		wmanIfCmnSsFecResetCounter OBJECT-TYPE
			SYNTAX INTEGER
				{
				null(0),
				resetCounter(1)
				}
			MAX-ACCESS read-write
			STATUS current
			DESCRIPTION
				"When SET this attribute to resetCounter(1), the
				corresponding entry of FEC counters will be reset.
				A GET operation performed on this object will always
				return null(0). The counter is normally reset after
				the packet count information is retrieved. "
			::= { wmanIfCmnSsFecCounterEntry 5 }

		
--  Common PKM  group
-- wmanIfCmnPkmObjects contain the Privacy Sublayer objects that are
-- common to both Base Station and Subscriber Station
		-- 1.3.6.1.2.1.10.184.1.3.3
		wmanIfCmnPkmObjects OBJECT IDENTIFIER ::= { wmanIfCommonObjects 3 }

		
--  Table wmanIfCmnCryptoSuiteTable
-- 
		-- 1.3.6.1.2.1.10.184.1.3.3.1
		wmanIfCmnCryptoSuiteTable OBJECT-TYPE
			SYNTAX SEQUENCE OF WmanIfCmnCryptoSuiteEntry
			MAX-ACCESS not-accessible
			STATUS current
			DESCRIPTION
				"This table describes the PKM cryptographic suite
				capabilites for each SS or BS wireless interface."
			::= { wmanIfCmnPkmObjects 1 }

		
		-- 1.3.6.1.2.1.10.184.1.3.3.1.1
		wmanIfCmnCryptoSuiteEntry OBJECT-TYPE
			SYNTAX WmanIfCmnCryptoSuiteEntry
			MAX-ACCESS not-accessible
			STATUS current
			DESCRIPTION
				"Each entry contains the cryptographic suite pair that SS
				or BS supports."
			INDEX { ifIndex, wmanIfCmnCryptoSuiteIndex }
			::= { wmanIfCmnCryptoSuiteTable 1 }

		
		WmanIfCmnCryptoSuiteEntry ::=
			SEQUENCE { 
				wmanIfCmnCryptoSuiteIndex
					Integer32,
				wmanIfCmnCryptoSuiteDataEncryptAlg
					INTEGER,
				wmanIfCmnCryptoSuiteDataAuthentAlg
					INTEGER,
				wmanIfCmnCryptoSuiteTEKEncryptAlg
					INTEGER
			 }

		-- 1.3.6.1.2.1.10.184.1.3.3.1.1.1
		wmanIfCmnCryptoSuiteIndex OBJECT-TYPE
			SYNTAX Integer32 (1..1000)
			MAX-ACCESS not-accessible
			STATUS current
			DESCRIPTION
				"The index for a cryptographic suite row."
			::= { wmanIfCmnCryptoSuiteEntry 1 }

		
		-- 1.3.6.1.2.1.10.184.1.3.3.1.1.2
		wmanIfCmnCryptoSuiteDataEncryptAlg OBJECT-TYPE
			SYNTAX INTEGER
				{
				none(0),
				des56CbcMode(1),
				aesCcmMode(2)
				}
			MAX-ACCESS read-only
			STATUS current
			DESCRIPTION
				"The value of this object is the data encryption algorithm
				for this cryptographic suite capability."
			REFERENCE
				"IEEE 802.16 standard; Table 373"
			::= { wmanIfCmnCryptoSuiteEntry 2 }

		
		-- 1.3.6.1.2.1.10.184.1.3.3.1.1.3
		wmanIfCmnCryptoSuiteDataAuthentAlg OBJECT-TYPE
			SYNTAX INTEGER { none(0) }
			MAX-ACCESS read-only
			STATUS current
			DESCRIPTION
				"The value of this object is the data authentication
				algorithm for this cryptographic suite capability."
			REFERENCE
				"IEEE 802.16 standard; Table 302"
			::= { wmanIfCmnCryptoSuiteEntry 3 }

		
		-- 1.3.6.1.2.1.10.184.1.3.3.1.1.4
		wmanIfCmnCryptoSuiteTEKEncryptAlg OBJECT-TYPE
			SYNTAX INTEGER
				{
				tripleDES128Key(1),
				rsa1024Key(2),
				aes128Key(3)
				}
			MAX-ACCESS read-only
			STATUS current
			DESCRIPTION
				"The value of this object is the TEK key encryption
				algorithm for this cryptographic suite capability."
			REFERENCE
				"IEEE 802.16 standard; Table 375"
			::= { wmanIfCmnCryptoSuiteEntry 4 }

		
--  wmanIfCmnOfdmPhy contain the OFDM PHY objects that are common to both
-- Base Station and Subscriber Station. When the objects are implemented
-- in the BS, they should have the readwrite access. When the objects
-- are implemented the SS, they should have the readonly access.
--   
		-- 1.3.6.1.2.1.10.184.1.3.4
		wmanIfCmnOfdmPhy OBJECT IDENTIFIER ::= { wmanIfCommonObjects 4 }

		
		-- 1.3.6.1.2.1.10.184.1.3.4.1
		wmanIfCmnOfdmUplinkChannelTable OBJECT-TYPE
			SYNTAX SEQUENCE OF WmanIfCmnOfdmUplinkChannelEntry
			MAX-ACCESS not-accessible
			STATUS current
			DESCRIPTION
				"This table contains UCD channel attributes, defining the
				transmission characteristics of uplink channels"
			REFERENCE
				"Section 11.3.1, table 276 and 279, in IEEE
				802.16REVd/D5-2004"
			::= { wmanIfCmnOfdmPhy 1 }

		
		-- 1.3.6.1.2.1.10.184.1.3.4.1.1
		wmanIfCmnOfdmUplinkChannelEntry OBJECT-TYPE
			SYNTAX WmanIfCmnOfdmUplinkChannelEntry
			MAX-ACCESS not-accessible
			STATUS current
			DESCRIPTION
				"This table provides one row for each uplink channel of
				multi-sector BS, and is indexed by BS ifIndex. An entry
				in this table exists for each ifEntry of BS with an
				ifType of propBWAp2Mp.
				The objects in each entry will be implemented as
				read-create in BS and read-only in SS."
			INDEX { ifIndex }
			::= { wmanIfCmnOfdmUplinkChannelTable 1 }

		
		WmanIfCmnOfdmUplinkChannelEntry ::=
			SEQUENCE { 
				wmanIfCmnOfdmCtBasedResvTimeout
					INTEGER,
				wmanIfCmnOfdmBwReqOppSize
					INTEGER,
				wmanIfCmnOfdmRangReqOppSize
					INTEGER,
				wmanIfCmnOfdmUplinkCenterFreq
					INTEGER,
				wmanIfCmnOfdmSubChReqRegionFull
					INTEGER,
				wmanIfCmnOfdmSubChFocusCtCode
					INTEGER
			 }

		-- 1.3.6.1.2.1.10.184.1.3.4.1.1.1
		wmanIfCmnOfdmCtBasedResvTimeout OBJECT-TYPE
			SYNTAX INTEGER (1..255)
			MAX-ACCESS read-write
			STATUS current
			DESCRIPTION
				"The number of UL-MAPs to receive before contention-based
				reservation is attempted again for the same connection."
			REFERENCE
				"Section 11.3.1, table 276, in IEEE 802.16REVd/D5-2004"
			::= { wmanIfCmnOfdmUplinkChannelEntry 1 }

		
		-- 1.3.6.1.2.1.10.184.1.3.4.1.1.2
		wmanIfCmnOfdmBwReqOppSize OBJECT-TYPE
			SYNTAX INTEGER (1..65535)
			UNITS "PS"
			MAX-ACCESS read-write
			STATUS current
			DESCRIPTION
				" Size (in units of PS) of PHY payload that SS may use to
				format and transmit a bandwidth request message in a
				contention request opportunity. The value includes all
				PHY overhead as well as allowance for the MAC data the
				message may hold."
			REFERENCE
				"Section 11.3.1, table 276, in IEEE 802.16REVd/D5-2004"
			::= { wmanIfCmnOfdmUplinkChannelEntry 2 }

		
		-- 1.3.6.1.2.1.10.184.1.3.4.1.1.3
		wmanIfCmnOfdmRangReqOppSize OBJECT-TYPE
			SYNTAX INTEGER (1..65535)
			UNITS "PS"
			MAX-ACCESS read-write
			STATUS current
			DESCRIPTION
				" Size (in units of PS) of PHY payload that SS may use to
				format and transmit a RNG-REQ message in a contention
				request opportunity. The value includes all PHY overhead
				as well as allowance for the MAC data the message may
				hold and the maxiumum SS/BS roundtrip propagation delay."
			REFERENCE
				"Section 11.3.1, table 276, in IEEE 802.16REVd/D5-2004"
			::= { wmanIfCmnOfdmUplinkChannelEntry 3 }

		
		-- 1.3.6.1.2.1.10.184.1.3.4.1.1.4
		wmanIfCmnOfdmUplinkCenterFreq OBJECT-TYPE
			SYNTAX INTEGER
			UNITS "KHz"
			MAX-ACCESS read-write
			STATUS current
			DESCRIPTION
				" Uplink center frequency (KHz)"
			REFERENCE
				"Section 11.3.1, table 276, in IEEE 802.16REVd/D5-2004"
			::= { wmanIfCmnOfdmUplinkChannelEntry 4 }

		
		-- 1.3.6.1.2.1.10.184.1.3.4.1.1.5
		wmanIfCmnOfdmSubChReqRegionFull OBJECT-TYPE
			SYNTAX INTEGER (0..255)
			MAX-ACCESS read-write
			STATUS current
			DESCRIPTION
				"Airspan implementation work around: Broken definition in this draft. 
				To alow operation with the type checking MIB browser/agent 
				need to be define as an INTEGER (0..255) with binary encoding given 
				define only in the description.
				--------
				Bits 0 - 2 Number of subchannels used by each transmit
				opportunity when REQ Region-Full is allocated in
				subchannelization region, per the following enumeration:
				   0: 1 Subchannel.
				   1: 2 Subchannels.
				   2: 4 Subchannels.
				   3: 8 Subchannels.
				   4: 16 Subchannels.
				   5-7: Shall not be used.
				Bits 3 - 7: Number of OFDM symbols used by each transmit
				opportunity when REQ Region-Full is allocated in
				subchannelization region.
				"
			REFERENCE
				"Section 11.3.1, table 279, in IEEE 802.16REVd/D5-2004"
			::= { wmanIfCmnOfdmUplinkChannelEntry 5 }

		
		-- 1.3.6.1.2.1.10.184.1.3.4.1.1.6
		wmanIfCmnOfdmSubChFocusCtCode OBJECT-TYPE
			SYNTAX INTEGER (0..8)
			MAX-ACCESS read-write
			STATUS current
			DESCRIPTION
				"Number of contention codes (CSE) that shall only be used to
				request a subchannelized allocation. Default value 0.
				Allowed values 0-8."
			REFERENCE
				"Section 11.3.1, table 279, in IEEE 802.16REVd/D5-2004"
			DEFVAL { 0 }
			::= { wmanIfCmnOfdmUplinkChannelEntry 6 }

		
		-- 1.3.6.1.2.1.10.184.1.3.4.2
		wmanIfCmnOfdmDownlinkChannelTable OBJECT-TYPE
			SYNTAX SEQUENCE OF WmanIfCmnOfdmDownlinkChannelEntry
			MAX-ACCESS not-accessible
			STATUS current
			DESCRIPTION
				"This table contains DCD channel attributes, defining the
				transmission characteristics of downlink channels"
			REFERENCE
				"Section 11.4.1, Table 286, in IEEE 802.16REVd/D5-2004"
			::= { wmanIfCmnOfdmPhy 2 }

		
		-- 1.3.6.1.2.1.10.184.1.3.4.2.1
		wmanIfCmnOfdmDownlinkChannelEntry OBJECT-TYPE
			SYNTAX WmanIfCmnOfdmDownlinkChannelEntry
			MAX-ACCESS not-accessible
			STATUS current
			DESCRIPTION
				"This table provides one row for each downlink channel of
				multi-sector BS, and is indexed by BS ifIndex. An entry
				in this table exists for each ifEntry of BS with an
				ifType of propBWAp2Mp.
				The objects in each entry will be implemented as
				read-create in BS and read-only in SS."
			INDEX { ifIndex }
			::= { wmanIfCmnOfdmDownlinkChannelTable 1 }

		
		WmanIfCmnOfdmDownlinkChannelEntry ::=
			SEQUENCE { 
				wmanIfCmnOfdmBsEIRP
					INTEGER,
				wmanIfCmnOfdmChannelNumber
					INTEGER,
				wmanIfCmnOfdmTTG
					INTEGER,
				wmanIfCmnOfdmRTG
					INTEGER,
				wmanIfCmnOfdmInitRngMaxRSS
					INTEGER,
				wmanIfCmnOfdmChSwitchFrameNmr
					INTEGER,
				wmanIfCmnOfdmDownlinkCenterFreq
					INTEGER,
				wmanIfCmnOfdmBsId
					OCTET STRING,
				wmanIfCmnOfdmMacVersion
					INTEGER,
				wmanIfCmnOfdmFrameDurationCode
					INTEGER,
				wmanIfCmnOfdmFrameNumber
					INTEGER
			 }

		-- 1.3.6.1.2.1.10.184.1.3.4.2.1.1
		wmanIfCmnOfdmBsEIRP OBJECT-TYPE
			SYNTAX INTEGER (-32768..32767)
			UNITS "dbM"
			MAX-ACCESS read-write
			STATUS current
			DESCRIPTION
				" Signed in units of 1 dBM."
			REFERENCE
				"Section 11.4.1, table 286, in IEEE 802.16REVd/D5-2004"
			::= { wmanIfCmnOfdmDownlinkChannelEntry 1 }

		
		-- 1.3.6.1.2.1.10.184.1.3.4.2.1.2
		wmanIfCmnOfdmChannelNumber OBJECT-TYPE
			SYNTAX INTEGER (1..255)
			MAX-ACCESS read-write
			STATUS current
			DESCRIPTION
				" Downlink channel number as defined in 8.5.
				Used for license-exempt operation only."
			REFERENCE
				"Section 11.4.1, table 286, in IEEE 802.16REVd/D5-2004"
			::= { wmanIfCmnOfdmDownlinkChannelEntry 2 }

		
		-- 1.3.6.1.2.1.10.184.1.3.4.2.1.3
		wmanIfCmnOfdmTTG OBJECT-TYPE
			SYNTAX INTEGER (0..65535)
			MAX-ACCESS read-write
			STATUS current
			DESCRIPTION
				" Transmit / Receive Transition Gap."
			REFERENCE
				"Section 11.4.1, table 286, in IEEE 802.16REVd/D5-2004"
			::= { wmanIfCmnOfdmDownlinkChannelEntry 3 }

		
		-- 1.3.6.1.2.1.10.184.1.3.4.2.1.4
		wmanIfCmnOfdmRTG OBJECT-TYPE
			SYNTAX INTEGER (0..255)
			MAX-ACCESS read-write
			STATUS current
			DESCRIPTION
				" Receive / Transmit Transition Gap."
			REFERENCE
				"Section 11.4.1, table 286, in IEEE 802.16REVd/D5-2004"
			::= { wmanIfCmnOfdmDownlinkChannelEntry 4 }

		
		-- 1.3.6.1.2.1.10.184.1.3.4.2.1.5
		wmanIfCmnOfdmInitRngMaxRSS OBJECT-TYPE
			SYNTAX INTEGER (-32768..32767)
			UNITS "dbM"
			MAX-ACCESS read-write
			STATUS current
			DESCRIPTION
				" Initial Ranging Max. Received Signal Strength at BS
				Signed in units of 1 dBm."
			REFERENCE
				"Section 11.4.1, table 286, in IEEE 802.16REVd/D5-2004"
			::= { wmanIfCmnOfdmDownlinkChannelEntry 5 }

		
		-- 1.3.6.1.2.1.10.184.1.3.4.2.1.6
		wmanIfCmnOfdmChSwitchFrameNmr OBJECT-TYPE
			SYNTAX INTEGER (0..16777215)
			MAX-ACCESS read-write
			STATUS current
			DESCRIPTION
				" Channel switch frame number as defined in 6.4.14.7,
				Used for license-exempt operation only."
			REFERENCE
				"Section 11.4.1, table 286, in IEEE 802.16REVd/D5-2004"
			::= { wmanIfCmnOfdmDownlinkChannelEntry 6 }

		
		-- 1.3.6.1.2.1.10.184.1.3.4.2.1.7
		wmanIfCmnOfdmDownlinkCenterFreq OBJECT-TYPE
			SYNTAX INTEGER
			UNITS "KHz"
			MAX-ACCESS read-write
			STATUS current
			DESCRIPTION
				" Downlink center frequency (kHz)."
			REFERENCE
				"Section 11.4.1, table 286, in IEEE 802.16REVd/D5-2004"
			::= { wmanIfCmnOfdmDownlinkChannelEntry 7 }

		
		-- 1.3.6.1.2.1.10.184.1.3.4.2.1.8
		wmanIfCmnOfdmBsId OBJECT-TYPE
			SYNTAX OCTET STRING (SIZE (6))
			MAX-ACCESS read-write
			STATUS current
			DESCRIPTION
				" Base station ID."
			REFERENCE
				"Section 11.4.1, table 286, in IEEE 802.16REVd/D5-2004"
			::= { wmanIfCmnOfdmDownlinkChannelEntry 8 }

		
		-- 1.3.6.1.2.1.10.184.1.3.4.2.1.9
		wmanIfCmnOfdmMacVersion OBJECT-TYPE
			SYNTAX INTEGER
				{
				ieee802Dot16-2001(1),
				ieee802Dot16c-2002(2),
				ieee802Dot16a-2003(3),
				ieee802Dot16-2004(4),
				ieee802Dot16-2004Cor1(5)
				}
			MAX-ACCESS read-write
			STATUS current
			DESCRIPTION
				" This parameter specifies the version of 802.16 to which
				the message originator conforms."
			REFERENCE
				"Section 11.4.1, table 286, in IEEE 802.16REVd/D5-2004"
			::= { wmanIfCmnOfdmDownlinkChannelEntry 9 }

		
		-- 1.3.6.1.2.1.10.184.1.3.4.2.1.10
		wmanIfCmnOfdmFrameDurationCode OBJECT-TYPE
			SYNTAX INTEGER
				{
				duration2dot5ms(0),
				duration4ms(1),
				duration5ms(2),
				duration8ms(3),
				duration10ms(4),
				duration12dot5ms(5),
				duration20ms(6)
				}
			MAX-ACCESS read-write
			STATUS current
			DESCRIPTION
				" The duration of the frame. The frame duration code
				values are specified in Table 230."
			REFERENCE
				"Section 11.4.1, table 230, in IEEE 802.16/2004"
			::= { wmanIfCmnOfdmDownlinkChannelEntry 10 }

		
		-- 1.3.6.1.2.1.10.184.1.3.4.2.1.11
		wmanIfCmnOfdmFrameNumber OBJECT-TYPE
			SYNTAX INTEGER (0..16777215)
			MAX-ACCESS read-write
			STATUS current
			DESCRIPTION
				" The number of frame containing the DCD message."
			REFERENCE
				"Section 11.4.1, table 286, in IEEE 802.16REVd/D5-2004"
			::= { wmanIfCmnOfdmDownlinkChannelEntry 11 }

		
		-- 1.3.6.1.2.1.10.184.1.3.4.3
		wmanIfCmnOfdmUcdBurstProfileTable OBJECT-TYPE
			SYNTAX SEQUENCE OF WmanIfCmnOfdmUcdBurstProfileEntry
			MAX-ACCESS not-accessible
			STATUS current
			DESCRIPTION
				"This table contains UCD burst profiles for each uplink
				channel"
			REFERENCE
				"Section 11.3.1.1, table 281 and 284, in IEEE
				802.16REVd/D5-2004"
			::= { wmanIfCmnOfdmPhy 3 }

		
		-- 1.3.6.1.2.1.10.184.1.3.4.3.1
		wmanIfCmnOfdmUcdBurstProfileEntry OBJECT-TYPE
			SYNTAX WmanIfCmnOfdmUcdBurstProfileEntry
			MAX-ACCESS not-accessible
			STATUS current
			DESCRIPTION
				"This table provides one row for each UCD burst profile.
				This table is double indexed. The primary index is an
				ifIndex with an ifType of propBWAp2Mp. The secondary index
				is wmanIfCmnOfdmOfdmUcdBurstProfIndex.
				The objects in each entry will be implemented as
				read-create in BS and read-only in SS."
			INDEX { ifIndex, wmanIfCmnOfdmUiucIndex }
			::= { wmanIfCmnOfdmUcdBurstProfileTable 1 }

		
		WmanIfCmnOfdmUcdBurstProfileEntry ::=
			SEQUENCE { 
				wmanIfCmnOfdmUiucIndex
					INTEGER,
				wmanIfCmnOfdmUplinkFrequency
					INTEGER,
				wmanIfCmnOfdmUcdFecCodeType
					WmanIfOfdmFecCodeType,
				wmanIfCmnOfdmFocusCtPowerBoost
					INTEGER,
				wmanIfCmnOfdmUcdBurstProfileRowStatus
					RowStatus
			 }

		-- 1.3.6.1.2.1.10.184.1.3.4.3.1.1
		wmanIfCmnOfdmUiucIndex OBJECT-TYPE
			SYNTAX INTEGER (5..12)
			MAX-ACCESS not-accessible
			STATUS current
			DESCRIPTION
				"The Uplink Interval Usage Code indiates the uplink burst
				profile in the UCD message, and is used along with ifIndex
				to identify an entry in the
				wmanIfCmnOfdmUcdBurstProfileTable."
			REFERENCE
				"Section 8.3.6.3.1, in IEEE 802.16/2004"
			::= { wmanIfCmnOfdmUcdBurstProfileEntry 1 }

		
		-- 1.3.6.1.2.1.10.184.1.3.4.3.1.2
		wmanIfCmnOfdmUplinkFrequency OBJECT-TYPE
			SYNTAX INTEGER
			UNITS "KHz"
			MAX-ACCESS read-create
			STATUS current
			DESCRIPTION
				"Uplink Frequency (kHz)."
			REFERENCE
				"Section 11.3.1.1, table 281, in IEEE 802.16REVd/D5-2004"
			::= { wmanIfCmnOfdmUcdBurstProfileEntry 2 }

		
		-- 1.3.6.1.2.1.10.184.1.3.4.3.1.3
		wmanIfCmnOfdmUcdFecCodeType OBJECT-TYPE
			SYNTAX WmanIfOfdmFecCodeType
			MAX-ACCESS read-create
			STATUS current
			DESCRIPTION
				"Defines uplink FEC code as per textual convention WmanIfOfdmFecCodeType."
			REFERENCE
				"Section 11.3.1.1, table 284, in IEEE 802.16REVd/D5-2004"
			::= { wmanIfCmnOfdmUcdBurstProfileEntry 3 }

		
		-- 1.3.6.1.2.1.10.184.1.3.4.3.1.4
		wmanIfCmnOfdmFocusCtPowerBoost OBJECT-TYPE
			SYNTAX INTEGER
			MAX-ACCESS read-create
			STATUS current
			DESCRIPTION
				"The power boost in dB of focused contention carriers, as
				described in 8.3.6.3.3."
			REFERENCE
				"Section 11.3.1.1, table 284, in IEEE 802.16REVd/D5-2004"
			::= { wmanIfCmnOfdmUcdBurstProfileEntry 4 }

		
		-- 1.3.6.1.2.1.10.184.1.3.4.3.1.5
		wmanIfCmnOfdmUcdBurstProfileRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { wmanIfCmnOfdmUcdBurstProfileEntry 5 }

		
		-- 1.3.6.1.2.1.10.184.1.3.4.4
		wmanIfCmnOfdmDcdBurstProfileTable OBJECT-TYPE
			SYNTAX SEQUENCE OF WmanIfCmnOfdmDcdBurstProfileEntry
			MAX-ACCESS not-accessible
			STATUS current
			DESCRIPTION
				"This table provides one row for each DCD burst profile.
				This table is double indexed. The primary index is an
				ifIndex with an ifType of propBWAp2Mp. The secondary
				index is wmanIfCmnOfdmDiucIndex."
			::= { wmanIfCmnOfdmPhy 4 }

		
		-- 1.3.6.1.2.1.10.184.1.3.4.4.1
		wmanIfCmnOfdmDcdBurstProfileEntry OBJECT-TYPE
			SYNTAX WmanIfCmnOfdmDcdBurstProfileEntry
			MAX-ACCESS not-accessible
			STATUS current
			DESCRIPTION
				"This table provides one row for each DCD burst profile.
				This table is double indexed. The primary index is an
				ifIndex with an ifType of propBWAp2Mp. The secondary index
				is wmanIfCmnOfdmDcdBurstProfIndex.
				The objects in each entry will be implemented as
				read-create in BS and read-only in SS."
			INDEX { ifIndex, wmanIfCmnOfdmDiucIndex }
			::= { wmanIfCmnOfdmDcdBurstProfileTable 1 }

		
		WmanIfCmnOfdmDcdBurstProfileEntry ::=
			SEQUENCE { 
				wmanIfCmnOfdmDiucIndex
					INTEGER,
				wmanIfCmnOfdmDownlinkFrequency
					INTEGER,
				wmanIfCmnOfdmDcdFecCodeType
					WmanIfOfdmFecCodeType,
				wmanIfCmnOfdmDiucMandatoryExitThresh
					INTEGER,
				wmanIfCmnOfdmDiucMinEntryThresh
					INTEGER,
				wmanIfCmnOfdmTcsEnable
					INTEGER,
				wmanIfCmnOfdmDcdBurstProfileRowStatus
					RowStatus
			 }

		-- 1.3.6.1.2.1.10.184.1.3.4.4.1.1
		wmanIfCmnOfdmDiucIndex OBJECT-TYPE
			SYNTAX INTEGER (1..11)
			MAX-ACCESS not-accessible
			STATUS current
			DESCRIPTION
				"The Downlink Interval Usage Code indiates the downlink
				burst profile in the UCD message, and is used along with
				ifIndex to identify an entry in the
				wmanIfCmnOfdmDcdBurstProfileTable."
			REFERENCE
				"Section 8.3.6.3.1, in IEEE 802.16/2004"
			::= { wmanIfCmnOfdmDcdBurstProfileEntry 1 }

		
		-- 1.3.6.1.2.1.10.184.1.3.4.4.1.2
		wmanIfCmnOfdmDownlinkFrequency OBJECT-TYPE
			SYNTAX INTEGER
			UNITS "KHz"
			MAX-ACCESS read-create
			STATUS current
			DESCRIPTION
				"Downlink Frequency (kHz)."
			REFERENCE
				"Section 11.4.1, table 287, in IEEE 802.16REVd/D5-2004"
			::= { wmanIfCmnOfdmDcdBurstProfileEntry 2 }

		
		-- 1.3.6.1.2.1.10.184.1.3.4.4.1.3
		wmanIfCmnOfdmDcdFecCodeType OBJECT-TYPE
			SYNTAX WmanIfOfdmFecCodeType
			MAX-ACCESS read-create
			STATUS current
			DESCRIPTION
				"Defines downlink FEC code as per textual convention WmanIfOfdmFecCodeType."
			REFERENCE
				"Section 11.4.1, table 290, in IEEE 802.16REVd/D5-2004"
			::= { wmanIfCmnOfdmDcdBurstProfileEntry 3 }

		
		-- 1.3.6.1.2.1.10.184.1.3.4.4.1.4
		wmanIfCmnOfdmDiucMandatoryExitThresh OBJECT-TYPE
			SYNTAX INTEGER (0..255)
			MAX-ACCESS read-create
			STATUS current
			DESCRIPTION
				"DIUC mandatory exit threshold: 0 - 63.75 dB CINR at or
				below where this DIUC can no longer be used and where this
				change to a more robust DIUC is required, in 0.25 dB units."
			REFERENCE
				"Section 11.4.1, table 290, in IEEE 802.16REVd/D5-2004"
			::= { wmanIfCmnOfdmDcdBurstProfileEntry 4 }

		
		-- 1.3.6.1.2.1.10.184.1.3.4.4.1.5
		wmanIfCmnOfdmDiucMinEntryThresh OBJECT-TYPE
			SYNTAX INTEGER (0..255)
			MAX-ACCESS read-create
			STATUS current
			DESCRIPTION
				"DIUC minimum entry threshold: 0 - 63.75 dB The minimum CINR
				required to start using this DIUC when changing from a more
				robust DIUC is required, in 0.25 dB units."
			REFERENCE
				"Section 11.4.1, table 290, in IEEE 802.16REVd/D5-2004"
			::= { wmanIfCmnOfdmDcdBurstProfileEntry 5 }

		
		-- 1.3.6.1.2.1.10.184.1.3.4.4.1.6
		wmanIfCmnOfdmTcsEnable OBJECT-TYPE
			SYNTAX INTEGER
				{
				tcsDisabled(0),
				tcsEnabled(1)
				}
			MAX-ACCESS read-create
			STATUS current
			DESCRIPTION
				"Indicates whether Transmission COnvergence Sublayer
				is enabled or disabled."
			REFERENCE
				"Section 11.4.1, table 360, in IEEE 802.16/2004"
			::= { wmanIfCmnOfdmDcdBurstProfileEntry 6 }

		
		-- 1.3.6.1.2.1.10.184.1.3.4.4.1.7
		wmanIfCmnOfdmDcdBurstProfileRowStatus OBJECT-TYPE
			SYNTAX RowStatus
			MAX-ACCESS read-create
			STATUS current
			DESCRIPTION
				"This object is used to create a new row or modify or
				delete an existing row in this table.
				
				If the implementator of this MIB has choosen not
				to implement 'dynamic assignment' of profiles, this
				object is not useful and should return noSuchName
				upon SNMP request."
			::= { wmanIfCmnOfdmDcdBurstProfileEntry 7 }

		
	
	END

--
-- WMAN-IF-MIB-9-21_AirspanImplementation.mib
--
