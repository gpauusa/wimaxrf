--
-- AIRSPAN-BS-SOC-MIB.mib
-- MIB generated by MG-SOFT Visual MIB Builder Version 7.0  Build 240
-- Tuesday, July 27, 2010 at 13:59:09
--

	AIRSPAN-BS-SOC-MIB DEFINITIONS ::= BEGIN
 
		IMPORTS
			AsmaxBandwidthCode			
				FROM AIRSPAN-ASMAX-BS-COMMON-MIB			
			AsmaxBooleanSwitch			
				FROM AIRSPAN-ASMAX-COMMON-MIB			
			asMaxBS			
				FROM AIRSPAN-PRODUCTS-MIB			
			asDot1qVlanProvId, AsDot1qVlanIdOrNone			
				FROM AIRSPAN-Q-BRIDGE-MIB			
			ifIndex			
				FROM IF-MIB			
			InetAddressType, InetAddress			
				FROM INET-ADDRESS-MIB			
			OBJECT-GROUP, MODULE-COMPLIANCE, NOTIFICATION-GROUP			
				FROM SNMPv2-CONF			
			Integer32, OBJECT-TYPE, MODULE-IDENTITY, NOTIFICATION-TYPE			
				FROM SNMPv2-SMI			
			MacAddress, RowStatus, DisplayString, TEXTUAL-CONVENTION			
				FROM SNMPv2-TC			
			wmanIfBsSfId, wmanIfBsQoSProfileIndex, wmanIfBsClassifierRuleIndex, wmanIfBsSsMacAddress, WmanIfChannelNumber, 
			WmanIfBsIdType			
				FROM WMAN-IF-MIB;
	
	
		-- 1.3.6.1.4.1.989.1.16.2.5
		asMaxBSSoc MODULE-IDENTITY 
			LAST-UPDATED "201007261100Z"		-- July 26, 2010 at 11:00 GMT
			ORGANIZATION 
				"Airspan Communications Ltd"
			CONTACT-INFO 
				"Contact-info."
			DESCRIPTION 
				"Private MIB module for MicroMAX-SOC base station.
				---------------------
				Old revision history:
				September 30, 2008 at 07:00 GMT
				Draft 23:
				- Added DHCP Option 82 Agent Remote ID:
				  asMaxBsSocConfAltRemoteIdEnabled,
				  asMaxBsSocConfCircuitID,
				  asMaxBsSocSsCfgRemoteId
				April 24, 2008 at 17:58 GMT
				Draft 22:
				- Added Single User objects asMaxBsSocVlanCfgSingleUserEnabled
				- Added dynamic contention slots configuration:
				  asMaxBsSocConfDynamicConEnable, 
				  asMaxBsSocConfDynamicConLowCollisionRate,
				  asMaxBsSocConfDynamicConHighCollisionRate,
				  asMaxBsSocConfDynamicConSampleRate
				November 27, 2007 at 14:44 GMT
				Draft 21:
				- changed the value range of asMaxBsSocCccMaxPowerThreshold to -90 to -75, from -85 to -50
				October 30, 2007 at 11:07 GMT
				Draft 20:
				- Introduced an Obsolete group 
				- Marked asMaxBsSocConfSsMinSubchanWidth as Obsolete
				- Marked asMaxBsSocSsCfgSubChannelMinWidth as Obsolete
				October 02, 2007 at 11:51 GMT
				Draft 19:
				- Removed asMaxBsSocSchedulerFlowsAboveCir
				- Removed asMaxBsSocSchedulerFlowsBelowCir
				- Added asMaxBsSocSchedulingPolicy
				- Added asMaxBsSocPriority0Weighting
				- Added asMaxBsSocPriority1Weighting
				- Added asMaxBsSocPriority2Weighting
				- Added asMaxBsSocPriority3Weighting
				- Added asMaxBsSocPriority4Weighting
				- Added asMaxBsSocPriority5Weighting
				- Added asMaxBsSocPriority6Weighting
				- Added asMaxBsSocPriority7Weighting
				September 05, 2007 at 09:30 GMT
				Draft 18:
				- Added Mac Forced Forwarding objects asMaxBsSocVlanCfgMacFFXxx
				- Added asMaxBsSocCccMaxPowerThreshold
				- Added asMaxBsSocSsCfgSubChannelMinWidth
				August 30, 2007 at 15:23 GMT
				Draft 17:
				- Added asMaxBsSocCccEnabled
				- Added asMaxBsSocConfReuseGroup
				- Added asMaxBsSocSchedulerFlowsAboveMinReservedRate
				- Added asMaxBsSocSchedulerFlowsBelowMinReservedRate
				July 19, 2007 at 16:25 GMT
				Draft 16
				- added asMaxBsSocSsCfgBsidConfigEnabled
				June 20, 2007 at 16:00 GMT
				Draft 15
				- fixed default for asMaxBsSocConfBcastOfdmRateId
				June 12, 2007 at 17:45 GMT
				Draft 14
				- added asMaxBsSocConfBcastOfdmRateId
				May 18, 2007 at 11:00 GMT
				Draft 13
				- Table asMaxBsSocDfsCfgTable rewritten entirely
				- Events added to enumeration asMaxBsSocTrapStatusDfsEventType
				- Added asMaxBsSocConfUlMidambles
				April 19, 2007 at 10:42 GMT
				Draft 12:
				- Corrected syntax of default for asMaxBsSocConfDataEncryptModeMap
				April 17, 2007 at 16:00 GMT
				Draft 11
				- Removed MAC forced forwarding objects
				- Changed default for asMaxBsSocConfSsMinSubchanWidth and asMaxBsSocConfDataEncryptModeMap
				April 11, 2007 at 18:00 GMT
				Draft 10
				- added asMaxBsSocConfSsMinSubchanWidth
				- added default to asMaxBsSocSsHwRevision
				- changed type to string for asMaxBsSocSsSwVersion
				- changed defaults for asMaxBsSocSsCfgDlBurstXxx objects
				- changed table asMaxBsSocSsTrapStatusTable to read-only
				- added SS HW version to SsStatusChandedTrap
				April 04, 2007 at 14:00 GMT
				Draft 9
				Addition of new objects for SR6.0.
				- new objects in asMaxBsSocSsStatusTable
				  reporting HW rev, SW ver, IP and MAC adddresses of SS, WiFiAP and EasyVoice
				- new table asMaxBsSocSsCfgTable with configuration objects for
				  dl burst adaptive modulation properties, BSID, LAN table size
				- new traps asMaxBsSocSsStatusChangedTrap, asMaxBsSocSsEventTrap
				- new table asMaxBsSocClassifierRuleExtTable with configuration of
				  classifier VLANs and discarding rule action
				- new table asMaxBsSocVlanCfgExtTable
				- new table asMaxBsSocDfsCfgTable
				- new trap asMaxBsSocDfsEventTrap with associated objects
				January 24, 2007 at 16:12 GMT
				Draft 8
				 - Fixed indexing of asMaxBsSocSvcClassExtTable
				January 11, 2007 at 18:25 GMT
				Draft 7
				 - added asMaxBsSocSvcClassExtTable
				December 11, 2006 at 10:28 GMT
				Draft 6
				  - cleanup of imported objects
				December 05, 2006 at 20:51 GMT
				Draft 5
				- removed asMaxBsSocSvcClassExtTable
				- removed asMaxBsSocConfDfsEnabled
				- removed asMaxBsSocDfsFrequencyChangeTrap
				- corrected OID for asMaxBsSocTrapPrefix
				November 29, 2006 at 09:50 GMT
				Draft 4
				- added asMaxBsSocSvcClassExtTable with poll period config
				October 27, 2006 at 18:22 GMT
				Draft 3
				-added asMaxBsSocConfBcastScXxx objects
				-removed cryptographic suites and key encryption config objects
				-added asMaxBsSocSchedulerConfigTable table
				-added asMaxBsSocRfConfTxEnabled object 
				-added asMaxBsSocRfStatOldDnlkFrequencyInd
				October 20, 2006 at 13:15 GMT
				Draft 2
				- Added objects for DFS:
				  asMaxBsSocConfDfsEnabled, asMaxBsSocRfStatDownlinkFrequencyInd, asMaxBsSocDfsFrequencyChangeTrap
				- Added support for GPS synchronisation mode:
				  asMaxBsSocConfGpsOperationMode, asMaxBsSocTrapStatusGpsSyncPresent, asMaxBsSocGpsSyncChangeTrap
				- Added encryption mode configuration
				- Added authentication configuration
				October 01, 2006 at 13:13 GMT
				Draft 1
				- Released for SR3.0
				September 04, 2006 at 18:16 GMT
				column name corrected from asdmaxSsStatusProductCode to asmaxSsStatusProductCode
				"
			REVISION "201007261100Z"		-- July 26, 2010 at 11:00 GMT
			DESCRIPTION 
				"Draft 24:
				- Added support for Encryption Licensing i.e. objects asMaxBsSocLicenceCertificate and asMaxBsSocLicenceCertCapabilities
                for config and status and trap asMaxBsSocLicenceCertInvalidTrap to report errors in the certificate "
			::= { asMaxBS 5 }

		
	
--
-- Textual conventions
--
	
		AsmaxLeChannelMap ::= TEXTUAL-CONVENTION
			STATUS current
			DESCRIPTION 
				"Defines binary map of all license exempt channel. It can be used for objects
				enabling defined behaviour on a per channel bases. Example is DFS when channel
				can be included(enabled) or excluded(disable) for dynamic frequency selection.
				  Bit 0: enabled/disabled channel 0
				  Bit 1: enabled/disabled channel 1
				  ...
				  Bit 199: enabled/disabled channel 199
				The actual center frequency fro each channel dependa on the channel numbering scheme."
			SYNTAX OCTET STRING (SIZE (25))

	
--
-- Node definitions
--
	
		-- 1.3.6.1.4.1.989.1.16.2.5.1
		asMaxBsSocConformance OBJECT IDENTIFIER ::= { asMaxBSSoc 1 }

		
		-- 1.3.6.1.4.1.989.1.16.2.5.1.1
		asMaxBsSocConfigurationGroup OBJECT-GROUP
			OBJECTS { asMaxBsSocRfConfTxPower, asMaxBsSocRfStatDuplexMode, asMaxBsSocRfStatMinTxPower, asMaxBsSocRfStatMaxTxPower, asMaxBsSocRfStatTxPowerInd, 
				asMaxBsSocConfBandwidth, asMaxBsSocConfUplinkCinrProtection, asMaxBsSocConfSubchannelisationEnabled, asmaxBsSocSsStatusProductCode, asMaxBsSocConfAuthenticationEnabled, 
				asMaxBsSocConfDataEncryptModeMap, asMaxBsSocConfGpsOperationMode, asMaxBsSocTrapStatusGpsSyncPresent, asMaxBsSocRfStatOldDnlkFrequencyInd, asMaxBsSocRfStatCurrentDnlkFrequencyInd, 
				asMaxBsSocRfConfTxEnabled, asMaxBsSocSchedulerDlSubframeSize, asMaxBsSocSchedulerAdaptiveSplit, asMaxBsSocSchedulerFrameMode, asMaxBsSocConfBcastScIndex, 
				asMaxBsSocConfBcastScAssociated, asMaxBsSocSvcClassExtRowStatus, asMaxBsSocSvcClassExtPollPeriod, asMaxBsSocSsIpAddress, asMaxBsSocSsIpAddrType, 
				asMaxBsSocSsSwVersion, asMaxBsSocSsHwRevision, asMaxBsSocClsfRuleExtRowStatus, asMaxBsSocClsfRuleExtQTagPriority, asMaxBsSocClsfRuleExtQTagVlanID, 
				asMaxBsSocClsfRuleExtQTagEnabled, asMaxBsSocClsfRuleExtAction, asMaxBsSocSsTrapSsEvent, asMaxBsSocSsTrapSsMacAddress, asMaxBsSocRfConfRxCommandedPower, 
				asMaxBsSocConfUplinkCinrHisteresis, asMaxBsSocSsWiFiApIpAddrType, asMaxBsSocSsWiFiApIpAddress, asMaxBsSocSsWiFiApMacAddress, asMaxBsSocSsEasyVoiceIpAddrType, 
				asMaxBsSocDfsEnabled, asMaxBsSocVlanCfgRowStatus, asMaxBsSocVlanCfgDhcpRelayAgentMode, asMaxBsSocTrapStatusDfsChannelNumber, asMaxBsSocTrapStatusDfsEventType, 
				asMaxBsSocSsCfgDlBurstConfigEnabled, asMaxBsSocSsCfgAllowedBSID, asMaxBsSocSsEasyVoiceMacAddress, asMaxBsSocSsEasyVoiceIpAddress, asMaxBsSocSsCfgDlBurstAvgAlphaLow, 
				asMaxBsSocSsCfgDlBurstAvgAlphaHigh, asMaxBsSocSsCfgDlBurstSnrProtection, asMaxBsSocSsCfgDlBurstSnrHysteresis, asMaxBsSocSsCfgLanTableMaxSize, asMaxBsSocSsCfgAllowedBSIDMask, 
				asMaxBsSocConfBcastOfdmRateId, asMaxBsSocSsCfgBsidConfigEnabled, asMaxBsSocSsCfgRowStatus, asMaxBsSocConfUlMidambles, asMaxBsSocDfsAvailabilityCheckEnabled, 
				asMaxBsSocDfsInServiceCheckEnabled, asMaxBsSocDfsIMEnabled, asMaxBsSocDfsStandardType, asMaxBsSocDfsChannelListScheme, asMaxBsSocDfsChannelMap, 
				asMaxBsSocDfsPowerThreshold, asMaxBsSocDfsTxPowerLimitCfgEnabled, asMaxBsSocDfsTxPowerLimit, asMaxBsSocDfsNumSssToSwitchChannel, asMaxBsSocDfsMeasurementBw, 
				asMaxBsSocDfsMinNumberPulses, asMaxBsSocDfsDetectSensibility, asMaxBsSocVlanCfgMacFFIpAddress, asMaxBsSocVlanCfgMacFFIpAddressType, asMaxBsSocVlanCfgMacFFEnabled, 
				asMaxBsSocConfDynamicConEnable, asMaxBsSocConfDynamicConLowCollisionRate, asMaxBsSocConfDynamicConHighCollisionRate, asMaxBsSocConfDynamicConSampleRate, asMaxBsSocVlanCfgSingleUserEnabled, 
				asMaxBsSocConfAltRemoteIdEnabled, asMaxBsSocSsCfgRemoteId, asMaxBsSocConfCircuitID, asMaxBsSocDfsMinNumberOfBursts, asMaxBsSocConfReuseGroup, 
				asMaxBsSocSchedulingPolicy, asMaxBsSocPriority0Weighting, asMaxBsSocPriority1Weighting, asMaxBsSocPriority2Weighting, asMaxBsSocPriority3Weighting, 
				asMaxBsSocPriority4Weighting, asMaxBsSocPriority5Weighting, asMaxBsSocPriority6Weighting, asMaxBsSocPriority7Weighting, asMaxBsSocCccEnabled, 
				asMaxBsSocCccMaxPowerThreshold, asMaxBsSocTrapStatusLicenceCertInvalid, asMaxBsSocLicenceCertificate, asMaxBsSocLicenceCertCapabilities }
			STATUS current
			DESCRIPTION 
				"Description."
			::= { asMaxBsSocConformance 1 }

		
		-- 1.3.6.1.4.1.989.1.16.2.5.1.2
		asMaxBsSocNotificationGroup NOTIFICATION-GROUP
			NOTIFICATIONS { asMaxBsSocGpsSyncChangeTrap, asMaxBsSocSsStatusChangedTrap, asMaxBsSocSsEventTrap, asMaxBsSocDfsEventTrap, asMaxBsSocLicenceCertInvalidTrap
				 }
			STATUS current
			DESCRIPTION 
				"Description."
			::= { asMaxBsSocConformance 2 }

		
		-- 1.3.6.1.4.1.989.1.16.2.5.1.3
		asMaxBsSocCompliance MODULE-COMPLIANCE
			STATUS current
			DESCRIPTION 
				"Description."
			MODULE -- this module
				MANDATORY-GROUPS { asMaxBsSocConfigurationGroup, asMaxBsSocNotificationGroup }
			::= { asMaxBsSocConformance 3 }

		
		-- 1.3.6.1.4.1.989.1.16.2.5.1.4
		asMaxBsSocObsoleteGroup OBJECT-GROUP
			OBJECTS { asMaxBsSocConfSsMinSubchanWidth, asMaxBsSocSsCfgSubChannelMinWidth }
			STATUS obsolete
			DESCRIPTION 
				"Description."
			::= { asMaxBsSocConformance 4 }

		
		-- 1.3.6.1.4.1.989.1.16.2.5.2
		asMaxBsSocNotifications OBJECT IDENTIFIER ::= { asMaxBSSoc 2 }

		
		-- 1.3.6.1.4.1.989.1.16.2.5.2.0
		asMaxBsSocTrapPrefix OBJECT IDENTIFIER ::= { asMaxBsSocNotifications 0 }

		
		-- 1.3.6.1.4.1.989.1.16.2.5.2.0.1
		asMaxBsSocGpsSyncChangeTrap NOTIFICATION-TYPE
			OBJECTS { asMaxBsSocTrapStatusGpsSyncPresent }
			STATUS current
			DESCRIPTION 
				"Trap is sent each time when the synchronisation signal from GPS is lost or recovered.
				Associated object is sent to indicate what is the status of the synchronisation after the change."
			::= { asMaxBsSocTrapPrefix 1 }

		
		-- 1.3.6.1.4.1.989.1.16.2.5.2.0.2
		asMaxBsSocSsStatusChangedTrap NOTIFICATION-TYPE
			OBJECTS { asMaxBsSocSsTrapSsMacAddress, asMaxBsSocSsHwRevision, asMaxBsSocSsSwVersion, asMaxBsSocSsIpAddrType, asMaxBsSocSsIpAddress, 
				asMaxBsSocSsWiFiApIpAddrType, asMaxBsSocSsWiFiApIpAddress, asMaxBsSocSsWiFiApMacAddress, asMaxBsSocSsEasyVoiceIpAddrType, asMaxBsSocSsEasyVoiceIpAddress, 
				asMaxBsSocSsEasyVoiceMacAddress }
			STATUS current
			DESCRIPTION 
				"BS shall send this trap each time any of the critical to NMS operation
				status parameters changes: SW version, IP and MAC addresses of SS itself,
				WiFi AP and EasyVoice."
			::= { asMaxBsSocTrapPrefix 2 }

		
		-- 1.3.6.1.4.1.989.1.16.2.5.2.0.3
		asMaxBsSocSsEventTrap NOTIFICATION-TYPE
			OBJECTS { asMaxBsSocSsTrapSsMacAddress, asMaxBsSocSsTrapSsEvent }
			STATUS current
			DESCRIPTION 
				"Description."
			::= { asMaxBsSocTrapPrefix 3 }

		
		-- 1.3.6.1.4.1.989.1.16.2.5.2.0.4
		asMaxBsSocDfsEventTrap NOTIFICATION-TYPE
			OBJECTS { ifIndex, asMaxBsSocTrapStatusDfsEventType, asMaxBsSocTrapStatusDfsChannelNumber }
			STATUS current
			DESCRIPTION 
				"Defines the event trap for DFS system.
				Some values of the event type may raise an alarm and some may clear (NMS specific).
				For example dfsEventTypeUnableToTransmit value of asMaxBsSocTrapStatusDfsEventType
				will raise an alarm."
			::= { asMaxBsSocTrapPrefix 4 }

		
		-- 1.3.6.1.4.1.989.1.16.2.5.2.0.5
		asMaxBsSocLicenceCertInvalidTrap NOTIFICATION-TYPE
			OBJECTS { asMaxBsSocTrapStatusLicenceCertInvalid }
			STATUS current
			DESCRIPTION 
				"Trap sent to indicate a change in the validity of the encryption licence certificate."
			::= { asMaxBsSocTrapPrefix 5 }

		
		-- 1.3.6.1.4.1.989.1.16.2.5.2.2
		asMaxBsSocTrapStatusTable OBJECT-TYPE
			SYNTAX SEQUENCE OF AsMaxBsSocTrapStatusEntry
			MAX-ACCESS not-accessible
			STATUS current
			DESCRIPTION
				"Description."
			::= { asMaxBsSocNotifications 2 }

		
		-- 1.3.6.1.4.1.989.1.16.2.5.2.2.1
		asMaxBsSocTrapStatusEntry OBJECT-TYPE
			SYNTAX AsMaxBsSocTrapStatusEntry
			MAX-ACCESS not-accessible
			STATUS current
			DESCRIPTION
				"Description."
			INDEX { asMaxBsSocTrapStatusIndex }
			::= { asMaxBsSocTrapStatusTable 1 }

		
		AsMaxBsSocTrapStatusEntry ::=
			SEQUENCE { 
				asMaxBsSocTrapStatusIndex
					Integer32,
				asMaxBsSocTrapStatusGpsSyncPresent
					AsmaxBooleanSwitch,
				asMaxBsSocTrapStatusDfsEventType
					INTEGER,
				asMaxBsSocTrapStatusDfsChannelNumber
					WmanIfChannelNumber,
				asMaxBsSocTrapStatusLicenceCertInvalid
					AsmaxBooleanSwitch
			 }

		-- 1.3.6.1.4.1.989.1.16.2.5.2.2.1.1
		asMaxBsSocTrapStatusIndex OBJECT-TYPE
			SYNTAX Integer32 (1)
			MAX-ACCESS not-accessible
			STATUS current
			DESCRIPTION
				"Arbitrary index for single row table with only one value 1."
			::= { asMaxBsSocTrapStatusEntry 1 }

		
		-- 1.3.6.1.4.1.989.1.16.2.5.2.2.1.2
		asMaxBsSocTrapStatusGpsSyncPresent OBJECT-TYPE
			SYNTAX AsmaxBooleanSwitch
			MAX-ACCESS read-only
			STATUS current
			DESCRIPTION
				"Reports the status of synchronisation. True value indicates that synchronistation is present.
				False value indicated lost synchronisation."
			::= { asMaxBsSocTrapStatusEntry 2 }

		
		-- 1.3.6.1.4.1.989.1.16.2.5.2.2.1.3
		asMaxBsSocTrapStatusDfsEventType OBJECT-TYPE
			SYNTAX INTEGER
				{
				dfsEventRadarDetected(1),
				dfsEventNewChannelSelected(2),
				dfsEventUnableToTransmit(3),
				dfsEventUnableToOperate2Channels(4),
				dfsEventUnableToOperate3Channels(5)
				}
			MAX-ACCESS read-only
			STATUS current
			DESCRIPTION
				"Object defines the type of change reported by DFS system.
				Values dfsEventRadarDetected and dfsEventUnableToTransmit 
				can be used to raise an alarm.
				Value dfsEventNewChannelSelected can be used to clear alarm.
				Values dfsEventUnableToOperate2Channels, dfsEventUnableToOperate3Channels
				are info."
			::= { asMaxBsSocTrapStatusEntry 3 }

		
		-- 1.3.6.1.4.1.989.1.16.2.5.2.2.1.4
		asMaxBsSocTrapStatusDfsChannelNumber OBJECT-TYPE
			SYNTAX WmanIfChannelNumber
			MAX-ACCESS read-only
			STATUS current
			DESCRIPTION
				"Object defines the channel number associated with asMaxBsSocTrapStatusDfsEventType.
				In case where the channel is not selected the channelNumber=0."
			::= { asMaxBsSocTrapStatusEntry 4 }

		
		-- 1.3.6.1.4.1.989.1.16.2.5.2.2.1.5
		asMaxBsSocTrapStatusLicenceCertInvalid OBJECT-TYPE
			SYNTAX AsmaxBooleanSwitch
			MAX-ACCESS read-only
			STATUS current
			DESCRIPTION
				"Reports the invalidity or otherwise of the currently configured encryption licence.
				Note: a value of TRUE indicates that the licence is INVALID; a value of FALSE that the licence is VALID.
				In the absence of any configured encryption licence, this property shall report FALSE."
			::= { asMaxBsSocTrapStatusEntry 5 }

		
		-- 1.3.6.1.4.1.989.1.16.2.5.2.3
		asMaxBsSocSsTrapStatusTable OBJECT-TYPE
			SYNTAX SEQUENCE OF AsMaxBsSocSsTrapStatusEntry
			MAX-ACCESS not-accessible
			STATUS current
			DESCRIPTION
				"Table providing definitions of trap specific objects 
				for BS-SS traps."
			::= { asMaxBsSocNotifications 3 }

		
		-- 1.3.6.1.4.1.989.1.16.2.5.2.3.1
		asMaxBsSocSsTrapStatusEntry OBJECT-TYPE
			SYNTAX AsMaxBsSocSsTrapStatusEntry
			MAX-ACCESS not-accessible
			STATUS current
			DESCRIPTION
				"Description."
			INDEX { asMaxBsSocSsTrapSsMacAddress }
			::= { asMaxBsSocSsTrapStatusTable 1 }

		
		AsMaxBsSocSsTrapStatusEntry ::=
			SEQUENCE { 
				asMaxBsSocSsTrapSsMacAddress
					MacAddress,
				asMaxBsSocSsTrapSsEvent
					INTEGER
			 }

		-- 1.3.6.1.4.1.989.1.16.2.5.2.3.1.1
		asMaxBsSocSsTrapSsMacAddress OBJECT-TYPE
			SYNTAX MacAddress
			MAX-ACCESS read-only
			STATUS current
			DESCRIPTION
				"SS MAC address defintion used as atrap object."
			::= { asMaxBsSocSsTrapStatusEntry 1 }

		
		-- 1.3.6.1.4.1.989.1.16.2.5.2.3.1.2
		asMaxBsSocSsTrapSsEvent OBJECT-TYPE
			SYNTAX INTEGER { ssEventWiFiReset(0) }
			MAX-ACCESS read-only
			STATUS current
			DESCRIPTION
				"An event sent by SS to BS. BS should send trap asMaxBsSocSsEventTrap
				containing the definition of SS event."
			::= { asMaxBsSocSsTrapStatusEntry 2 }

		
		-- 1.3.6.1.4.1.989.1.16.2.5.3
		asMaxBsSocPacketCs OBJECT IDENTIFIER ::= { asMaxBSSoc 3 }

		
		-- 1.3.6.1.4.1.989.1.16.2.5.3.1
		asMaxBsSocSvcClassExtTable OBJECT-TYPE
			SYNTAX SEQUENCE OF AsMaxBsSocSvcClassExtEntry
			MAX-ACCESS not-accessible
			STATUS current
			DESCRIPTION
				"Description."
			::= { asMaxBsSocPacketCs 1 }

		
		-- 1.3.6.1.4.1.989.1.16.2.5.3.1.1
		asMaxBsSocSvcClassExtEntry OBJECT-TYPE
			SYNTAX AsMaxBsSocSvcClassExtEntry
			MAX-ACCESS not-accessible
			STATUS current
			DESCRIPTION
				"A table defining extensions to WMAN-IF-MIB standard MIB 
				table wmanIfBsServiceClassTable.
				When the row in this table doesn't exist the system should
				ignore the corresponding row in the base table or use
				some default values instead."
			INDEX { ifIndex, wmanIfBsQoSProfileIndex }
			::= { asMaxBsSocSvcClassExtTable 1 }

		
		AsMaxBsSocSvcClassExtEntry ::=
			SEQUENCE { 
				asMaxBsSocSvcClassExtPollPeriod
					INTEGER,
				asMaxBsSocSvcClassExtRowStatus
					RowStatus
			 }

		-- 1.3.6.1.4.1.989.1.16.2.5.3.1.1.1
		asMaxBsSocSvcClassExtPollPeriod OBJECT-TYPE
			SYNTAX INTEGER (1..60000)
			UNITS "ms"
			MAX-ACCESS read-create
			STATUS current
			DESCRIPTION
				"Poll period (in miliseconds) used by RTPS, nRTPS and UGS (sometimes) to 
				define the grant repetition rate."
			DEFVAL { 1000 }
			::= { asMaxBsSocSvcClassExtEntry 1 }

		
		-- 1.3.6.1.4.1.989.1.16.2.5.3.1.1.2
		asMaxBsSocSvcClassExtRowStatus OBJECT-TYPE
			SYNTAX RowStatus
			MAX-ACCESS read-create
			STATUS current
			DESCRIPTION
				"Description."
			::= { asMaxBsSocSvcClassExtEntry 2 }

		
		-- 1.3.6.1.4.1.989.1.16.2.5.3.2
		asMaxBsSocClassifierRuleExtTable OBJECT-TYPE
			SYNTAX SEQUENCE OF AsMaxBsSocClassifierRuleExtEntry
			MAX-ACCESS not-accessible
			STATUS current
			DESCRIPTION
				"Description."
			::= { asMaxBsSocPacketCs 2 }

		
		-- 1.3.6.1.4.1.989.1.16.2.5.3.2.1
		asMaxBsSocClassifierRuleExtEntry OBJECT-TYPE
			SYNTAX AsMaxBsSocClassifierRuleExtEntry
			MAX-ACCESS not-accessible
			STATUS current
			DESCRIPTION
				"Description."
			INDEX { ifIndex, wmanIfBsSfId, wmanIfBsClassifierRuleIndex }
			::= { asMaxBsSocClassifierRuleExtTable 1 }

		
		AsMaxBsSocClassifierRuleExtEntry ::=
			SEQUENCE { 
				asMaxBsSocClsfRuleExtAction
					BITS,
				asMaxBsSocClsfRuleExtQTagEnabled
					AsmaxBooleanSwitch,
				asMaxBsSocClsfRuleExtQTagVlanID
					AsDot1qVlanIdOrNone,
				asMaxBsSocClsfRuleExtQTagPriority
					INTEGER,
				asMaxBsSocClsfRuleExtRowStatus
					RowStatus
			 }

		-- 1.3.6.1.4.1.989.1.16.2.5.3.2.1.1
		asMaxBsSocClsfRuleExtAction OBJECT-TYPE
			SYNTAX BITS { classifierRuleActionDiscard(0) }
			MAX-ACCESS read-create
			STATUS current
			DESCRIPTION
				"An action to be taken when the packet matches the rule. The first bit defines
				general forward/discard action. The default value is empty (i.e. all bits clear), 
				which means forward. The classification rule actions were initially defined 
				in the amendment 802.16e. This object is defined in absence of relevant object
				in the standard WMAN-IF-MIB."
			REFERENCE
				"IEEE802.16e-2005 standard, subcluse 11.13.19.3.4.17"
			DEFVAL { {  } }
			::= { asMaxBsSocClassifierRuleExtEntry 1 }

		
		-- 1.3.6.1.4.1.989.1.16.2.5.3.2.1.2
		asMaxBsSocClsfRuleExtQTagEnabled OBJECT-TYPE
			SYNTAX AsmaxBooleanSwitch
			MAX-ACCESS read-create
			STATUS current
			DESCRIPTION
				"When enabled each packet matching this classifier rule shall have
				a VLAN tag inserted with VLAN ID defined by asMaxBsSocClsfRuleExtQTagVlanID
				and VLAN priority defined by asMaxBsSocClsfRuleExtQTagPriority."
			DEFVAL { booleanFalse }
			::= { asMaxBsSocClassifierRuleExtEntry 2 }

		
		-- 1.3.6.1.4.1.989.1.16.2.5.3.2.1.3
		asMaxBsSocClsfRuleExtQTagVlanID OBJECT-TYPE
			SYNTAX AsDot1qVlanIdOrNone
			MAX-ACCESS read-create
			STATUS current
			DESCRIPTION
				"VLAN ID of the VLAN tag inserted in the packet when packet matches 
				the classification rule and the tagging is enabled by the object 
				asMaxBsSocClsfRuleExtQTagEnabled. A value of 0 should be used when 
				the tagging is disabled."
			DEFVAL { 0 }
			::= { asMaxBsSocClassifierRuleExtEntry 3 }

		
		-- 1.3.6.1.4.1.989.1.16.2.5.3.2.1.4
		asMaxBsSocClsfRuleExtQTagPriority OBJECT-TYPE
			SYNTAX INTEGER (0..7)
			MAX-ACCESS read-create
			STATUS current
			DESCRIPTION
				"VLAN priority (as defined in 802.1Q) of the VLAN tag inserted in the packet when packet matches 
				the classification rule and the tagging is enabled by the object 
				asMaxBsSocClsfRuleExtQTagEnabled."
			DEFVAL { 0 }
			::= { asMaxBsSocClassifierRuleExtEntry 4 }

		
		-- 1.3.6.1.4.1.989.1.16.2.5.3.2.1.5
		asMaxBsSocClsfRuleExtRowStatus OBJECT-TYPE
			SYNTAX RowStatus
			MAX-ACCESS read-create
			STATUS current
			DESCRIPTION
				"Description."
			::= { asMaxBsSocClassifierRuleExtEntry 5 }

		
		-- 1.3.6.1.4.1.989.1.16.2.5.4
		asMaxBsSocCps OBJECT IDENTIFIER ::= { asMaxBSSoc 4 }

		
		-- 1.3.6.1.4.1.989.1.16.2.5.4.1
		asMaxBsSocConfigTable OBJECT-TYPE
			SYNTAX SEQUENCE OF AsMaxBsSocConfigEntry
			MAX-ACCESS not-accessible
			STATUS current
			DESCRIPTION
				"General purpose configuration table for BS application and protocols."
			::= { asMaxBsSocCps 1 }

		
		-- 1.3.6.1.4.1.989.1.16.2.5.4.1.1
		asMaxBsSocConfigEntry OBJECT-TYPE
			SYNTAX AsMaxBsSocConfigEntry
			MAX-ACCESS not-accessible
			STATUS current
			DESCRIPTION
				"One row per interface."
			INDEX { ifIndex }
			::= { asMaxBsSocConfigTable 1 }

		
		AsMaxBsSocConfigEntry ::=
			SEQUENCE { 
				asMaxBsSocConfBandwidth
					AsmaxBandwidthCode,
				asMaxBsSocConfUplinkCinrProtection
					INTEGER,
				asMaxBsSocConfUplinkCinrHisteresis
					INTEGER,
				asMaxBsSocConfSubchannelisationEnabled
					AsmaxBooleanSwitch,
				asMaxBsSocConfGpsOperationMode
					INTEGER,
				asMaxBsSocConfDataEncryptModeMap
					BITS,
				asMaxBsSocConfAuthenticationEnabled
					AsmaxBooleanSwitch,
				asMaxBsSocConfBcastScAssociated
					AsmaxBooleanSwitch,
				asMaxBsSocConfBcastScIndex
					Integer32,
				asMaxBsSocConfSsMinSubchanWidth
					INTEGER,
				asMaxBsSocConfUlMidambles
					INTEGER,
				asMaxBsSocConfBcastOfdmRateId
					INTEGER,
				asMaxBsSocConfReuseGroup
					INTEGER,
				asMaxBsSocConfDynamicConEnable
					AsmaxBooleanSwitch,
				asMaxBsSocConfDynamicConLowCollisionRate
					INTEGER,
				asMaxBsSocConfDynamicConHighCollisionRate
					INTEGER,
				asMaxBsSocConfDynamicConSampleRate
					INTEGER,
				asMaxBsSocConfAltRemoteIdEnabled
					AsmaxBooleanSwitch,
				asMaxBsSocConfCircuitID
					INTEGER
			 }

		-- 1.3.6.1.4.1.989.1.16.2.5.4.1.1.1
		asMaxBsSocConfBandwidth OBJECT-TYPE
			SYNTAX AsmaxBandwidthCode
			MAX-ACCESS read-write
			STATUS current
			DESCRIPTION
				"Description."
			::= { asMaxBsSocConfigEntry 1 }

		
		-- 1.3.6.1.4.1.989.1.16.2.5.4.1.1.2
		asMaxBsSocConfUplinkCinrProtection OBJECT-TYPE
			SYNTAX INTEGER (0..60)
			UNITS "0.25 dB"
			MAX-ACCESS read-write
			STATUS current
			DESCRIPTION
				"Configure CINR protection in db from nominal CINR(predefined in SW)"
			DEFVAL { 6 }
			::= { asMaxBsSocConfigEntry 2 }

		
		-- 1.3.6.1.4.1.989.1.16.2.5.4.1.1.3
		asMaxBsSocConfUplinkCinrHisteresis OBJECT-TYPE
			SYNTAX INTEGER (0..60)
			UNITS "0.25 dB"
			MAX-ACCESS read-write
			STATUS current
			DESCRIPTION
				"Configure CINR hysteresis  in db when upgrading the FEC code"
			DEFVAL { 4 }
			::= { asMaxBsSocConfigEntry 3 }

		
		-- 1.3.6.1.4.1.989.1.16.2.5.4.1.1.4
		asMaxBsSocConfSubchannelisationEnabled OBJECT-TYPE
			SYNTAX AsmaxBooleanSwitch
			MAX-ACCESS read-write
			STATUS current
			DESCRIPTION
				"Enable/disable adaptive subchannelisation system on this BS.
				When subchannelisation system is disabled all SSs 
				are instructed to use full channel width."
			DEFVAL { booleanFalse }
			::= { asMaxBsSocConfigEntry 4 }

		
		-- 1.3.6.1.4.1.989.1.16.2.5.4.1.1.5
		asMaxBsSocConfGpsOperationMode OBJECT-TYPE
			SYNTAX INTEGER
				{
				gpsModeSyncDisabled(1),
				gpsModeTrapAndStop(2),
				gpsModeTrapAndContinue(3)
				}
			MAX-ACCESS read-write
			STATUS current
			DESCRIPTION
				"Defines what BS sector should do in case of loss of synchronisation from GPS.
				This object may be also used to enable/disable frame synchronisation in absence
				of GPS (internal synchronisation)."
			DEFVAL { gpsModeTrapAndStop }
			::= { asMaxBsSocConfigEntry 5 }

		
		-- 1.3.6.1.4.1.989.1.16.2.5.4.1.1.6
		asMaxBsSocConfDataEncryptModeMap OBJECT-TYPE
			SYNTAX BITS
				{
				dataEncryptNone(0),
				dataEncryptCbcDes(1),
				dataEncryptCcmAes(2)
				}
			MAX-ACCESS read-write
			STATUS current
			DESCRIPTION
				"Configuration of allowed data encryption modes (algorythms) for all SSs registered on this BS sector.
				The mode map bits indicated the modes which are enabled (bit set to 1) and modes
				which are disabled (bit set to 0).
				"
			REFERENCE
				"IEEE 802.16-2004, Table 375"
			DEFVAL { { dataEncryptNone,dataEncryptCbcDes,dataEncryptCcmAes } }
			::= { asMaxBsSocConfigEntry 6 }

		
		-- 1.3.6.1.4.1.989.1.16.2.5.4.1.1.7
		asMaxBsSocConfAuthenticationEnabled OBJECT-TYPE
			SYNTAX AsmaxBooleanSwitch
			MAX-ACCESS read-write
			STATUS current
			DESCRIPTION
				"Enables authentication od SSs. When disabled all SSs are authenticated 
				and allowed to continue the net entry process without any checks of certificates or other."
			DEFVAL { booleanFalse }
			::= { asMaxBsSocConfigEntry 7 }

		
		-- 1.3.6.1.4.1.989.1.16.2.5.4.1.1.8
		asMaxBsSocConfBcastScAssociated OBJECT-TYPE
			SYNTAX AsmaxBooleanSwitch
			MAX-ACCESS read-write
			STATUS current
			DESCRIPTION
				"If set to true the BS uses provisioned Service Class index (asMaxBsSocConfBcastScIndex)."
			DEFVAL { booleanFalse }
			::= { asMaxBsSocConfigEntry 8 }

		
		-- 1.3.6.1.4.1.989.1.16.2.5.4.1.1.9
		asMaxBsSocConfBcastScIndex OBJECT-TYPE
			SYNTAX Integer32 (1..65535)
			MAX-ACCESS read-write
			STATUS current
			DESCRIPTION
				"Index to Service Class to be used to police QoS of broadcast channel.
				Only used when object asMaxBsSocConfBcastScAssociated is set to true."
			::= { asMaxBsSocConfigEntry 9 }

		
		-- 1.3.6.1.4.1.989.1.16.2.5.4.1.1.10
		asMaxBsSocConfSsMinSubchanWidth OBJECT-TYPE
			SYNTAX INTEGER
				{
				subChannelWidthSixteenth(1),
				subChannelWidthEighth(2),
				subChannelWidthQuarter(4),
				subChannelWidthHalf(8),
				subChannelWidthFull(16)
				}
			MAX-ACCESS read-write
			STATUS obsolete
			DESCRIPTION
				"Indicates the minimum bandwidth that will be granted to the SSs
				for uplink data.  Must be 16, 8, 4, 2, or 1, where 
				16 = full bandwidth and 1 = sixteenth of bandwidth."
			DEFVAL { subChannelWidthFull }
			::= { asMaxBsSocConfigEntry 10 }

		
		-- 1.3.6.1.4.1.989.1.16.2.5.4.1.1.11
		asMaxBsSocConfUlMidambles OBJECT-TYPE
			SYNTAX INTEGER
				{
				disabled(0),
				afterEvery4DataSymbols(1),
				afterEvery8DataSymbols(2),
				afterEvery16DataSymbols(3)
				}
			MAX-ACCESS read-write
			STATUS current
			DESCRIPTION
				"Selects the uplink midamble mode to use inthe BS.
				Labels of enumeration corrected based on 802.16e-2005."
			DEFVAL { disabled }
			::= { asMaxBsSocConfigEntry 11 }

		
		-- 1.3.6.1.4.1.989.1.16.2.5.4.1.1.12
		asMaxBsSocConfBcastOfdmRateId OBJECT-TYPE
			SYNTAX INTEGER
				{
				rateIdBpsk1over2(0),
				rateIdQpsk1over2(1),
				rateIdQpsk3over4(2),
				rateId16Qam1over2(3),
				rateId16Qam3over4(4),
				rateId64Qam2over3(5),
				rateId64Qam3over4(6)
				}
			MAX-ACCESS read-write
			STATUS current
			DESCRIPTION
				"The Rate ID to be used in the downlink broadcast connection. 
				The rate ID defines the modulation encoding to be used."
			REFERENCE
				"Section 8.3.3.4.3 in IEEE 802.16-2004"
			DEFVAL { rateIdBpsk1over2 }
			::= { asMaxBsSocConfigEntry 12 }

		
		-- 1.3.6.1.4.1.989.1.16.2.5.4.1.1.13
		asMaxBsSocConfReuseGroup OBJECT-TYPE
			SYNTAX INTEGER
				{
				reuseGroupDisabled(0),
				reuseGroupA(1),
				reuseGroupB(2),
				reuseGroupC(3)
				}
			MAX-ACCESS read-write
			STATUS current
			DESCRIPTION
				"Defines the frequency reuse group the BS sector belongs to"
			DEFVAL { reuseGroupDisabled }
			::= { asMaxBsSocConfigEntry 13 }

		
		-- 1.3.6.1.4.1.989.1.16.2.5.4.1.1.14
		asMaxBsSocConfDynamicConEnable OBJECT-TYPE
			SYNTAX AsmaxBooleanSwitch
			MAX-ACCESS read-write
			STATUS current
			DESCRIPTION
				"Enable/Disable dynamic contention slots.
				Dynamically change the BWR opportunities number according to the collisions rate."
			DEFVAL { booleanFalse }
			::= { asMaxBsSocConfigEntry 14 }

		
		-- 1.3.6.1.4.1.989.1.16.2.5.4.1.1.15
		asMaxBsSocConfDynamicConLowCollisionRate OBJECT-TYPE
			SYNTAX INTEGER (1..100)
			UNITS "Percentage"
			MAX-ACCESS read-write
			STATUS current
			DESCRIPTION
				"Low collision percentage threshold."
			DEFVAL { 10 }
			::= { asMaxBsSocConfigEntry 15 }

		
		-- 1.3.6.1.4.1.989.1.16.2.5.4.1.1.16
		asMaxBsSocConfDynamicConHighCollisionRate OBJECT-TYPE
			SYNTAX INTEGER (1..100)
			UNITS "Percentage"
			MAX-ACCESS read-write
			STATUS current
			DESCRIPTION
				"High collision percentage threshold."
			DEFVAL { 30 }
			::= { asMaxBsSocConfigEntry 16 }

		
		-- 1.3.6.1.4.1.989.1.16.2.5.4.1.1.17
		asMaxBsSocConfDynamicConSampleRate OBJECT-TYPE
			SYNTAX INTEGER (1000..100000)
			UNITS "Milliseconds"
			MAX-ACCESS read-write
			STATUS current
			DESCRIPTION
				"Statisics sampling rate."
			DEFVAL { 10000 }
			::= { asMaxBsSocConfigEntry 17 }

		
		-- 1.3.6.1.4.1.989.1.16.2.5.4.1.1.18
		asMaxBsSocConfAltRemoteIdEnabled OBJECT-TYPE
			SYNTAX AsmaxBooleanSwitch
			MAX-ACCESS read-write
			STATUS current
			DESCRIPTION
				"Once a BSR was enabled to use AltRemoteId, for the received 
				DHCP option 82 request (from a PC behind an SS), it will insert the 
				Subscriber-ID in the RemoteId field instead of using the SS MacAddress."
			DEFVAL { booleanFalse }
			::= { asMaxBsSocConfigEntry 18 }

		
		-- 1.3.6.1.4.1.989.1.16.2.5.4.1.1.19
		asMaxBsSocConfCircuitID OBJECT-TYPE
			SYNTAX INTEGER (0..2147483647)
			MAX-ACCESS read-write
			STATUS current
			DESCRIPTION
				"The Circuit ID of base station. In DHCP packet with opt 82
				BS MAC address changed to Circuit ID."
			DEFVAL { 0 }
			::= { asMaxBsSocConfigEntry 19 }

		
		-- 1.3.6.1.4.1.989.1.16.2.5.4.2
		asMaxBsSocSsStatusTable OBJECT-TYPE
			SYNTAX SEQUENCE OF AsMaxBsSocSsStatusEntry
			MAX-ACCESS not-accessible
			STATUS current
			DESCRIPTION
				"This table contains SS related status information not present
				in standard MIB. There is one row for every SS registered with BS.
				This table effectively extends the table wmanIfBsRegisteredSsTable."
			::= { asMaxBsSocCps 2 }

		
		-- 1.3.6.1.4.1.989.1.16.2.5.4.2.1
		asMaxBsSocSsStatusEntry OBJECT-TYPE
			SYNTAX AsMaxBsSocSsStatusEntry
			MAX-ACCESS not-accessible
			STATUS current
			DESCRIPTION
				"Description."
			INDEX { wmanIfBsSsMacAddress }
			::= { asMaxBsSocSsStatusTable 1 }

		
		AsMaxBsSocSsStatusEntry ::=
			SEQUENCE { 
				asmaxBsSocSsStatusProductCode
					OCTET STRING,
				asMaxBsSocSsHwRevision
					INTEGER,
				asMaxBsSocSsSwVersion
					DisplayString,
				asMaxBsSocSsIpAddrType
					InetAddressType,
				asMaxBsSocSsIpAddress
					InetAddress,
				asMaxBsSocSsWiFiApIpAddrType
					InetAddressType,
				asMaxBsSocSsWiFiApIpAddress
					InetAddress,
				asMaxBsSocSsWiFiApMacAddress
					MacAddress,
				asMaxBsSocSsEasyVoiceIpAddrType
					InetAddressType,
				asMaxBsSocSsEasyVoiceIpAddress
					InetAddress,
				asMaxBsSocSsEasyVoiceMacAddress
					MacAddress
			 }

		-- 1.3.6.1.4.1.989.1.16.2.5.4.2.1.1
		asmaxBsSocSsStatusProductCode OBJECT-TYPE
			SYNTAX OCTET STRING (SIZE (0..64))
			MAX-ACCESS read-only
			STATUS current
			DESCRIPTION
				"String based code identifying SS product e.g. EST490T-INT-4"
			::= { asMaxBsSocSsStatusEntry 1 }

		
		-- 1.3.6.1.4.1.989.1.16.2.5.4.2.1.2
		asMaxBsSocSsHwRevision OBJECT-TYPE
			SYNTAX INTEGER (0..65535)
			MAX-ACCESS read-only
			STATUS current
			DESCRIPTION
				"SS Hardware revision reported using custom TLV type 2 of REG-RSP.
				"
			REFERENCE
				"ASMAX Proprietary TLV r9.doc"
			DEFVAL { 0 }
			::= { asMaxBsSocSsStatusEntry 2 }

		
		-- 1.3.6.1.4.1.989.1.16.2.5.4.2.1.3
		asMaxBsSocSsSwVersion OBJECT-TYPE
			SYNTAX DisplayString
			MAX-ACCESS read-only
			STATUS current
			DESCRIPTION
				"SW version SS is currently running, reported using custom TLV type 3 of REG-RSP.
				BS shall send a trap asMaxBsSocReportedSsStatusChanged on each change 
				in the value of this object."
			REFERENCE
				"ASMAX Proprietary TLV r9.doc"
			::= { asMaxBsSocSsStatusEntry 3 }

		
		-- 1.3.6.1.4.1.989.1.16.2.5.4.2.1.4
		asMaxBsSocSsIpAddrType OBJECT-TYPE
			SYNTAX InetAddressType
			MAX-ACCESS read-only
			STATUS current
			DESCRIPTION
				"The type of InetAddress used by asMaxBsSocSsIpAddress. Typically it refers to IPv4
				but is defined in fully flexible way to satisfy SNMP MIB guidelines."
			DEFVAL { ipv4 }
			::= { asMaxBsSocSsStatusEntry 4 }

		
		-- 1.3.6.1.4.1.989.1.16.2.5.4.2.1.5
		asMaxBsSocSsIpAddress OBJECT-TYPE
			SYNTAX InetAddress
			MAX-ACCESS read-only
			STATUS current
			DESCRIPTION
				"IP address of SS management stack, 
				reported using custom TLV type 2.4 of CNFG-RSP.
				When address hasn't been reported yet the object shall read 0xFFFFFFFF.
				BS shall send a trap asMaxBsSocReportedSsStatusChanged on each change 
				in the value of this object."
			REFERENCE
				"ASMAX Proprietary TLV r9.doc"
			DEFVAL { 'FFFFFFFF'h }
			::= { asMaxBsSocSsStatusEntry 5 }

		
		-- 1.3.6.1.4.1.989.1.16.2.5.4.2.1.6
		asMaxBsSocSsWiFiApIpAddrType OBJECT-TYPE
			SYNTAX InetAddressType
			MAX-ACCESS read-only
			STATUS current
			DESCRIPTION
				"The type of InetAddress used by asMaxBsSocSsWiFiApIpAddress. Typically it refers to IPv4
				but is defined in fully flexible way to satisfy SNMP MIB guidelines."
			DEFVAL { ipv4 }
			::= { asMaxBsSocSsStatusEntry 6 }

		
		-- 1.3.6.1.4.1.989.1.16.2.5.4.2.1.7
		asMaxBsSocSsWiFiApIpAddress OBJECT-TYPE
			SYNTAX InetAddress
			MAX-ACCESS read-only
			STATUS current
			DESCRIPTION
				"IP address of SS integrated WiFi AP, 
				reported using custom TLV type 2.5 of CNFG-RSP.
				When address hasn't been reported yet the object shall read 0xFFFFFFFF.
				BS shall send a trap asMaxBsSocReportedSsStatusChanged on each change 
				in the value of this object."
			REFERENCE
				"ASMAX Proprietary TLV r9.doc"
			DEFVAL { 'FFFFFFFF'h }
			::= { asMaxBsSocSsStatusEntry 7 }

		
		-- 1.3.6.1.4.1.989.1.16.2.5.4.2.1.8
		asMaxBsSocSsWiFiApMacAddress OBJECT-TYPE
			SYNTAX MacAddress
			MAX-ACCESS read-only
			STATUS current
			DESCRIPTION
				"MAC Address of SS integrated WiFi AP, 
				reported using custom TLV type 2.7 of CNFG-RSP.
				When address hasn't been reported yet the object shall read FF:FF:FF:FF:FF:FF.
				BS shall send a trap asMaxBsSocReportedSsStatusChanged on each change 
				in the value of this object."
			REFERENCE
				"ASMAX Proprietary TLV r9.doc"
			DEFVAL { 'FFFFFFFFFFFF'h }
			::= { asMaxBsSocSsStatusEntry 8 }

		
		-- 1.3.6.1.4.1.989.1.16.2.5.4.2.1.9
		asMaxBsSocSsEasyVoiceIpAddrType OBJECT-TYPE
			SYNTAX InetAddressType
			MAX-ACCESS read-only
			STATUS current
			DESCRIPTION
				"The type of InetAddress used by asMaxBsSocSsEasyVoiceIpAddress. Typically it refers to IPv4
				but is defined in fully flexible way to satisfy SNMP MIB guidelines."
			DEFVAL { ipv4 }
			::= { asMaxBsSocSsStatusEntry 9 }

		
		-- 1.3.6.1.4.1.989.1.16.2.5.4.2.1.10
		asMaxBsSocSsEasyVoiceIpAddress OBJECT-TYPE
			SYNTAX InetAddress
			MAX-ACCESS read-only
			STATUS current
			DESCRIPTION
				"IP address of SS integrated EasyVoice product (residential VoIP gateway), 
				reported using custom TLV type 2.6 of CNFG-RSP.
				When address hasn't been reported yet the object shall read 0xFFFFFFFF.
				BS shall send a trap asMaxBsSocReportedSsStatusChanged on each change 
				in the value of this object."
			REFERENCE
				"ASMAX Proprietary TLV r9.doc"
			DEFVAL { 'FFFFFFFF'h }
			::= { asMaxBsSocSsStatusEntry 10 }

		
		-- 1.3.6.1.4.1.989.1.16.2.5.4.2.1.11
		asMaxBsSocSsEasyVoiceMacAddress OBJECT-TYPE
			SYNTAX MacAddress
			MAX-ACCESS read-only
			STATUS current
			DESCRIPTION
				"MAC Address of SS integrated EasyVoice product (residential VoIP gateway), 
				reported using custom TLV type 2.8 of CNFG-RSP.
				When address hasn't been reported yet the object shall read FF:FF:FF:FF:FF:FF.
				BS shall send a trap asMaxBsSocReportedSsStatusChanged on each change 
				in the value of this object."
			REFERENCE
				"ASMAX Proprietary TLV r9.doc"
			DEFVAL { 'FFFFFFFFFFFF'h }
			::= { asMaxBsSocSsStatusEntry 11 }

		
		-- 1.3.6.1.4.1.989.1.16.2.5.4.3
		asMaxBsSocSchedulerConfigTable OBJECT-TYPE
			SYNTAX SEQUENCE OF AsMaxBsSocSchedulerConfigEntry
			MAX-ACCESS not-accessible
			STATUS current
			DESCRIPTION
				"Description."
			::= { asMaxBsSocCps 3 }

		
		-- 1.3.6.1.4.1.989.1.16.2.5.4.3.1
		asMaxBsSocSchedulerConfigEntry OBJECT-TYPE
			SYNTAX AsMaxBsSocSchedulerConfigEntry
			MAX-ACCESS not-accessible
			STATUS current
			DESCRIPTION
				"Description."
			AUGMENTS { asMaxBsSocConfigEntry }
			::= { asMaxBsSocSchedulerConfigTable 1 }

		
		AsMaxBsSocSchedulerConfigEntry ::=
			SEQUENCE { 
				asMaxBsSocSchedulerFrameMode
					INTEGER,
				asMaxBsSocSchedulerAdaptiveSplit
					INTEGER,
				asMaxBsSocSchedulerDlSubframeSize
					Integer32,
				asMaxBsSocSchedulingPolicy
					INTEGER,
				asMaxBsSocPriority0Weighting
					Integer32,
				asMaxBsSocPriority1Weighting
					Integer32,
				asMaxBsSocPriority2Weighting
					Integer32,
				asMaxBsSocPriority3Weighting
					Integer32,
				asMaxBsSocPriority4Weighting
					Integer32,
				asMaxBsSocPriority5Weighting
					Integer32,
				asMaxBsSocPriority6Weighting
					Integer32,
				asMaxBsSocPriority7Weighting
					Integer32
			 }

		-- 1.3.6.1.4.1.989.1.16.2.5.4.3.1.1
		asMaxBsSocSchedulerFrameMode OBJECT-TYPE
			SYNTAX INTEGER
				{
				frameModeTdd(1),
				frameModeFdd(2)
				}
			MAX-ACCESS read-write
			STATUS current
			DESCRIPTION
				"Frame-mode can be used with duplex mode as follows:
				-FDD duplex with frameModeFdd
				-FDD duplex with frameModeTdd (simulated)
				-TDD duplex with frameModeTdd
				FDD mode can be simulated when working with TDD duplex."
			DEFVAL { frameModeFdd }
			::= { asMaxBsSocSchedulerConfigEntry 1 }

		
		-- 1.3.6.1.4.1.989.1.16.2.5.4.3.1.2
		asMaxBsSocSchedulerAdaptiveSplit OBJECT-TYPE
			SYNTAX INTEGER
				{
				adaptiveSplitFixed(1),
				adaptiveSplitVariable(2)
				}
			MAX-ACCESS read-write
			STATUS current
			DESCRIPTION
				"Object valid for TDD only. When fixed split is selected the size of the split is defiend
				by asMaxBsSocSchedulerDlSubframeSize."
			DEFVAL { adaptiveSplitVariable }
			::= { asMaxBsSocSchedulerConfigEntry 2 }

		
		-- 1.3.6.1.4.1.989.1.16.2.5.4.3.1.3
		asMaxBsSocSchedulerDlSubframeSize OBJECT-TYPE
			SYNTAX Integer32 (1..100)
			UNITS "%"
			MAX-ACCESS read-write
			STATUS current
			DESCRIPTION
				"Object is used only when asMaxBsSocSchedulerAdaptiveSplit selects mode adaptiveSplitFixed."
			DEFVAL { 50 }
			::= { asMaxBsSocSchedulerConfigEntry 3 }

		
		-- 1.3.6.1.4.1.989.1.16.2.5.4.3.1.4
		asMaxBsSocSchedulingPolicy OBJECT-TYPE
			SYNTAX INTEGER
				{
				strict(1),
				weightedFairQueuing(2)
				}
			MAX-ACCESS read-write
			STATUS current
			DESCRIPTION
				"Defines the scheduling policy for service flows."
			DEFVAL { strict }
			::= { asMaxBsSocSchedulerConfigEntry 4 }

		
		-- 1.3.6.1.4.1.989.1.16.2.5.4.3.1.5
		asMaxBsSocPriority0Weighting OBJECT-TYPE
			SYNTAX Integer32 (1..255)
			UNITS "1"
			MAX-ACCESS read-write
			STATUS current
			DESCRIPTION
				"Defines the weighting for priority level 0."
			::= { asMaxBsSocSchedulerConfigEntry 5 }

		
		-- 1.3.6.1.4.1.989.1.16.2.5.4.3.1.6
		asMaxBsSocPriority1Weighting OBJECT-TYPE
			SYNTAX Integer32 (1..255)
			UNITS "1"
			MAX-ACCESS read-write
			STATUS current
			DESCRIPTION
				"Defines the weighting for priority level 1."
			::= { asMaxBsSocSchedulerConfigEntry 6 }

		
		-- 1.3.6.1.4.1.989.1.16.2.5.4.3.1.7
		asMaxBsSocPriority2Weighting OBJECT-TYPE
			SYNTAX Integer32 (1..255)
			UNITS "1"
			MAX-ACCESS read-write
			STATUS current
			DESCRIPTION
				"Defines the weighting for priority level 2."
			::= { asMaxBsSocSchedulerConfigEntry 7 }

		
		-- 1.3.6.1.4.1.989.1.16.2.5.4.3.1.8
		asMaxBsSocPriority3Weighting OBJECT-TYPE
			SYNTAX Integer32 (1..255)
			UNITS "1"
			MAX-ACCESS read-write
			STATUS current
			DESCRIPTION
				"Defines the weighting for priority level 3."
			::= { asMaxBsSocSchedulerConfigEntry 8 }

		
		-- 1.3.6.1.4.1.989.1.16.2.5.4.3.1.9
		asMaxBsSocPriority4Weighting OBJECT-TYPE
			SYNTAX Integer32 (1..255)
			UNITS "1"
			MAX-ACCESS read-write
			STATUS current
			DESCRIPTION
				"Defines the weighting for priority level 4."
			::= { asMaxBsSocSchedulerConfigEntry 9 }

		
		-- 1.3.6.1.4.1.989.1.16.2.5.4.3.1.10
		asMaxBsSocPriority5Weighting OBJECT-TYPE
			SYNTAX Integer32 (1..255)
			UNITS "1"
			MAX-ACCESS read-write
			STATUS current
			DESCRIPTION
				"Defines the weighting for priority level 5."
			::= { asMaxBsSocSchedulerConfigEntry 10 }

		
		-- 1.3.6.1.4.1.989.1.16.2.5.4.3.1.11
		asMaxBsSocPriority6Weighting OBJECT-TYPE
			SYNTAX Integer32 (1..255)
			UNITS "1"
			MAX-ACCESS read-write
			STATUS current
			DESCRIPTION
				"Defines the weighting for priority level 6."
			::= { asMaxBsSocSchedulerConfigEntry 11 }

		
		-- 1.3.6.1.4.1.989.1.16.2.5.4.3.1.12
		asMaxBsSocPriority7Weighting OBJECT-TYPE
			SYNTAX Integer32 (1..255)
			UNITS "1"
			MAX-ACCESS read-write
			STATUS current
			DESCRIPTION
				"Defines the weighting for priority level 7."
			::= { asMaxBsSocSchedulerConfigEntry 12 }

		
		-- 1.3.6.1.4.1.989.1.16.2.5.4.4
		asMaxBsSocSsCfgTable OBJECT-TYPE
			SYNTAX SEQUENCE OF AsMaxBsSocSsCfgEntry
			MAX-ACCESS not-accessible
			STATUS current
			DESCRIPTION
				"Table with configuration objects for SSs."
			REFERENCE
				"Custom configuration of SS. Typically this is either implemented by BS on a per SS bases
				or send to SS using standard or custom TLVs.
				NMS should implement this configuration for classes of SSs (config profile)."
			::= { asMaxBsSocCps 4 }

		
		-- 1.3.6.1.4.1.989.1.16.2.5.4.4.1
		asMaxBsSocSsCfgEntry OBJECT-TYPE
			SYNTAX AsMaxBsSocSsCfgEntry
			MAX-ACCESS not-accessible
			STATUS current
			DESCRIPTION
				"Description."
			INDEX { wmanIfBsSsMacAddress }
			::= { asMaxBsSocSsCfgTable 1 }

		
		AsMaxBsSocSsCfgEntry ::=
			SEQUENCE { 
				asMaxBsSocSsCfgDlBurstConfigEnabled
					AsmaxBooleanSwitch,
				asMaxBsSocSsCfgDlBurstAvgAlphaLow
					INTEGER,
				asMaxBsSocSsCfgDlBurstAvgAlphaHigh
					INTEGER,
				asMaxBsSocSsCfgDlBurstSnrProtection
					INTEGER,
				asMaxBsSocSsCfgDlBurstSnrHysteresis
					INTEGER,
				asMaxBsSocSsCfgLanTableMaxSize
					INTEGER,
				asMaxBsSocSsCfgAllowedBSID
					WmanIfBsIdType,
				asMaxBsSocSsCfgAllowedBSIDMask
					WmanIfBsIdType,
				asMaxBsSocSsCfgRowStatus
					RowStatus,
				asMaxBsSocSsCfgBsidConfigEnabled
					AsmaxBooleanSwitch,
				asMaxBsSocSsCfgSubChannelMinWidth
					INTEGER,
				asMaxBsSocSsCfgRemoteId
					INTEGER
			 }

		-- 1.3.6.1.4.1.989.1.16.2.5.4.4.1.1
		asMaxBsSocSsCfgDlBurstConfigEnabled OBJECT-TYPE
			SYNTAX AsmaxBooleanSwitch
			MAX-ACCESS read-create
			STATUS current
			DESCRIPTION
				"When enabled BS shall send the configuration of downlink burst to this SS 
				using relevant custom TLVs. The configuration to send is defined in objects:
				asMaxBsSocSsCfgDlBurstAvgAlphaLow, asMaxBsSocSsCfgDlBurstAvgAlphaHigh,
				asMaxBsSocSsCfgDlBurstSnrProtection, asMaxBsSocSsCfgDlBurstSnrHysteresis."
			DEFVAL { booleanFalse }
			::= { asMaxBsSocSsCfgEntry 1 }

		
		-- 1.3.6.1.4.1.989.1.16.2.5.4.4.1.2
		asMaxBsSocSsCfgDlBurstAvgAlphaLow OBJECT-TYPE
			SYNTAX INTEGER (1..1023)
			MAX-ACCESS read-create
			STATUS current
			DESCRIPTION
				"Downlink burst profile parameters for adaptive modulation algorithm.
				Averaging factor alpha low defined in custom TLV 1.1.1 of CNFG-REQ."
			REFERENCE
				"ASMAX Proprietary TLV r9.doc"
			DEFVAL { 1 }
			::= { asMaxBsSocSsCfgEntry 2 }

		
		-- 1.3.6.1.4.1.989.1.16.2.5.4.4.1.3
		asMaxBsSocSsCfgDlBurstAvgAlphaHigh OBJECT-TYPE
			SYNTAX INTEGER (1..1023)
			MAX-ACCESS read-create
			STATUS current
			DESCRIPTION
				"Downlink burst profile parameters for adaptive modulation algorithm.
				Averaging factor alpha high defined in custom TLV 1.1.1 of CNFG-REQ."
			REFERENCE
				"ASMAX Proprietary TLV r9.doc"
			DEFVAL { 32 }
			::= { asMaxBsSocSsCfgEntry 3 }

		
		-- 1.3.6.1.4.1.989.1.16.2.5.4.4.1.4
		asMaxBsSocSsCfgDlBurstSnrProtection OBJECT-TYPE
			SYNTAX INTEGER (0..15)
			UNITS "dB"
			MAX-ACCESS read-create
			STATUS current
			DESCRIPTION
				"Downlink burst profile parameters for adaptive modulation algorithm.
				SNR protection margin defined in custom TLV 1.1.2 of CNFG-REQ."
			REFERENCE
				"ASMAX Proprietary TLV r9.doc"
			DEFVAL { 4 }
			::= { asMaxBsSocSsCfgEntry 4 }

		
		-- 1.3.6.1.4.1.989.1.16.2.5.4.4.1.5
		asMaxBsSocSsCfgDlBurstSnrHysteresis OBJECT-TYPE
			SYNTAX INTEGER (0..15)
			UNITS "dB"
			MAX-ACCESS read-create
			STATUS current
			DESCRIPTION
				"Downlink burst profile parameters for adaptive modulation algorithm.
				SNR hysteresis defined in custom TLV 1.1.2 of CNFG-REQ."
			REFERENCE
				"ASMAX Proprietary TLV r9.doc"
			DEFVAL { 3 }
			::= { asMaxBsSocSsCfgEntry 5 }

		
		-- 1.3.6.1.4.1.989.1.16.2.5.4.4.1.6
		asMaxBsSocSsCfgLanTableMaxSize OBJECT-TYPE
			SYNTAX INTEGER (1..128)
			MAX-ACCESS read-create
			STATUS current
			DESCRIPTION
				"Maximum size of the CPE LAN MAC address table. This object restricts number 
				of host machines connected to the SS LAN.
				The object is defined in TLV 1.2 of CNFG-REQ."
			REFERENCE
				"ASMAX Proprietary TLV r9.doc"
			DEFVAL { 128 }
			::= { asMaxBsSocSsCfgEntry 6 }

		
		-- 1.3.6.1.4.1.989.1.16.2.5.4.4.1.7
		asMaxBsSocSsCfgAllowedBSID OBJECT-TYPE
			SYNTAX WmanIfBsIdType
			MAX-ACCESS read-create
			STATUS current
			DESCRIPTION
				"Test value used to check if SS is allowed to registered on a given 
				BS identified with BSID.
				To allow registration BS BSID binary anded with the value of asMaxBsSocSsCfgAllowedBSIDMask
				should match the value of asMaxBsSocSsCfgAllowedBSID.
				The object is defined in TLV 1.4 of CNFG-REQ."
			REFERENCE
				"ASMAX Proprietary TLV r9.doc"
			DEFVAL { '000000000000'h }
			::= { asMaxBsSocSsCfgEntry 7 }

		
		-- 1.3.6.1.4.1.989.1.16.2.5.4.4.1.8
		asMaxBsSocSsCfgAllowedBSIDMask OBJECT-TYPE
			SYNTAX WmanIfBsIdType
			MAX-ACCESS read-create
			STATUS current
			DESCRIPTION
				"Mask value used to check if SS is allowed to registered on a given 
				BS identified with BSID.
				To allow registration BS BSID binary anded with the value of asMaxBsSocSsCfgAllowedBSIDMask
				should match the value of asMaxBsSocSsCfgAllowedBSID.
				The object is defined in TLV 1.4 of CNFG-REQ."
			REFERENCE
				"ASMAX Proprietary TLV r9.doc"
			DEFVAL { '000000000000'h }
			::= { asMaxBsSocSsCfgEntry 8 }

		
		-- 1.3.6.1.4.1.989.1.16.2.5.4.4.1.9
		asMaxBsSocSsCfgRowStatus OBJECT-TYPE
			SYNTAX RowStatus
			MAX-ACCESS read-create
			STATUS current
			DESCRIPTION
				"Description."
			::= { asMaxBsSocSsCfgEntry 9 }

		
		-- 1.3.6.1.4.1.989.1.16.2.5.4.4.1.10
		asMaxBsSocSsCfgBsidConfigEnabled OBJECT-TYPE
			SYNTAX AsmaxBooleanSwitch
			MAX-ACCESS read-create
			STATUS current
			DESCRIPTION
				"When set to booleanFalse Base Station ignores the configuration 
				of allowed BSID and BSID Mask.
				When set to booleanTrue Base Station sends the configuration 
				of BSID and BSID Mask to SS."
			DEFVAL { booleanFalse }
			::= { asMaxBsSocSsCfgEntry 10 }

		
		-- 1.3.6.1.4.1.989.1.16.2.5.4.4.1.11
		asMaxBsSocSsCfgSubChannelMinWidth OBJECT-TYPE
			SYNTAX INTEGER
				{
				subChannelWidthSixteenth(1),
				subChannelWidthEighth(2),
				subChannelWidthQuarter(4),
				subChannelWidthHalf(8),
				subChannelWidthFull(16)
				}
			MAX-ACCESS read-create
			STATUS obsolete
			DESCRIPTION
				"Indicates the minimum bandwidth that will be granted to the SS 
				for uplink data. Must be 16, 8, 4, 2, or 1, where 16 = full bandwidth 
				and 1 = sixteenth of bandwidth.
				"
			DEFVAL { subChannelWidthFull }
			::= { asMaxBsSocSsCfgEntry 11 }

		
		-- 1.3.6.1.4.1.989.1.16.2.5.4.4.1.12
		asMaxBsSocSsCfgRemoteId OBJECT-TYPE
			SYNTAX INTEGER (0..2147483647)
			MAX-ACCESS read-create
			STATUS current
			DESCRIPTION
				"When AltRemoteIdEnabled, RemoteId id used as the alternate agent 
				remote ID in the reply to  DHCP option 82 request (instead of the SS MacAddress)."
			DEFVAL { 0 }
			::= { asMaxBsSocSsCfgEntry 12 }

		
		-- 1.3.6.1.4.1.989.1.16.2.5.4.5
		asMaxBsSocVlanCfgExtTable OBJECT-TYPE
			SYNTAX SEQUENCE OF AsMaxBsSocVlanCfgExtEntry
			MAX-ACCESS not-accessible
			STATUS current
			DESCRIPTION
				"Table with VLAN specific configuration."
			::= { asMaxBsSocCps 5 }

		
		-- 1.3.6.1.4.1.989.1.16.2.5.4.5.1
		asMaxBsSocVlanCfgExtEntry OBJECT-TYPE
			SYNTAX AsMaxBsSocVlanCfgExtEntry
			MAX-ACCESS not-accessible
			STATUS current
			DESCRIPTION
				"Description."
			INDEX { asDot1qVlanProvId }
			::= { asMaxBsSocVlanCfgExtTable 1 }

		
		AsMaxBsSocVlanCfgExtEntry ::=
			SEQUENCE { 
				asMaxBsSocVlanCfgDhcpRelayAgentMode
					INTEGER,
				asMaxBsSocVlanCfgRowStatus
					RowStatus,
				asMaxBsSocVlanCfgMacFFEnabled
					AsmaxBooleanSwitch,
				asMaxBsSocVlanCfgMacFFIpAddressType
					InetAddressType,
				asMaxBsSocVlanCfgMacFFIpAddress
					InetAddress,
				asMaxBsSocVlanCfgSingleUserEnabled
					AsmaxBooleanSwitch
			 }

		-- 1.3.6.1.4.1.989.1.16.2.5.4.5.1.1
		asMaxBsSocVlanCfgDhcpRelayAgentMode OBJECT-TYPE
			SYNTAX INTEGER
				{
				dhcpRelayModeOff(0),
				dhcpRelayModeOption82Text(1),
				dhcpRelayModeOption82Binary(2)
				}
			MAX-ACCESS read-create
			STATUS current
			DESCRIPTION
				"Defines the mode of the DHCP relay agent (Option 82)."
			DEFVAL { dhcpRelayModeOff }
			::= { asMaxBsSocVlanCfgExtEntry 1 }

		
		-- 1.3.6.1.4.1.989.1.16.2.5.4.5.1.2
		asMaxBsSocVlanCfgRowStatus OBJECT-TYPE
			SYNTAX RowStatus
			MAX-ACCESS read-create
			STATUS current
			DESCRIPTION
				"Description."
			::= { asMaxBsSocVlanCfgExtEntry 2 }

		
		-- 1.3.6.1.4.1.989.1.16.2.5.4.5.1.3
		asMaxBsSocVlanCfgMacFFEnabled OBJECT-TYPE
			SYNTAX AsmaxBooleanSwitch
			MAX-ACCESS read-create
			STATUS current
			DESCRIPTION
				"Enables/disables MAC Forced Forwarding.
				When enabled all uplink traffic from the SSs in this VLAN is forwarded 
				to a specified router - see  asMaxBsSocVlanCfgMacFFIpAddress."
			DEFVAL { booleanFalse }
			::= { asMaxBsSocVlanCfgExtEntry 3 }

		
		-- 1.3.6.1.4.1.989.1.16.2.5.4.5.1.4
		asMaxBsSocVlanCfgMacFFIpAddressType OBJECT-TYPE
			SYNTAX InetAddressType
			MAX-ACCESS read-create
			STATUS current
			DESCRIPTION
				"This specifies the type of IP address for asMaxBsSocVlanCfgMacFFIpAddress.
				Normally IPv4."
			DEFVAL { ipv4 }
			::= { asMaxBsSocVlanCfgExtEntry 4 }

		
		-- 1.3.6.1.4.1.989.1.16.2.5.4.5.1.5
		asMaxBsSocVlanCfgMacFFIpAddress OBJECT-TYPE
			SYNTAX InetAddress
			MAX-ACCESS read-create
			STATUS current
			DESCRIPTION
				"Specifies the IP address of the router that uplink traffic is forwarded 
				to when MAC Forced Forwarding is enabled.
				 
				"
			::= { asMaxBsSocVlanCfgExtEntry 5 }

		
		-- 1.3.6.1.4.1.989.1.16.2.5.4.5.1.6
		asMaxBsSocVlanCfgSingleUserEnabled OBJECT-TYPE
			SYNTAX AsmaxBooleanSwitch
			MAX-ACCESS read-create
			STATUS current
			DESCRIPTION
				"Enables/disables Single-User mode.
				When enabled all uplink traffic from the SSs in this VLAN is not 
				forwarded to another SS but only to the network."
			DEFVAL { booleanFalse }
			::= { asMaxBsSocVlanCfgExtEntry 6 }

		
		-- 1.3.6.1.4.1.989.1.16.2.5.4.6
		asMaxBsSocLicenceTable OBJECT-TYPE
			SYNTAX SEQUENCE OF AsMaxBsSocLicenceEntry
			MAX-ACCESS not-accessible
			STATUS current
			DESCRIPTION
				"Table for both configuring and reporting BS Licence"
			::= { asMaxBsSocCps 6 }

		
		-- 1.3.6.1.4.1.989.1.16.2.5.4.6.1
		asMaxBsSocLicenceEntry OBJECT-TYPE
			SYNTAX AsMaxBsSocLicenceEntry
			MAX-ACCESS not-accessible
			STATUS current
			DESCRIPTION
				"A single row table representing the whole BS."
			INDEX { asMaxBsSocLicenceIndex }
			::= { asMaxBsSocLicenceTable 1 }

		
		AsMaxBsSocLicenceEntry ::=
			SEQUENCE { 
				asMaxBsSocLicenceIndex
					INTEGER,
				asMaxBsSocLicenceCertificate
					OCTET STRING,
				asMaxBsSocLicenceCertCapabilities
					DisplayString
			 }

		-- 1.3.6.1.4.1.989.1.16.2.5.4.6.1.1
		asMaxBsSocLicenceIndex OBJECT-TYPE
			SYNTAX INTEGER (1)
			MAX-ACCESS not-accessible
			STATUS current
			DESCRIPTION
				"Arbitrary Index for a single row table.  Returns 1 "
			::= { asMaxBsSocLicenceEntry 1 }

		
		-- 1.3.6.1.4.1.989.1.16.2.5.4.6.1.2
		asMaxBsSocLicenceCertificate OBJECT-TYPE
			SYNTAX OCTET STRING (SIZE (0..65535))
			MAX-ACCESS read-write
			STATUS current
			DESCRIPTION
				"Certificate defining the encryption features licensed for this BS.
				The licence includes a MAC Address property which defines the Inventory MAC address
				of the BS this licence pertains to."
			DEFVAL { ''b }
			::= { asMaxBsSocLicenceEntry 2 }

		
		-- 1.3.6.1.4.1.989.1.16.2.5.4.6.1.3
		asMaxBsSocLicenceCertCapabilities OBJECT-TYPE
			SYNTAX DisplayString
			MAX-ACCESS read-only
			STATUS current
			DESCRIPTION
				"BS capabilities licenced using object asMaxBsSocLicenceCertificate.
				The capabilites are encoded in clear text ready to display on EMS GUI.
				This field consists of a set of strings, one per capability, separated by white space"
			DEFVAL { ''b }
			::= { asMaxBsSocLicenceEntry 3 }

		
		-- 1.3.6.1.4.1.989.1.16.2.5.5
		asMaxBsSocPhy OBJECT IDENTIFIER ::= { asMaxBSSoc 5 }

		
		-- 1.3.6.1.4.1.989.1.16.2.5.5.1
		asMaxBsSocRfConfigTable OBJECT-TYPE
			SYNTAX SEQUENCE OF AsMaxBsSocRfConfigEntry
			MAX-ACCESS not-accessible
			STATUS current
			DESCRIPTION
				"Groups configuration objects of radio subsystem."
			::= { asMaxBsSocPhy 1 }

		
		-- 1.3.6.1.4.1.989.1.16.2.5.5.1.1
		asMaxBsSocRfConfigEntry OBJECT-TYPE
			SYNTAX AsMaxBsSocRfConfigEntry
			MAX-ACCESS not-accessible
			STATUS current
			DESCRIPTION
				"One row per interface."
			INDEX { ifIndex }
			::= { asMaxBsSocRfConfigTable 1 }

		
		AsMaxBsSocRfConfigEntry ::=
			SEQUENCE { 
				asMaxBsSocRfConfTxPower
					Integer32,
				asMaxBsSocRfConfRxCommandedPower
					INTEGER,
				asMaxBsSocRfConfTxEnabled
					AsmaxBooleanSwitch
			 }

		-- 1.3.6.1.4.1.989.1.16.2.5.5.1.1.1
		asMaxBsSocRfConfTxPower OBJECT-TYPE
			SYNTAX Integer32 (0..160)
			UNITS "0.25 dBm"
			MAX-ACCESS read-write
			STATUS current
			DESCRIPTION
				"Transmitter output level in 0.25 dBm.
				The range is not restricted by this MIB object definition. 
				Instead manager validates teh range against: 
				asMaxBsSocRfStatMinTxPower and asMaxBsSocRfStatMaxTxPower
				
				It is used in calculation of BS DL EIRP as follows:
				EIRP = TxPower + AntennaGain"
			::= { asMaxBsSocRfConfigEntry 1 }

		
		-- 1.3.6.1.4.1.989.1.16.2.5.5.1.1.2
		asMaxBsSocRfConfRxCommandedPower OBJECT-TYPE
			SYNTAX INTEGER (-320..-200)
			UNITS "0.25 dBm"
			MAX-ACCESS read-write
			STATUS current
			DESCRIPTION
				"Uplink commanded power. Sets level at which data portion of SS burst 
				should be received when power control loop is converged.
				(Similar to Rx Level Set Point as defined for ranging in some other BSs.)"
			DEFVAL { -280 }
			::= { asMaxBsSocRfConfigEntry 2 }

		
		-- 1.3.6.1.4.1.989.1.16.2.5.5.1.1.3
		asMaxBsSocRfConfTxEnabled OBJECT-TYPE
			SYNTAX AsmaxBooleanSwitch
			MAX-ACCESS read-write
			STATUS current
			DESCRIPTION
				"Enables/disabled BS transmitter."
			DEFVAL { booleanTrue }
			::= { asMaxBsSocRfConfigEntry 3 }

		
		-- 1.3.6.1.4.1.989.1.16.2.5.5.2
		asMaxBsSocRfStatusTable OBJECT-TYPE
			SYNTAX SEQUENCE OF AsMaxBsSocRfStatusEntry
			MAX-ACCESS not-accessible
			STATUS current
			DESCRIPTION
				"Groups status data for radio subsystem:
				- settings stored in RF EEPROM
				- values achieved as a result of configuration
				- other RF status information"
			::= { asMaxBsSocPhy 2 }

		
		-- 1.3.6.1.4.1.989.1.16.2.5.5.2.1
		asMaxBsSocRfStatusEntry OBJECT-TYPE
			SYNTAX AsMaxBsSocRfStatusEntry
			MAX-ACCESS not-accessible
			STATUS current
			DESCRIPTION
				"One row per interface."
			INDEX { ifIndex }
			::= { asMaxBsSocRfStatusTable 1 }

		
		AsMaxBsSocRfStatusEntry ::=
			SEQUENCE { 
				asMaxBsSocRfStatMinTxPower
					Integer32,
				asMaxBsSocRfStatMaxTxPower
					Integer32,
				asMaxBsSocRfStatTxPowerInd
					Integer32,
				asMaxBsSocRfStatDuplexMode
					INTEGER,
				asMaxBsSocRfStatCurrentDnlkFrequencyInd
					Integer32,
				asMaxBsSocRfStatOldDnlkFrequencyInd
					Integer32
			 }

		-- 1.3.6.1.4.1.989.1.16.2.5.5.2.1.1
		asMaxBsSocRfStatMinTxPower OBJECT-TYPE
			SYNTAX Integer32
			UNITS "0.25 dBm"
			MAX-ACCESS read-only
			STATUS current
			DESCRIPTION
				"Transmitter capable minimum TX power"
			::= { asMaxBsSocRfStatusEntry 1 }

		
		-- 1.3.6.1.4.1.989.1.16.2.5.5.2.1.2
		asMaxBsSocRfStatMaxTxPower OBJECT-TYPE
			SYNTAX Integer32
			UNITS "0.25 dBm"
			MAX-ACCESS read-only
			STATUS current
			DESCRIPTION
				"Transmitter capable maximum TX power"
			::= { asMaxBsSocRfStatusEntry 2 }

		
		-- 1.3.6.1.4.1.989.1.16.2.5.5.2.1.3
		asMaxBsSocRfStatTxPowerInd OBJECT-TYPE
			SYNTAX Integer32
			UNITS "0.25 dBm"
			MAX-ACCESS read-only
			STATUS current
			DESCRIPTION
				"Provides a measurement or an estimate of the transmitted power at the antenna."
			::= { asMaxBsSocRfStatusEntry 3 }

		
		-- 1.3.6.1.4.1.989.1.16.2.5.5.2.1.4
		asMaxBsSocRfStatDuplexMode OBJECT-TYPE
			SYNTAX INTEGER
				{
				duplexFdd(0),
				duplexTdd(1)
				}
			MAX-ACCESS read-only
			STATUS current
			DESCRIPTION
				"Description."
			::= { asMaxBsSocRfStatusEntry 4 }

		
		-- 1.3.6.1.4.1.989.1.16.2.5.5.2.1.5
		asMaxBsSocRfStatCurrentDnlkFrequencyInd OBJECT-TYPE
			SYNTAX Integer32
			UNITS "kHz"
			MAX-ACCESS read-only
			STATUS current
			DESCRIPTION
				"Reports currently used downlink frequency. This may differ from frequency configured
				using object wmanIfBsOfdmDownlinkCenterFreq when DFS (Dynamic Frequency Selection) is turned on."
			::= { asMaxBsSocRfStatusEntry 5 }

		
		-- 1.3.6.1.4.1.989.1.16.2.5.5.2.1.6
		asMaxBsSocRfStatOldDnlkFrequencyInd OBJECT-TYPE
			SYNTAX Integer32
			UNITS "kHz"
			MAX-ACCESS read-only
			STATUS current
			DESCRIPTION
				"Reports previously used downlink frequency. This may differ from currently used frequency reported
				using object asMaxBsSocRfStatCurrentDnlkFrequencyInd when DFS (Dynamic Frequency Selection) is turned on."
			::= { asMaxBsSocRfStatusEntry 6 }

		
		-- 1.3.6.1.4.1.989.1.16.2.5.5.3
		asMaxBsSocDfsCfgTable OBJECT-TYPE
			SYNTAX SEQUENCE OF AsMaxBsSocDfsCfgEntry
			MAX-ACCESS not-accessible
			STATUS current
			DESCRIPTION
				"Defines configuration for Dynamic Frequency Switching."
			::= { asMaxBsSocPhy 3 }

		
		-- 1.3.6.1.4.1.989.1.16.2.5.5.3.1
		asMaxBsSocDfsCfgEntry OBJECT-TYPE
			SYNTAX AsMaxBsSocDfsCfgEntry
			MAX-ACCESS not-accessible
			STATUS current
			DESCRIPTION
				"Description."
			INDEX { ifIndex }
			::= { asMaxBsSocDfsCfgTable 1 }

		
		AsMaxBsSocDfsCfgEntry ::=
			SEQUENCE { 
				asMaxBsSocDfsEnabled
					AsmaxBooleanSwitch,
				asMaxBsSocDfsAvailabilityCheckEnabled
					AsmaxBooleanSwitch,
				asMaxBsSocDfsInServiceCheckEnabled
					AsmaxBooleanSwitch,
				asMaxBsSocDfsIMEnabled
					AsmaxBooleanSwitch,
				asMaxBsSocDfsStandardType
					INTEGER,
				asMaxBsSocDfsChannelListScheme
					INTEGER,
				asMaxBsSocDfsChannelMap
					AsmaxLeChannelMap,
				asMaxBsSocDfsPowerThreshold
					Integer32,
				asMaxBsSocDfsTxPowerLimitCfgEnabled
					AsmaxBooleanSwitch,
				asMaxBsSocDfsTxPowerLimit
					Integer32,
				asMaxBsSocDfsNumSssToSwitchChannel
					Integer32,
				asMaxBsSocDfsMeasurementBw
					Integer32,
				asMaxBsSocDfsMinNumberPulses
					Integer32,
				asMaxBsSocDfsDetectSensibility
					Integer32,
				asMaxBsSocDfsMinNumberOfBursts
					Integer32,
				asMaxBsSocCccEnabled
					AsmaxBooleanSwitch,
				asMaxBsSocCccMaxPowerThreshold
					Integer32
			 }

		-- 1.3.6.1.4.1.989.1.16.2.5.5.3.1.1
		asMaxBsSocDfsEnabled OBJECT-TYPE
			SYNTAX AsmaxBooleanSwitch
			MAX-ACCESS read-write
			STATUS current
			DESCRIPTION
				"General DFS enable switch."
			DEFVAL { booleanFalse }
			::= { asMaxBsSocDfsCfgEntry 1 }

		
		-- 1.3.6.1.4.1.989.1.16.2.5.5.3.1.2
		asMaxBsSocDfsAvailabilityCheckEnabled OBJECT-TYPE
			SYNTAX AsmaxBooleanSwitch
			MAX-ACCESS read-write
			STATUS current
			DESCRIPTION
				"Availability check switch."
			DEFVAL { booleanFalse }
			::= { asMaxBsSocDfsCfgEntry 2 }

		
		-- 1.3.6.1.4.1.989.1.16.2.5.5.3.1.3
		asMaxBsSocDfsInServiceCheckEnabled OBJECT-TYPE
			SYNTAX AsmaxBooleanSwitch
			MAX-ACCESS read-write
			STATUS current
			DESCRIPTION
				"In-service check switch."
			DEFVAL { booleanFalse }
			::= { asMaxBsSocDfsCfgEntry 3 }

		
		-- 1.3.6.1.4.1.989.1.16.2.5.5.3.1.4
		asMaxBsSocDfsIMEnabled OBJECT-TYPE
			SYNTAX AsmaxBooleanSwitch
			MAX-ACCESS read-write
			STATUS current
			DESCRIPTION
				"Interface Monitoring (IM) switch."
			DEFVAL { booleanFalse }
			::= { asMaxBsSocDfsCfgEntry 4 }

		
		-- 1.3.6.1.4.1.989.1.16.2.5.5.3.1.5
		asMaxBsSocDfsStandardType OBJECT-TYPE
			SYNTAX INTEGER
				{
				dfsStandardTypeETSI(1),
				dfsStandardTypeFCC(2)
				}
			MAX-ACCESS read-write
			STATUS current
			DESCRIPTION
				"The standard that defined the radar type, detection threshold. "
			DEFVAL { dfsStandardTypeETSI }
			::= { asMaxBsSocDfsCfgEntry 5 }

		
		-- 1.3.6.1.4.1.989.1.16.2.5.5.3.1.6
		asMaxBsSocDfsChannelListScheme OBJECT-TYPE
			SYNTAX INTEGER
				{
				channelListUsaWimaxHuman(1),
				channelListEuropeWimaxHuman(2),
				channelListEtsiFcc(3),
				channelList5MhzSpacing(4),
				channelList2Dot5MhzSpacing(5)
				}
			MAX-ACCESS read-write
			STATUS current
			DESCRIPTION
				"Channel list scheme used to calculate center frequency from the channel number.
				This is defiend either by standard or by BS capabilities."
			::= { asMaxBsSocDfsCfgEntry 6 }

		
		-- 1.3.6.1.4.1.989.1.16.2.5.5.3.1.7
		asMaxBsSocDfsChannelMap OBJECT-TYPE
			SYNTAX AsmaxLeChannelMap
			MAX-ACCESS read-write
			STATUS current
			DESCRIPTION
				"Defines the binary map of all the channels included in DFS algorithm.
				When bit in the map is set to 1 the channel ins included otherwise it is excluded."
			DEFVAL { '00000000000000000000000000000000000000000000000000'h }
			::= { asMaxBsSocDfsCfgEntry 7 }

		
		-- 1.3.6.1.4.1.989.1.16.2.5.5.3.1.8
		asMaxBsSocDfsPowerThreshold OBJECT-TYPE
			SYNTAX Integer32 (0..80)
			UNITS "dBm"
			MAX-ACCESS read-write
			STATUS current
			DESCRIPTION
				"Conducted power threshold, which includes the antenna gain, 
				i.e. the BS should treated the antenna gain as 0dBi."
			DEFVAL { 53 }
			::= { asMaxBsSocDfsCfgEntry 8 }

		
		-- 1.3.6.1.4.1.989.1.16.2.5.5.3.1.9
		asMaxBsSocDfsTxPowerLimitCfgEnabled OBJECT-TYPE
			SYNTAX AsmaxBooleanSwitch
			MAX-ACCESS read-write
			STATUS current
			DESCRIPTION
				"Switch controlling the source of the transmitted power limit.
				When enabled (booleanTrue) the limit can be configured 
				with object asMaxBsSocDfsTxPowerLimit.
				When disabled (booleanFalse) the limit cannot be configured
				and BS has to use factory defaults for limit."
			DEFVAL { booleanFalse }
			::= { asMaxBsSocDfsCfgEntry 9 }

		
		-- 1.3.6.1.4.1.989.1.16.2.5.5.3.1.10
		asMaxBsSocDfsTxPowerLimit OBJECT-TYPE
			SYNTAX Integer32 (0..35)
			UNITS "dBm"
			MAX-ACCESS read-write
			STATUS current
			DESCRIPTION
				"The max Tx power allowed. Only effective when config enabled 
				by object asMaxBsSocDfsTxPowerLimitCfgEnabled."
			DEFVAL { 17 }
			::= { asMaxBsSocDfsCfgEntry 10 }

		
		-- 1.3.6.1.4.1.989.1.16.2.5.5.3.1.11
		asMaxBsSocDfsNumSssToSwitchChannel OBJECT-TYPE
			SYNTAX Integer32 (0..50)
			UNITS "%"
			MAX-ACCESS read-write
			STATUS current
			DESCRIPTION
				"Number of SS (in percents of the total population), which detect radar 
				before BS switches to a new channel (for 5min period)."
			DEFVAL { 10 }
			::= { asMaxBsSocDfsCfgEntry 11 }

		
		-- 1.3.6.1.4.1.989.1.16.2.5.5.3.1.12
		asMaxBsSocDfsMeasurementBw OBJECT-TYPE
			SYNTAX Integer32 (15..50)
			UNITS "%"
			MAX-ACCESS read-write
			STATUS current
			DESCRIPTION
				"Percentage of channel bandwith used for DFS measurements.
				Increment in 5% steps of channel BW which begins at 15%."
			DEFVAL { 20 }
			::= { asMaxBsSocDfsCfgEntry 12 }

		
		-- 1.3.6.1.4.1.989.1.16.2.5.5.3.1.13
		asMaxBsSocDfsMinNumberPulses OBJECT-TYPE
			SYNTAX Integer32 (2..10)
			MAX-ACCESS read-write
			STATUS current
			DESCRIPTION
				"The minimum number of Pulses for detection declaration."
			DEFVAL { 4 }
			::= { asMaxBsSocDfsCfgEntry 13 }

		
		-- 1.3.6.1.4.1.989.1.16.2.5.5.3.1.14
		asMaxBsSocDfsDetectSensibility OBJECT-TYPE
			SYNTAX Integer32 (0..100)
			UNITS "%"
			MAX-ACCESS read-write
			STATUS current
			DESCRIPTION
				"Radar detection minimum likelihood, define the ratio of radar signal 
				to the total detected signal."
			DEFVAL { 90 }
			::= { asMaxBsSocDfsCfgEntry 14 }

		
		-- 1.3.6.1.4.1.989.1.16.2.5.5.3.1.15
		asMaxBsSocDfsMinNumberOfBursts OBJECT-TYPE
			SYNTAX Integer32 (1..8)
			MAX-ACCESS read-write
			STATUS current
			DESCRIPTION
				"The minimum number of burst for detection declaration."
			DEFVAL { 2 }
			::= { asMaxBsSocDfsCfgEntry 15 }

		
		-- 1.3.6.1.4.1.989.1.16.2.5.5.3.1.16
		asMaxBsSocCccEnabled OBJECT-TYPE
			SYNTAX AsmaxBooleanSwitch
			MAX-ACCESS read-write
			STATUS current
			DESCRIPTION
				"Clearest Channel Choice (CCC) switch."
			DEFVAL { booleanFalse }
			::= { asMaxBsSocDfsCfgEntry 16 }

		
		-- 1.3.6.1.4.1.989.1.16.2.5.5.3.1.17
		asMaxBsSocCccMaxPowerThreshold OBJECT-TYPE
			SYNTAX Integer32 (-90..-75)
			UNITS "dBm"
			MAX-ACCESS read-write
			STATUS current
			DESCRIPTION
				"Maximum power threshold for Cleares Channel Choice algorithm."
			DEFVAL { -78 }
			::= { asMaxBsSocDfsCfgEntry 17 }

		
	
	END

--
-- AIRSPAN-BS-SOC-MIB.mib
--
