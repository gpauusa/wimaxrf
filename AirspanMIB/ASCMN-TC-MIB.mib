--
-- ASCMN-TC-MIB.mib
-- MIB generated by MG-SOFT Visual MIB Builder 2010 Version 8.0  Build 400
-- Monday, March 21, 2011 at 16:53:55
--

    ASCMN-TC-MIB DEFINITIONS ::= BEGIN
 
        IMPORTS
            asCmn            
                FROM AIRSPAN-PRODUCTS-MIB            
            ifIndex            
                FROM IF-MIB            
            MODULE-IDENTITY            
                FROM SNMPv2-SMI            
            TEXTUAL-CONVENTION            
                FROM SNMPv2-TC;
    
    
        -- 1.3.6.1.4.1.989.1.22.5
        asCmnTc MODULE-IDENTITY 
            LAST-UPDATED "201103210941Z"		-- March 21, 2011 at 09:41 GMT
            ORGANIZATION 
                "Airspan Communications Ltd"
            CONTACT-INFO 
                "kdudzins@airspan.com"
            DESCRIPTION 
                "Propriatory MIB defining Airspan specific Textual Conventions."
            REVISION "201103150941Z"		-- March 15, 2011 at 09:41 GMT
            DESCRIPTION 
                "Pre-Draft 1:
                - initial version "
            REVISION "201103210941Z"		-- March 21, 2011 at 09:41 GMT
            DESCRIPTION 
                "Pre-Draft 2:
                - added textual Convention AsCmnTcRunningStatus"
            ::= { asCmn 5 }

        
    
--
-- Textual conventions
--
    
        AsCmnTcBooleanSwitch ::= TEXTUAL-CONVENTION
            STATUS current
            DESCRIPTION 
                "Description."
            SYNTAX INTEGER
                {
                booleanFalse(0),
                booleanTrue(1)
                }

        AsCmnTcOperationalStatus ::= TEXTUAL-CONVENTION
            STATUS current
            DESCRIPTION 
                "The possible operational status for the stack."
            SYNTAX INTEGER
                {
                operationalStatusNone(0),
                operationalStatusInService(1),
                operationalStatusOutOfService(2)
                }

        AsCmnTcResetCmd ::= TEXTUAL-CONVENTION
            STATUS current
            DESCRIPTION 
                "The possible reset command values for the stack."
            SYNTAX INTEGER
                {
                resetCmdIdle(0),
                resetCmdAll(1)
                }

        AsCmnTcRunningStatus ::= TEXTUAL-CONVENTION
            STATUS current
            DESCRIPTION 
                "The possible running status for the stack."
            SYNTAX INTEGER
                {
                runningStatusNone(0),
                runningStatusStarting(1),
                runningStatusRunning(2),
                runningStatusFailed(3)
                }

        AsCmnTcSoftwareType ::= TEXTUAL-CONVENTION
            STATUS current
            DESCRIPTION 
                "Defines the type of image or image package to install. 
                Different types may require different implementation.
                Some types are implicitly linked to specific type of hardware 
                e.g. swTypeBsdu will be used by BSDU.
                "
            SYNTAX INTEGER
                {
                swTypeOs(1),
                swTypeApp(2),
                swTypeScrt(3),
                swTypeMcrt(4),
                swTypeCombinedMicromax(5),
                swTypeCombinedHipermax(6),
                swTypeSecurityCertificates(7),
                swTypeSocObsoleted(11),
                swTypeBsdu(12),
                swTypeBoot(13),
                swTypeCombinedBsMobile(14),
                swTypeDtoE(15),
                swTypeEtoD(16),
                swTypeAirSynergy(17)
                }

    
--
-- Node definitions
--
    
    
    END

--
-- ASCMN-TC-MIB.mib
--
