--
-- AIRSPAN-BRIDGE-MIB.mib
-- MIB generated by MG-SOFT Visual MIB Builder Version 5.0  Build 250
-- Wednesday, February 15, 2006 at 14:33:00
--

-- *****************************************************************
-- AIRSPAN_BRIDGE-MIB.mib:  Bridge MIB file
-- 
-- November 2005, Kurshid Zaman
-- 
-- Copyright (c) 2005 by Airspan Inc.
-- All rights reserved.
-- 
-- *****************************************************************
-- 
-- This mib was extracted from RFC 4188                        

	AIRSPAN-BRIDGE-MIB DEFINITIONS ::= BEGIN
 
		IMPORTS
			asMaxMisc			
				FROM AIRSPAN-PRODUCTS-MIB			
			InterfaceIndex			
				FROM IF-MIB			
			Integer32, OBJECT-TYPE, MODULE-IDENTITY			
				FROM SNMPv2-SMI			
			MacAddress			
				FROM SNMPv2-TC;
	
	
		-- 1.3.6.1.4.1.989.1.16.5.1
		asMaxBridge MODULE-IDENTITY 
			LAST-UPDATED "200602151423Z"		-- February 15, 2006 at 14:23 GMT
			ORGANIZATION 
				"Airspan"
			CONTACT-INFO 
				"Contact-info."
			DESCRIPTION 
				"Airspan specific simple bridge MIB based on RFC4188."
			REVISION "200602151423Z"		-- February 15, 2006 at 14:23 GMT
			DESCRIPTION 
				"Draft 2
				- moved to private Airspan tree (names changed)
				- used imported MacAddress TC
				- INTEGER syntax changed to strongly sized Integer32
				- InterfaceIndex TC used for port IfIndex
				"
			REVISION "200511231116Z"		-- November 23, 2005 at 11:16 GMT
			DESCRIPTION 
				"Draft 1.
				-Introduced MIB module AIRSPAN-BRIDGE-MIB
				 "
			::= { asMaxMisc 1 }

		
	
	
--
-- Node definitions
--
	
--  Node definitions
-- 
		-- 1.3.6.1.4.1.989.1.16.5.1.1
		asMaxDot1dBase OBJECT IDENTIFIER ::= { asMaxBridge 1 }

		
--    The Generic Bridge Port Table
		-- 1.3.6.1.4.1.989.1.16.5.1.1.4
		asMaxDot1dBasePortTable OBJECT-TYPE
			SYNTAX SEQUENCE OF AsMaxDot1dBasePortEntry
			MAX-ACCESS not-accessible
			STATUS current
			DESCRIPTION
				"A table that contains generic information about
				every port that is associated with this bridge.
				Transparent, source-route, and srt ports are
				included."
			::= { asMaxDot1dBase 4 }

		
		-- 1.3.6.1.4.1.989.1.16.5.1.1.4.1
		asMaxDot1dBasePortEntry OBJECT-TYPE
			SYNTAX AsMaxDot1dBasePortEntry
			MAX-ACCESS not-accessible
			STATUS current
			DESCRIPTION
				"A list of information for each port of the
				bridge."
			REFERENCE
				"IEEE 802.1D-1998"
			INDEX { asMaxDot1dBasePort }
			::= { asMaxDot1dBasePortTable 1 }

		
		AsMaxDot1dBasePortEntry ::=
			SEQUENCE { 
				asMaxDot1dBasePort
					Integer32,
				asMaxDot1dBasePortIfIndex
					InterfaceIndex,
				asMaxDot1dBasePortCircuit
					MacAddress
			 }

		-- 1.3.6.1.4.1.989.1.16.5.1.1.4.1.1
		asMaxDot1dBasePort OBJECT-TYPE
			SYNTAX Integer32 (1..65535)
			MAX-ACCESS read-only
			STATUS current
			DESCRIPTION
				"The port number of the port for which this entry
				contains bridge management information."
			::= { asMaxDot1dBasePortEntry 1 }

		
		-- 1.3.6.1.4.1.989.1.16.5.1.1.4.1.2
		asMaxDot1dBasePortIfIndex OBJECT-TYPE
			SYNTAX InterfaceIndex
			MAX-ACCESS read-only
			STATUS current
			DESCRIPTION
				"The value of the instance of the ifIndex object,
				defined in MIB-II, for the interface corresponding
				to this port."
			::= { asMaxDot1dBasePortEntry 2 }

		
		-- 1.3.6.1.4.1.989.1.16.5.1.1.4.1.3
		asMaxDot1dBasePortCircuit OBJECT-TYPE
			SYNTAX MacAddress
			MAX-ACCESS read-only
			STATUS current
			DESCRIPTION
				"For a port which (potentially) has the same value
				of asMaxDot1dBasePortIfIndex as another port on the
				same bridge, this object contains the name of an
				object instance unique to this port.  For example,
				in the case where multiple ports correspond one-
				to-one with multiple X.25 virtual circuits, this
				value might identify an (e.g., the first) object
				instance associated with the X.25 virtual circuit
				corresponding to this port.
				
				For a port which has a unique value of
				asMaxDot1dBasePortIfIndex, this object can have the
				value { 0 0 }."
			::= { asMaxDot1dBasePortEntry 3 }

		
		-- 1.3.6.1.4.1.989.1.16.5.1.2
		asMaxDot1dTp OBJECT IDENTIFIER ::= { asMaxBridge 2 }

		
--  the asMaxDot1dTp group
-- Implementation of the asMaxDot1dTp group is optional.  It is
-- implemented by those bridges that support the transparent
-- bridging mode.  A transparent or SRT bridge will implement
-- this group.
--  The Forwarding Database for Transparent Bridges
		-- 1.3.6.1.4.1.989.1.16.5.1.2.3
		asMaxDot1dTpFdbTable OBJECT-TYPE
			SYNTAX SEQUENCE OF AsMaxDot1dTpFdbEntry
			MAX-ACCESS not-accessible
			STATUS current
			DESCRIPTION
				"A table that contains information about unicast
				entries for which the bridge has forwarding and/or
				filtering information.  This information is used
				by the transparent bridging function in
				determining how to propagate a received frame."
			::= { asMaxDot1dTp 3 }

		
		-- 1.3.6.1.4.1.989.1.16.5.1.2.3.1
		asMaxDot1dTpFdbEntry OBJECT-TYPE
			SYNTAX AsMaxDot1dTpFdbEntry
			MAX-ACCESS not-accessible
			STATUS current
			DESCRIPTION
				"Information about a specific unicast MAC address
				for which the bridge has some forwarding and/or
				filtering information."
			INDEX { asMaxDot1dTpFdbAddress }
			::= { asMaxDot1dTpFdbTable 1 }

		
		AsMaxDot1dTpFdbEntry ::=
			SEQUENCE { 
				asMaxDot1dTpFdbAddress
					MacAddress,
				asMaxDot1dTpFdbPort
					Integer32,
				asMaxDot1dTpFdbStatus
					INTEGER
			 }

		-- 1.3.6.1.4.1.989.1.16.5.1.2.3.1.1
		asMaxDot1dTpFdbAddress OBJECT-TYPE
			SYNTAX MacAddress
			MAX-ACCESS read-only
			STATUS current
			DESCRIPTION
				"A unicast MAC address for which the bridge has
				forwarding and/or filtering information."
			REFERENCE
				"IEEE 802.1D-1998: Clause 7.9.1, 7.9.2"
			::= { asMaxDot1dTpFdbEntry 1 }

		
		-- 1.3.6.1.4.1.989.1.16.5.1.2.3.1.2
		asMaxDot1dTpFdbPort OBJECT-TYPE
			SYNTAX Integer32
			MAX-ACCESS read-only
			STATUS current
			DESCRIPTION
				"Either the value '0', or the port number of the
				port on which a frame having a source address
				equal to the value of the corresponding instance
				of asMaxDot1dTpFdbAddress has been seen.  A value of
				'0' indicates that the port number has not been
				learned but that the bridge does have some
				forwarding/filtering information about this
				address (e.g. in the asMaxDot1dStaticTable).
				Implementors are encouraged to assign the port
				value to this object whenever it is learned even
				for addresses for which the corresponding value of
				asMaxDot1dTpFdbStatus is not learned(3)."
			::= { asMaxDot1dTpFdbEntry 2 }

		
		-- 1.3.6.1.4.1.989.1.16.5.1.2.3.1.3
		asMaxDot1dTpFdbStatus OBJECT-TYPE
			SYNTAX INTEGER
				{
				other(1),
				invalid(2),
				learned(3),
				self(4),
				mgmt(5)
				}
			MAX-ACCESS read-only
			STATUS current
			DESCRIPTION
				"The status of this entry.  The meanings of the
				values are:
				
				  other(1)   : none of the following.  This would
				               include the case where some other
				               MIB object (not the corresponding
				               instance of asMaxDot1dTpFdbPort, nor an
				               entry in the asMaxDot1dStaticTable) is
				               being used to determine if and how
				               frames addressed to the value of
				               the corresponding instance of
				               asMaxDot1dTpFdbAddress are being
				               forwarded.
				
				  invalid(2) : this entry is not longer valid
				               (e.g., it was learned but has since
				               aged-out), but has not yet been
				               flushed from the table.
				
				  learned(3) : the value of the corresponding
				               instance of asMaxDot1dTpFdbPort was
				               learned, and is being used.
				
				  self(4)    : the value of the corresponding
				               instance of asMaxDot1dTpFdbAddress
				               represents one of the bridge's
				               addresses.  The corresponding
				               instance of asMaxDot1dTpFdbPort
				               indicates which of the bridge's
				               ports has this address.
				
				  mgmt(5)    : the value of the corresponding
				               instance of asMaxDot1dTpFdbAddress is
				               also the value of an existing
				               instance of asMaxDot1dStaticAddress."
			::= { asMaxDot1dTpFdbEntry 3 }

		
	
	END

--
-- AIRSPAN-BRIDGE-MIB.mib
--
