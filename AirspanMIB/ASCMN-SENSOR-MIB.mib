--
-- ASCMN-SENSOR-MIB.mib
-- MIB generated by MG-SOFT Visual MIB Builder 2010 Version 8.0  Build 400
-- Wednesday, March 16, 2011 at 17:12:14
--

	ASCMN-SENSOR-MIB DEFINITIONS ::= BEGIN
 
		IMPORTS
			asCmn			
				FROM AIRSPAN-PRODUCTS-MIB			
			AsCmnTcBooleanSwitch			
				FROM ASCMN-TC-MIB			
			ifIndex			
				FROM IF-MIB			
			OBJECT-GROUP, MODULE-COMPLIANCE, NOTIFICATION-GROUP			
				FROM SNMPv2-CONF			
			OBJECT-TYPE, MODULE-IDENTITY, NOTIFICATION-TYPE			
				FROM SNMPv2-SMI			
			DisplayString			
				FROM SNMPv2-TC;
	
	
		-- 1.3.6.1.4.1.989.1.22.3
		asCmnSensor MODULE-IDENTITY 
			LAST-UPDATED "201103162241Z"		-- March 16, 2011 at 22:41 GMT
			ORGANIZATION 
				"Airspan Communications Ltd"
			CONTACT-INFO 
				"kdudzins@airspan.com"
			DESCRIPTION 
				"Propriatory MIB for common sensor reporting and related alarms on Airspan platforms."
			REVISION "201103150941Z"		-- March 15, 2011 at 09:41 GMT
			DESCRIPTION 
				"Pre-Draft 1:
				- initial version "
			REVISION "201103162241Z"		-- March 16, 2011 at 22:41 GMT
			DESCRIPTION 
			"Pre-Draft 2:
				- updated syntax - replaced INTEGER with Integer32 in places"
            ::= { asCmn 3 }

		
	
	
--
-- Node definitions
--
	
		-- 1.3.6.1.4.1.989.1.22.3.1
		asCmnSensorConformance OBJECT IDENTIFIER ::= { asCmnSensor 1 }

		
--  this module
		-- 1.3.6.1.4.1.989.1.22.3.1.1
		asCmnSensorCompliance MODULE-COMPLIANCE
			STATUS current
			DESCRIPTION 
				"Description."
			MODULE -- this module
				MANDATORY-GROUPS { asCmnSensorObjectGroup }
			::= { asCmnSensorConformance 1 }

		
		-- 1.3.6.1.4.1.989.1.22.3.1.2
		asCmnSensorObjectGroup OBJECT-GROUP
			OBJECTS { asCmnSensorTemperatureChangeTrapEnabled, asCmnSensorDcVoltageTrapEnabled, asCmnSensorTemperatureStatus, asCmnSensorTemperatureStatusInfo, asCmnSensorDcVoltageStatus, 
				asCmnSensorDcVoltageStatusInfo, asCmnSensorTempMonInventoryItem, asCmnSensorTempMonSensorName, asCmnSensorTempMonValue, asCmnSensorTempMonStatus, 
				asCmnSensorDcVoltageMonInventoryItem, asCmnSensorDcVoltageMonSensorName, asCmnSensorDcVoltageMonValue, asCmnSensorDcVoltageMonStatus }
			STATUS current
			DESCRIPTION 
				"Description."
			::= { asCmnSensorConformance 2 }

		
		-- 1.3.6.1.4.1.989.1.22.3.1.3
		asCmnSensorNotificationsGroup NOTIFICATION-GROUP
			NOTIFICATIONS { asCmnSensorTemperatureChangeTrap, asCmnSensorDcVoltageTrap }
			STATUS current
			DESCRIPTION 
				"Description."
			::= { asCmnSensorConformance 3 }

		
		-- 1.3.6.1.4.1.989.1.22.3.2
		asCmnSensorNotifications OBJECT IDENTIFIER ::= { asCmnSensor 2 }

		
		-- 1.3.6.1.4.1.989.1.22.3.2.0
		asCmnSensorTrapPrefix OBJECT IDENTIFIER ::= { asCmnSensorNotifications 0 }

		
		-- 1.3.6.1.4.1.989.1.22.3.2.0.1
		asCmnSensorTemperatureChangeTrap NOTIFICATION-TYPE
			OBJECTS { asCmnSensorTemperatureStatus, asCmnSensorTemperatureStatusInfo }
			STATUS current
			DESCRIPTION 
				"The trap is sent by the agent when:
				- One or more sensors enters an abnormal temperature range (alarm raise)
				- All the sensors return to a normal temperature (alarm cleared). 
				The reason for the trap is defined in its status object. The details of which sensor shows abnormal temperature
				are reported in the asCmnSensorTemperatureMonitorTable. The summary of the reason can be reported
				in the trap StatusInfo object.
				Normally only one trap is sent when the first sensor goes out of the normal temperature range.
				Subsequent changes in the number of sensors showing abnormal temperature do not required 
				another trap, however the corresponding object in the asCmnSensorTrapStatusTable should be updated on every change.
				Default severity: Major"
			::= { asCmnSensorTrapPrefix 1 }

		
		-- 1.3.6.1.4.1.989.1.22.3.2.0.2
		asCmnSensorDcVoltageTrap NOTIFICATION-TYPE
			OBJECTS { asCmnSensorDcVoltageStatus, asCmnSensorDcVoltageStatusInfo }
			STATUS current
			DESCRIPTION 
				"The trap is sent by the agent when:
				- One or more sensors enters an abnormal DC voltage range (alarm raise)
				- All the sensors return to a nominal DC voltage range (alarm cleared)
				The reason for the trap is defined in its status object. The details of which sensor shows abnormal DC voltage
				are reported in the asCmnSensorDcVoltageMonitorTable. The summary of the reason can be reported
				in the trap StatusInfo object.
				Normally only one trap is sent when the first sensor goes out of the normal DC voltage range.
				Subsequent changes in the number of sensors showing DC voltage out of range do not require 
				another trap, however the corresponding object in the asCmnSensorTrapStatusTable should be updated on every change.
				Default severity: Major"
			::= { asCmnSensorTrapPrefix 2 }

		
		-- 1.3.6.1.4.1.989.1.22.3.2.1
		asCmnSensorTrapControlTable OBJECT-TYPE
			SYNTAX SEQUENCE OF AsCmnSensorTrapControlEntry
			MAX-ACCESS not-accessible
			STATUS current
			DESCRIPTION
				"Description."
			::= { asCmnSensorNotifications 1 }

		
		-- 1.3.6.1.4.1.989.1.22.3.2.1.1
		asCmnSensorTrapControlEntry OBJECT-TYPE
			SYNTAX AsCmnSensorTrapControlEntry
			MAX-ACCESS not-accessible
			STATUS current
			DESCRIPTION
				"Single row."
			INDEX { asCmnSensorTrapControlIndex }
			::= { asCmnSensorTrapControlTable 1 }

		
		AsCmnSensorTrapControlEntry ::=
			SEQUENCE { 
				asCmnSensorTrapControlIndex
					Integer32,
				asCmnSensorTemperatureChangeTrapEnabled
					AsCmnTcBooleanSwitch,
				asCmnSensorDcVoltageTrapEnabled
					AsCmnTcBooleanSwitch
			 }

		-- 1.3.6.1.4.1.989.1.22.3.2.1.1.1
		asCmnSensorTrapControlIndex OBJECT-TYPE
			SYNTAX Integer32 (1)
			MAX-ACCESS not-accessible
			STATUS current
			DESCRIPTION
				"Arbitrary index - one row only."
			::= { asCmnSensorTrapControlEntry 1 }

		
		-- 1.3.6.1.4.1.989.1.22.3.2.1.1.2
		asCmnSensorTemperatureChangeTrapEnabled OBJECT-TYPE
			SYNTAX AsCmnTcBooleanSwitch
			MAX-ACCESS read-write
			STATUS current
			DESCRIPTION
				"Enables/disables TemperatureChangeTrap"
			DEFVAL { booleanFalse }
			::= { asCmnSensorTrapControlEntry 2 }

		
		-- 1.3.6.1.4.1.989.1.22.3.2.1.1.3
		asCmnSensorDcVoltageTrapEnabled OBJECT-TYPE
			SYNTAX AsCmnTcBooleanSwitch
			MAX-ACCESS read-write
			STATUS current
			DESCRIPTION
				"Enables/disables Dc Voltage Trap"
			DEFVAL { booleanFalse }
			::= { asCmnSensorTrapControlEntry 3 }

		
		-- 1.3.6.1.4.1.989.1.22.3.2.2
		asCmnSensorTrapStatusTable OBJECT-TYPE
			SYNTAX SEQUENCE OF AsCmnSensorTrapStatusEntry
			MAX-ACCESS not-accessible
			STATUS current
			DESCRIPTION
				"Reports current status of objects associated with traps. The table is designed for the single
				instance traps i.e. the table has only one row showing the status of all possible single instance traps
				defined in the system."
			::= { asCmnSensorNotifications 2 }

		
		-- 1.3.6.1.4.1.989.1.22.3.2.2.1
		asCmnSensorTrapStatusEntry OBJECT-TYPE
			SYNTAX AsCmnSensorTrapStatusEntry
			MAX-ACCESS not-accessible
			STATUS current
			DESCRIPTION
				"Single row."
			INDEX { asCmnSensorTrapStatusIndex }
			::= { asCmnSensorTrapStatusTable 1 }

		
		AsCmnSensorTrapStatusEntry ::=
			SEQUENCE { 
				asCmnSensorTrapStatusIndex
					Integer32,
				asCmnSensorTemperatureStatus
					INTEGER,
				asCmnSensorTemperatureStatusInfo
					DisplayString,
				asCmnSensorDcVoltageStatus
					INTEGER,
				asCmnSensorDcVoltageStatusInfo
					DisplayString
			 }

		-- 1.3.6.1.4.1.989.1.22.3.2.2.1.1
		asCmnSensorTrapStatusIndex OBJECT-TYPE
			SYNTAX Integer32 (1)
			MAX-ACCESS not-accessible
			STATUS current
			DESCRIPTION
				"Arbitrary index - one row only."
			::= { asCmnSensorTrapStatusEntry 1 }

		
		-- 1.3.6.1.4.1.989.1.22.3.2.2.1.2
		asCmnSensorTemperatureStatus OBJECT-TYPE
			SYNTAX INTEGER
				{
				normalTemperature(0),
				lowTempReached(1),
				highTempReached(2),
				abnormalTemperature(3)
				}
			MAX-ACCESS read-only
			STATUS current
			DESCRIPTION
				"Reports current temperature alarm trap status as defined in the value list.
				The status reports overall temperature condition of the system based on the reading 
				from multiple sensors. The status values have the following meaning:
				- normalTemperature: all the sensors in the system show the temperature with normal range
				- lowTempReached: one or more sensors show temperature below the lower limit
				- highTempReached: one or more sensors show the temperature above the higher limit
				- abnormalTemperature: one or more sensors show the temperature outside the normal range (too low or too high)"
			::= { asCmnSensorTrapStatusEntry 2 }

		
		-- 1.3.6.1.4.1.989.1.22.3.2.2.1.3
		asCmnSensorTemperatureStatusInfo OBJECT-TYPE
			SYNTAX DisplayString
			MAX-ACCESS read-only
			STATUS current
			DESCRIPTION
				"Implementation-specific free text description of the trap raised. e.g.
				- Hot/cold sensors=SDR,SCRT0,SCRT1
				- All sensors OK
				More details about the temperature sensors and their readings are reported
				in table asCmnSensorTemperatureMonitorTable."
			::= { asCmnSensorTrapStatusEntry 3 }

		
		-- 1.3.6.1.4.1.989.1.22.3.2.2.1.4
		asCmnSensorDcVoltageStatus OBJECT-TYPE
			SYNTAX INTEGER
				{
				dcVoltageNominal(0),
				dcVoltageOutOfRange(1)
				}
			MAX-ACCESS read-only
			STATUS current
			DESCRIPTION
				"Reports current DC voltage alarm trap status as defined in the value list.
				The status reports overall DC voltage condition of the system based on the reading 
				from multiple sensors. The status values have the following meaning:
				- dcVoltageNominal: all the sensors in the system show the DC voltage values within acceptable range
				- dcVoltageOutOfRange: one or more sensors show the DC voltage outside the nominal range"
			::= { asCmnSensorTrapStatusEntry 4 }

		
		-- 1.3.6.1.4.1.989.1.22.3.2.2.1.5
		asCmnSensorDcVoltageStatusInfo OBJECT-TYPE
			SYNTAX DisplayString
			MAX-ACCESS read-only
			STATUS current
			DESCRIPTION
				"Implementation specific free text description of the trap raised. e.g.
				- DC voltage out of range: DPRF-1, PSU-3
				- All sensors OK."
			::= { asCmnSensorTrapStatusEntry 5 }

		
		-- 1.3.6.1.4.1.989.1.22.3.3
		asCmnSensorDevice OBJECT IDENTIFIER ::= { asCmnSensor 3 }

		
		-- 1.3.6.1.4.1.989.1.22.3.3.1
		asCmnSensorTemperatureMonitorTable OBJECT-TYPE
			SYNTAX SEQUENCE OF AsCmnSensorTemperatureMonitorEntry
			MAX-ACCESS not-accessible
			STATUS current
			DESCRIPTION
				"Generic reporting table for all the temperature sensors in the system.
				Contains one row for each sensor."
			::= { asCmnSensorDevice 1 }

		
		-- 1.3.6.1.4.1.989.1.22.3.3.1.1
		asCmnSensorTemperatureMonitorEntry OBJECT-TYPE
			SYNTAX AsCmnSensorTemperatureMonitorEntry
			MAX-ACCESS not-accessible
			STATUS current
			DESCRIPTION
				"Description."
			INDEX { asCmnSensorTempMonItem }
			::= { asCmnSensorTemperatureMonitorTable 1 }

		
		AsCmnSensorTemperatureMonitorEntry ::=
			SEQUENCE { 
				asCmnSensorTempMonItem
					Integer32,
				asCmnSensorTempMonInventoryItem
					Integer32,
				asCmnSensorTempMonSensorName
					DisplayString,
				asCmnSensorTempMonValue
					Integer32,
				asCmnSensorTempMonStatus
					INTEGER
			 }

		-- 1.3.6.1.4.1.989.1.22.3.3.1.1.1
		asCmnSensorTempMonItem OBJECT-TYPE
			SYNTAX Integer32 (1..255)
			MAX-ACCESS not-accessible
			STATUS current
			DESCRIPTION
				"Arbitrary identifier for the sensor. Defined solely for the purpose of indexing of the rows in this table.
				Agent should use consecutive numbers starting from 1."
			::= { asCmnSensorTemperatureMonitorEntry 1 }

		
		-- 1.3.6.1.4.1.989.1.22.3.3.1.1.2
		asCmnSensorTempMonInventoryItem OBJECT-TYPE
			SYNTAX Integer32 (0..65535)
			MAX-ACCESS read-only
			STATUS current
			DESCRIPTION
				"Identifies the device instance the temperature sensor is installed on. 
				It is an index to generic inventory table. Zero means that the sensor is not installed on any 
				inventory item reported in the generic inventory table."
			::= { asCmnSensorTemperatureMonitorEntry 2 }

		
		-- 1.3.6.1.4.1.989.1.22.3.3.1.1.3
		asCmnSensorTempMonSensorName OBJECT-TYPE
			SYNTAX DisplayString
			MAX-ACCESS read-only
			STATUS current
			DESCRIPTION
				"Identifies the temperature sensor, the measured value of is reported in 
				asmacroTempMonValue. e.g. SDR CPU, SDR FPGA, SDR PICO
				"
			::= { asCmnSensorTemperatureMonitorEntry 3 }

		
		-- 1.3.6.1.4.1.989.1.22.3.3.1.1.4
		asCmnSensorTempMonValue OBJECT-TYPE
			SYNTAX Integer32 (-55..125)
			UNITS "deg C"
			MAX-ACCESS read-only
			STATUS current
			DESCRIPTION
				"The value of the measured temperature. The measurement algorithm should filter the small, 
				frequent changes in the temperature read from the sensor. 
				The details of the algorithm are implementation specific."
			::= { asCmnSensorTemperatureMonitorEntry 4 }

		
		-- 1.3.6.1.4.1.989.1.22.3.3.1.1.5
		asCmnSensorTempMonStatus OBJECT-TYPE
			SYNTAX INTEGER
				{
				tempNormal(0),
				tempTooHigh(1),
				tempTooLow(2)
				}
			MAX-ACCESS read-only
			STATUS current
			DESCRIPTION
				"The object reports the status of the temperature tested against some implementation
				specific criteria. This may be used by manager to indicate the abnormal temperature condition 
				of the sensor."
			::= { asCmnSensorTemperatureMonitorEntry 5 }

		
		-- 1.3.6.1.4.1.989.1.22.3.3.2
		asCmnSensorDcVoltageMonitorTable OBJECT-TYPE
			SYNTAX SEQUENCE OF AsCmnSensorDcVoltageMonitorEntry
			MAX-ACCESS not-accessible
			STATUS current
			DESCRIPTION
				"Generic reporting table for all the DC voltage sensors in the system.
				Contains one row for each sensor."
			::= { asCmnSensorDevice 2 }

		
		-- 1.3.6.1.4.1.989.1.22.3.3.2.1
		asCmnSensorDcVoltageMonitorEntry OBJECT-TYPE
			SYNTAX AsCmnSensorDcVoltageMonitorEntry
			MAX-ACCESS not-accessible
			STATUS current
			DESCRIPTION
				"Description."
			INDEX { asCmnSensorDcVoltageMonItem }
			::= { asCmnSensorDcVoltageMonitorTable 1 }

		
		AsCmnSensorDcVoltageMonitorEntry ::=
			SEQUENCE { 
				asCmnSensorDcVoltageMonItem
					Integer32,
				asCmnSensorDcVoltageMonInventoryItem
					Integer32,
				asCmnSensorDcVoltageMonSensorName
					DisplayString,
				asCmnSensorDcVoltageMonValue
					Integer32,
				asCmnSensorDcVoltageMonStatus
					INTEGER
			 }

		-- 1.3.6.1.4.1.989.1.22.3.3.2.1.1
		asCmnSensorDcVoltageMonItem OBJECT-TYPE
			SYNTAX Integer32 (1..255)
			MAX-ACCESS not-accessible
			STATUS current
			DESCRIPTION
				"Arbitrary identifyier of the sensor. Defined solely for the purpose of indexing of the rows in this table.
				Agent should use consecutive numbers starting with 1."
			::= { asCmnSensorDcVoltageMonitorEntry 1 }

		
		-- 1.3.6.1.4.1.989.1.22.3.3.2.1.2
		asCmnSensorDcVoltageMonInventoryItem OBJECT-TYPE
			SYNTAX Integer32 (0..65535)
			MAX-ACCESS read-only
			STATUS current
			DESCRIPTION
				"Identifies the device instance the dc voltage sensor is installed on. 
				It is an index to generic inventory table."
			::= { asCmnSensorDcVoltageMonitorEntry 2 }

		
		-- 1.3.6.1.4.1.989.1.22.3.3.2.1.3
		asCmnSensorDcVoltageMonSensorName OBJECT-TYPE
			SYNTAX DisplayString
			MAX-ACCESS read-only
			STATUS current
			DESCRIPTION
				"Identifies the dc voltage sensor e.g DPRF-1"
			::= { asCmnSensorDcVoltageMonitorEntry 3 }

		
		-- 1.3.6.1.4.1.989.1.22.3.3.2.1.4
		asCmnSensorDcVoltageMonValue OBJECT-TYPE
			SYNTAX Integer32 (0..50000)
			UNITS "mV"
			MAX-ACCESS read-only
			STATUS current
			DESCRIPTION
				"The value of the measured DC voltage The measurement algorithm should filter the small, 
				frequent changes in the voltage read from the sensor. 
				The details of the algorithm are implementation specific."
			DEFVAL { 0 }
			::= { asCmnSensorDcVoltageMonitorEntry 4 }

		
		-- 1.3.6.1.4.1.989.1.22.3.3.2.1.5
		asCmnSensorDcVoltageMonStatus OBJECT-TYPE
			SYNTAX INTEGER
				{
				dcVoltageNominal(0),
				dcVoltageTooHigh(1),
				dcVoltageTooLow(2),
				dcVoltageOutOfRange(3)
				}
			MAX-ACCESS read-only
			STATUS current
			DESCRIPTION
				"The object reports the status of the DC voltage tested against some implementation
				specific criteria. This may be used by manager to indicate the voltage out of nominal range."
			::= { asCmnSensorDcVoltageMonitorEntry 5 }

		
	
	END

--
-- ASCMN-SENSOR-MIB.mib
--
