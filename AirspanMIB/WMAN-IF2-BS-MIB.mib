WMAN-IF2-BS-MIB DEFINITIONS ::= BEGIN
                                    
  IMPORTS
        MODULE-IDENTITY,
        OBJECT-TYPE,
        NOTIFICATION-TYPE,   
        Unsigned32, Integer32, Counter32,
        Counter64, transmission
                FROM SNMPv2-SMI
        SnmpAdminString
                FROM SNMP-FRAMEWORK-MIB
        TEXTUAL-CONVENTION,
        MacAddress, RowStatus, TruthValue,
        TimeStamp, DateAndTime        
                FROM SNMPv2-TC
        InetAddressType, InetAddress
                FROM INET-ADDRESS-MIB 
        OBJECT-GROUP,
        MODULE-COMPLIANCE,
        NOTIFICATION-GROUP
                FROM SNMPv2-CONF
        ifIndex
                FROM IF-MIB
        wman
                FROM WMAN-DEV-MIB;

wmanIf2BsMib MODULE-IDENTITY
        LAST-UPDATED    "200802110000Z" -- February 11, 2008
        ORGANIZATION    "IEEE 802.16"
        CONTACT-INFO
            "WG E-mail: stds-802-16@ieee.org
             WG Chair:  Roger B. Marks
             Postal:    NextWave Broadband, Inc.
             E-mail:    r.b.marks@ieee.org
             
             TG Chair:  Phillip Barber
             Postal:    Huawei Technologies Co., Ltd
             E-mail:    pbarber@Huawei.com             

             Editor:    Joey Chou
             Postal:    Intel Corporation
                        5000 W. Chandler Blvd,
                        Chandler, AZ 85227, USA
             E-mail:    joey.chou@intel.com"                     
        DESCRIPTION
            "This MIB Module defines managed objects for Base Station
             based on IEEE Std 802.16. The MIB contains managed objects
             that are common for both fixed and mobile Broadband
             Wireless Networks."             
        REVISION        "200802110000Z"
        DESCRIPTION
            "Includes changes as per comment resolutions agreed at the
             Levi meeting"
        REVISION        "200711300000Z"
        DESCRIPTION
            "The first revision of WMAN-IF2-BS-MIB module that is
             enhanced to support IEEE 802.16e-2005 standard."
        ::= { wman 2 }

wmanIf2MibObjects    OBJECT IDENTIFIER ::= { wmanIf2BsMib 1 }
wmanIf2BsFm          OBJECT IDENTIFIER ::= { wmanIf2MibObjects 1 }
wmanIf2BsCm          OBJECT IDENTIFIER ::= { wmanIf2MibObjects 2 }
wmanIf2BsAm          OBJECT IDENTIFIER ::= { wmanIf2MibObjects 3 }
wmanIf2BsPm          OBJECT IDENTIFIER ::= { wmanIf2MibObjects 4 }
wmanIf2BsSm          OBJECT IDENTIFIER ::= { wmanIf2MibObjects 5 }

-- Textual Conventions

WmanIf2MacVersion ::= TEXTUAL-CONVENTION
        STATUS      current
        DESCRIPTION
            "Version number of IEEE 802.16."
        REFERENCE
                "Subclause 11.1.3"
        SYNTAX      INTEGER
                        {ieee802Dot16Of2001(1),
                         ieee802Dot16cOf2002andPredcessors(2),
                         ieee802Dot16aOf2003andPredcessors(3),
                         ieee802Dot16Of2004(4),
                         ieee802Dot16Of2004and16eOf2005(5),
                         ieee802Dot16Of2004and16efOf2005(6),
                         ieee802Dot16Of04and16efOf05and16gOf07(7),
                         ieee802Dot16Of2008(8)}
                             
WmanIf2CidType ::= TEXTUAL-CONVENTION
        STATUS      current
        DESCRIPTION
            "Type of CID."                     
        SYNTAX      INTEGER (0 .. 65535)

WmanIf2DataEncryptAlgId ::= TEXTUAL-CONVENTION
        STATUS      current
        DESCRIPTION     
            "Data encryption algorithm identifiers."
        REFERENCE            
            "Table 562"
        SYNTAX      INTEGER {none(0),
                             des56BitCbcMode(1),
                             aes128BitCcmMode(2),
                             aes128BitCbcMode(3),
                             aes128BitCtrMode(128)}

WmanIf2DataAuthAlgId ::= TEXTUAL-CONVENTION
        STATUS      current
        DESCRIPTION     
            "Data authentication algorithm identifiers."
        REFERENCE            
            "Table 563"
        SYNTAX      INTEGER {noDataAuthentication(0),
                             aes128BitCcmMode(1)}
            
WmanIf2TekEncryptAlgId ::= TEXTUAL-CONVENTION
        STATUS      current
        DESCRIPTION     
            "TEK encryption algorithm identifiers."
        REFERENCE            
            "Table 564"
        SYNTAX      INTEGER {tripleDes128BitKey(1),
                             rsa1024BitKey(2),
                             aes128BitKeyEcbMode(3),
                             aes128BitKeyWrap(4)}
            
WmanIf2PkmErrorCode ::= TEXTUAL-CONVENTION
        STATUS      current
        DESCRIPTION     
            "This error code provides further information about an
             Authorization Reject, Key Reject, Authorization Invalid,
             or TEK Invalid.
             
               0 - no failure
               1 - unauthorized SS
               2 - unauthorized SAID
               3 - unsolicited
               4 - invalid key sequence
               5 - key request authentication failure
               
             The following are error code for permanent authorization
             failure that indicates any reattempts at authorization
             would continue to result in Authorization Rejects.
               
               6 - the BS does not have the CA certificate belonging
                   to the issuer of an SS certificate 
               7 - SS certificate has an invalid signature
               8 - ASN.1 parsing failure during verification of SS
                   certificate
               9 - SS certificate is on the 'hot list'
               10 - inconsistencies between certificate data and data
                   in accompanying PKM attributes 
               11 - SS and BS have incompatible security capabilities"
        REFERENCE            
            "Table 560 Subclause 11.9.10"
        SYNTAX      INTEGER {noFailure(0),
                             unauthorizedSs(1),
                             unauthorizedSaid(2),
                             unsolicited(3),
                             invalidKeySequence(4),
                             keyReqAuthFailure(5),          
                             umknownManufactur(6),
                             invalidSignature(7),
                             asn1ParsingFailure(8),
                             ssCaOnHotList(9),
                             dataInconsistency(10),
                             ssBsIncompatibleSc(11)}
                                         
WmanIf2SaType ::= TEXTUAL-CONVENTION
        STATUS      current
        DESCRIPTION     
            "The type of Security Association (SA)."
        REFERENCE            
            "Table 567 in subclause 11.9.18"
        SYNTAX      INTEGER {primarySa(0),
                             staticSa(1),
                             dynamicSa(2)}

WmanIf2CertificateStat ::= TEXTUAL-CONVENTION
        STATUS      current
        DESCRIPTION
            "The reason why a SS's certificate is deemed valid
             or invalid:
                  
             0 - return unknown if the SS is running PKM mode
             1 - means the certificate is valid because it chains
                 to a valid certificate
             2 - means the certificate is valid because it has been
                 provisioned to be trusted
             3 - means the certificate is invalid because it has been
                 provisioned to be untrusted.
             4 - means the certificate is invalid because it chains
                 to an untrusted certificate.
             5 - refer to errors in parsing, validity periods, etc,
                 of SS certificate
             6 - refer to errors in parsing, validity periods, etc,
                 of CA certificate"
        REFERENCE            
            "Subclause 7.2.5.1 in IEEE Std 802.16-2004"
        SYNTAX      INTEGER {unknown (0),
                             validSsChained (1),
                             validSsTrusted (2),
                             invalidSsUntrusted (3),
                             invalidCAUntrusted (4),
                             invalidSsOther (5),
                             invalidCAOther (6)}
                                                                                       
WmanIf2ChannelNumber ::= TEXTUAL-CONVENTION
        STATUS      current
        DESCRIPTION     
            "Physical channel number"
        SYNTAX      INTEGER (0 .. 199)

WmanIf2OfdmFecCodeType ::= TEXTUAL-CONVENTION
        STATUS      current
        DESCRIPTION     
            "FEC code type and modulation type"
        REFERENCE            
            "Table 542 and 548"
        SYNTAX      INTEGER {bpskCc1Over2(0),
                             qpskRsCcCc1Over2(1),
                             qpskRsCcCc3Over4(2),
                             sixteenQamRsCcCc1Over2(3),
                             sixteenQamRsCcCc3Over4(4),
                             sixtyFourQamRsCcCc2Over3(5),
                             sixtyFourQamRsCcCc3Over4(6),
                             qpskBtc1Over2(7),
                             qpskBtc3Over4(8),
                             sixteenQamBtc3Over4(9),
                             sixteenQamBtc4Over5(10),
                             sixtyFourQamBtc2Over3(11),
                             sixtyFourQamBtc5Over6(12),
                             qpskCtc1Over2(13),
                             qpskCtc2Over3(14),
                             qpskCtc3Over4(15),
                             sixteenQamCtc1Over2(16),
                             sixteenQamCtc3Over4(17),
                             sixtyFourQamCtc2Over3(18),
                             sixtyFourQamCtc3Over4(19)}

WmanIf2OfdmaUcdFecCode ::= TEXTUAL-CONVENTION
        STATUS      current
        DESCRIPTION     
            "UCD FEC code type and modulation type"
        REFERENCE            
            "Table 543"
        SYNTAX 	    INTEGER {qpskCc1Over2(0),
                             qpskCc3Over4(1),
                             sixteenQamCc1Over2(2),
                             sixteenQamCc3Over4(3),
                             sixtyFourQamCc1Over2(4),
                             sixtyFourQamCc2Over3(5),
                             sixtyFourQamCc3Over4(6),
                             qpskBtc1Over2(7),
                             qpskBtc3Over4(8),
                             sixteenQamBtc3Over5(9),
                             sixteenQamBtc4Over5(10),
                             sixtyFourQamBtc5Over8(11),
                             sixtyFourQamBtc4Over5(12),
                             qpskCtc1Over2(13),
                             reserved(14),
                             qpskCtc3Over4(15),
                             sixteenQamCtc1Over2(16),
                             sixteenQamCtc3Over4(17),
                             sixtyFourQamCtc1Over2(18),
                             sixtyFourQamCtc2Over3(19),
                             sixtyFourQamCtc3Over4(20),
                             sixtyFourQamCtc5Over6(21),
                             qpskZtCc1Over2(22),
                             qpskZtCc3Over4(23),
                             sixteenQamZtCc1Over2(24),
                             sixteenQamZtCc3Over4(25),
                             sixtyFourQamZtCc1Over2(26),
                             sixtyFourQamZtCc2Over3(27),
                             sixtyFourQamZtCc3Over4(28),
                             qpskLdpc1over2(29),
                             qpskLdpc2over3A(30),
                             qpskLdpc3over4A(31),
                             sixteenQamLdpc1over2(32),
                             sixteenQamLdpc2over3A(33),
                             sixteenQamLdpc3over4A(34),
                             sixtyFourQamLdpc1over2(35),
                             sixtyFourQamLdpc2over3A(36),
                             sixtyFourQamLdpc3over4A(37),
                             qpskLdpc2over3B(38),
                             qpskLdpc3over4B(39),
                             sixteenQamLdpc2over3B(40),
                             sixteenQamLdpc3over4B(41),
                             sixtyFourQamLdpc2over3B(42),
                             sixtyFourQamLdpc3over4B(43),
                             qpskCcOptIntv1over2(44),
                             qpskCcOptIntv3over4(45),
                             sixteenQamCcOptIntv1over2(46),
                             sixteenQamCcOptIntv3over4(47),
                             sixtyFourQamCcOptIntv2over3(48),
                             sixtyFourQamCcOptIntv3over4(49),
                             qpskLdpc5over6(50),
                             sixteenQamLdpc5over6(51),
                             sixtyFourQamLdpc5over6(52)}

WmanIf2OfdmaDcdFecCode ::= TEXTUAL-CONVENTION
        STATUS      current
        DESCRIPTION     
            "DCD FEC code type and modulation type"
        REFERENCE            
            "Table 549"
        SYNTAX 	    INTEGER {qpskCc1Over2(0),
                             qpskCc3Over4(1),
                             sixteenQamCc1Over2(2),
                             sixteenQamCc3Over4(3),
                             sixtyFourQamCc1Over2(4),
                             sixtyFourQamCc2Over3(5),
                             sixtyFourQamCc3Over4(6),
                             qpskBtc1Over2(7),
                             qpskBtc3Over4Or2Over3(8),
                             sixteenQamBtc3Over5(9),
                             sixteenQamBtc4Over5(10),
                             sixtyFourQamBtc2Over3Or5Over8(11),
                             sixtyFourQamBtc5Over6Or4Over5(12),
                             qpskCtc1Over2(13),
                             reserved14(14),
                             qpskCtc3Over4(15),
                             sixteenQamCtc1Over2(16),
                             sixteenQamCtc3Over4(17),
                             sixtyFourQamCtc1Over2(18),
                             sixtyFourQamCtc2Over3(19),
                             sixtyFourQamCtc3Over4(20),
                             sixtyFourQamCtc5Over6(21),
                             qpskZtCc1Over2(22),
                             qpskZtCc3Over4(23),
                             sixteenQamZtCc1Over2(24),
                             sixteenQamZtCc3Over4(25),
                             sixtyFourQamZtCc1Over2(26),
                             sixtyFourQamZtCc2Over3(27),
                             sixtyFourQamZtCc3Over4(28),
                             qpskLdpc1over2(29),
                             qpskLdpc2over3A(30),
                             qpskLdpc3over4A(31),
                             sixteenQamLdpc1over2(32),
                             sixteenQamLdpc2over3A(33),
                             sixteenQamLdpc3over4A(34),
                             sixtyFourQamLdpc1over2(35),
                             sixtyFourQamLdpc2over3A(36),
                             sixtyFourQamLdpc3over4A(37),
                             qpskLdpc2over3B(38),
                             qpskLdpc3over4B(39),
                             sixteenQamLdpc2over3B(40),
                             sixteenQamLdpc3over4B(41),
                             sixtyFourQamLdpc2over3B(42),
                             sixtyFourQamLdpc3over4B(43),
                             qpskCcOptIntv1over2(44),
                             qpskCcOptIntv3over4(45),
                             sixteenQamCcOptIntv1over2(46),
                             sixteenQamCcOptIntv3over4(47),
                             sixtyFourQamCcOptIntv2over3(48),
                             sixtyFourQamCcOptIntv3over4(49),
                             qpskLdpc5over6(50),
                             sixteenQamLdpc5over6(51),
                             sixtyFourQamLdpc5over6(52)}

-- Textual convention for capabilities encodings
WmanIf2NumOfCid ::= TEXTUAL-CONVENTION
        STATUS      current
        DESCRIPTION
            "The object of this type shows the number of CIDs that
             SS can support."
        REFERENCE
            "Subclause 11.7.6"
        SYNTAX      INTEGER (1..65535) 
        
WmanIf2MaxDsxFlowType ::= TEXTUAL-CONVENTION
        STATUS      current
        DESCRIPTION
            "The object of this type specifies the maximum number of
             concurrent DSA, DSC, or DSD transactions that may be
             outstanding."
        REFERENCE
            "Subclause 11.7.8.2"
        SYNTAX      INTEGER (0..255) 
        
WmanIf2MaxMcaFlowType ::= TEXTUAL-CONVENTION
        STATUS      current
        DESCRIPTION
            "The object of this type specifies the maximum number of
             concurrent MCA transactions that may be outstanding."
        REFERENCE
            "Subclause 11.7.8.4"
        SYNTAX      INTEGER (0..255) 
        
WmanIf2MaxMcpGroupCid ::= TEXTUAL-CONVENTION
        STATUS      current
        DESCRIPTION
            "The object of this type indicates the maximum number of
             simultaneous Multicast Polling Groups the SS is
             capable of belonging to."
        REFERENCE
            "Subclause 11.7.8.5"
        SYNTAX      INTEGER (0..255) 
        
WmanIf2MaxPkmFlowType ::= TEXTUAL-CONVENTION
        STATUS      current
        DESCRIPTION
            "The object of this type specifies the maximum number of
             concurrent PKM transactions that may be outstanding."
        REFERENCE
            "Subclause 11.8.4.5"
        SYNTAX      INTEGER (0..255)  
                
WmanIf2MaxNumOfSaType ::= TEXTUAL-CONVENTION
        STATUS      current
        DESCRIPTION
            "This field specifies maximum number of supported
             security association of the SS."
        REFERENCE
            "Subclause 11.8.4.6"
        SYNTAX      INTEGER (0..255) 
                                                                                
WmanIf2MaxClassifiers ::= TEXTUAL-CONVENTION
        STATUS      current
        DESCRIPTION
            "The object of this type indicates the maximum number of
             admitted Classifiers that the SS is allowed to have."
        REFERENCE
            "Subclause 11.7.7.2"
        SYNTAX      INTEGER (0..65535)

WmanIf2SsTransitionGap ::= TEXTUAL-CONVENTION
        STATUS      current
        DESCRIPTION
            "This field indicates the transition speed SSTTG and SSRTG
             for TDD and H-FDD SSs. Allowed values are:
               OFDM mode: TDD and H-FDD 0..100
               Other modes: TDD: 0..50; H-FDD: 0..100"
        REFERENCE
            "Subclause 11.8.3.1"
        SYNTAX      INTEGER (0..100)

WmanIf2MaxTxPowerType ::= TEXTUAL-CONVENTION
        STATUS      current
        DESCRIPTION
            "This type is used to define maximum available power for 
             BPSK, QPSK, 16-QAM and 64-QAM constellations. The maximum
             power parameters are reported in dBm and quantized in 0.5
             dBm steps ranging from -64 dBm (encoded 0x00) to 63.5 dBm 
             (encoded 0xFF). Values outside this range shall be
             assigned the closest extreme. SSs that do not support
             QAM64 shall report the value of 0x00 in the maximum QAM64
             power field."
        REFERENCE
            "Subclause 11.8.3.2"
        SYNTAX      INTEGER (0..255)

WmanIf2BsIdType ::= TEXTUAL-CONVENTION
        STATUS      current
        DESCRIPTION     
            "Defines the encoding of BSID. The BSID is a 6 byte number
             and follows the encoding rules of MacAddress textual
             convention, i.e. as if it were transmitted 
             least-significant bit first. The value should be displayed
             with 2 parts clearly separated by a colon e.g:
             001DFF:00003A. The most significant part is representing
             the Operator ID. "
        SYNTAX      OCTET STRING (SIZE(6))

WmanIf2Ipv6FlowLabel ::= TEXTUAL-CONVENTION
        STATUS      current
        DESCRIPTION     
            "The value of this field specifies the matching values for
             the IPv6 Flow label field. As the flow label field has a
             length of 20 bits, the first 4 bits of the most significant
             byte shall be set to 0x0 and disregarded."
        SYNTAX      OCTET STRING (SIZE(3))

WmanIf2OfdmaDemMimo ::= TEXTUAL-CONVENTION
        STATUS      current
        DESCRIPTION
            "This field indicates the MIMO capability of OFDMA MS
             demodulator. A bit value of 0 indicates 'not supported'
             while 1 indicates 'supported'."
        REFERENCE
            "Subclause 11.8.3.7.5 in IEEE 802.16e"
        SYNTAX      BITS {twoAntStcMatrixA(0),
                          twoAntStcMatrixBVCoding(1),
                          twoAntStcMatrixBHCoding(2),
                          fourAntStcMatrixA(3),
                          fourAntStcMatrixBVCoding(4),
                          fourAntStcMatrixBHCoding(5),
                          fourAntStcMatrixCVCoding(6),
                          fourAntStcMatrixCHCodingt(7)}

WmanIf2OfdmaDemoMimo ::= TEXTUAL-CONVENTION
        STATUS      current
        DESCRIPTION
            "This field indicates the MIMO capability of OFDMA SS
             demodulator."
        REFERENCE
            "Subclause 11.8.3.7.5"
        SYNTAX      BITS {twoAntStcMatrixA(0),
                          twoAntStcMatrixBVertCoding(1),
                          twoAntStcMatrixBHorizCoding(2),
                          fourAntStcMatrixA(3),
                          fourAntStcMatrixBVertCoding(4),
                          fourAntStcMatrixBHorizCoding(5),
                          fourAntStcMatrixCVertCoding(6),
                          fourAntStcMatrixCHorizCodingt(7),
                          threeAntStcMatrixA(8),
                          threeAntStcMatrixB(9),
                          threeAntStcMatrixCVertCoding(10),
                          threeAntStcMatrixCHorizCodingt(11),
                          calculatingPrecodingWeight(12),
                          adaptiveRateControl(13),
                          calculatingChannelMatrix(14),
                          antennaGrouping(15),
                          antennaSelection(16),
                          codebookBasedPrecoding(17),
                          longTermPrecoding(18),
                          mimoMidamble(19),
                          alocGranularityDlPuscStc(20),
                          concurrentAlocDlPuscStc(21)} 

WmanIf2OfdmaUlMimo ::= TEXTUAL-CONVENTION
        STATUS      current
        DESCRIPTION
            "This field indicates the different MIMO options supported
             by a WirelessMAN-OFDMA PHY SS in the uplink. A bit value of
             0 indicates 'not supported' while 1 indicates 'supported'."
        REFERENCE
            "Subclause 11.8.3.7.6 in IEEE 802.16e"
        SYNTAX      BITS {twoAntSttd(0),
                          twoAntSmVCoding(1),
                          oneAntCooperativeSm(2)}
                                  
WmanIf2SdmaPilotCap ::= TEXTUAL-CONVENTION
        STATUS      current
        DESCRIPTION
            "This field indicates SDMA pilot pattern support for AMC
             zone."
        REFERENCE
            "Subclause 11.8.3.7.17"
        SYNTAX      INTEGER {noSupport(0),
                             sdmaPilotAandB(1),
                             allSdmaPilotPatterns(2)}

WmanIf2HarqAckDelay ::= TEXTUAL-CONVENTION
        STATUS      current
        DESCRIPTION
            "HARQ ACK delay for UL and DL bursts
               1 = one frame offset
               2 = two frames offset
               3 = three frames offset"
        REFERENCE
            "Table 540, 544"
        SYNTAX      INTEGER {oneframeoffset(1),
                             twoframesoffset(2),
                             threeframesoffset(3)}

WmanIf2AasBeamSel ::= TEXTUAL-CONVENTION
        STATUS      current
        DESCRIPTION
            "Boolean to indicate whether unsolicited AAS Beam Select
             messages (see 6.3.2.3.37) should be sent by the MS.
               0: MS should not send AAS Beam Select Messages
               1: MS may send AAS Beam Select Messages"
        REFERENCE
            "Table 540"
        SYNTAX      INTEGER {notAllowed(0),
                             allowed(1)}
                             
WmanIf2MaxMacLevel ::= TEXTUAL-CONVENTION
        STATUS      current
        DESCRIPTION
            "maximum amount of MAC level data including MAC headers and
             HARQ retransmission bursts the MS is capable of processing
             in the DL/UL part of a single MAC frame."
        REFERENCE
            "Subclause 11.7.8.6"
        SYNTAX      INTEGER (0..65535)

WmanIfPermutationType ::= TEXTUAL-CONVENTION
        STATUS      current
        DESCRIPTION
            "Permutation type for broadcast region in HARQ zone"
        REFERENCE
            "Table 544"
        SYNTAX      INTEGER {pusc(1),
                             fusc(2),
                             optionalFusc(3),
                             amc(4)}    
                           
WmanIf2HoSupportType ::= TEXTUAL-CONVENTION
        STATUS      current
        DESCRIPTION
            "The types of handover supported."
        REFERENCE
            "Table 544"
        SYNTAX      BITS {handover(0),
                          mdHandover(1),
                          fbssHandover(2)}
-- to be deleted 
WmanIf2ActionRule ::= TEXTUAL-CONVENTION
        STATUS      current
        DESCRIPTION
            "The value of this field specifies an action associated with
             the classifier rule
                 Bit #0: 0 = none.
                         1 = Discard packet"
        REFERENCE
            "Subclause 11.13.19.3.4.17"
        SYNTAX      BITS {discardPacket(0)}

WmanIf2LinkDirection ::= TEXTUAL-CONVENTION
        STATUS      current
        DESCRIPTION     
            "The direction of a connection." 
        SYNTAX      INTEGER {downstream(1),
                             upstream(2)}

WmanIf2SaServiceType ::= TEXTUAL-CONVENTION
        STATUS      current
        DESCRIPTION     
            "This attribute indicates service types of the corresponding
             SA type. This attribute shall be defined only when the SA
             type is Static SA or Dynamic SA. The GTEK shall be used to
             encrypt connection for group multicast service. The MTK
             shall be used to encrypt connection for MBS service."
        REFERENCE            
            "Subclause 11.9.35"
        SYNTAX      INTEGER {unicastService(0),
                             groupMulticastService(1),
                             mbsService(2)}

WmanIf2GlobalSrvClass ::= TEXTUAL-CONVENTION
        STATUS      current
        DESCRIPTION
            "Global Service Class Name contains 8 information fields
             that map to predefined QoS attributes as shown in
             subclause 6.3.14.4.1.
              
             bit#0:     Uplink/Downlink indicator
                        0 - uplink
                        1 - downlink
             bit#1-6:   Maximum sustained traffic rate in bps that is
                        defined in Table 124b  
             bit#7:     0 - no traffic indication
                        1 - traffic indication
             bit#8-13:  Maximum traffic burst defines the maximum burst
                        size that must be accommodated for the service. 
             bit#14-19: Minimum reserved traffic rate parameter
                        specifies the minimum rate, in bits per second,
                        reserved for this service flow.
             bit#20-25: Maximum latency specifies the maximum interval
                        between the reception of a packet at CS of BS
                        or SS and the arrival of the packet to the peer
                        device.
             bit#26:    SDU indicator specifies whether the SDUs on the
                        service flow are fixed-length or variable-length.
                        0 - variable length
                        1 - fixed length
             bit#27:    Paging indicator of an MS preference for the
                        reception of paging advisory messages during
                        idle mode. When set, it indicates that the BS
                        may present paging advisory messages or other
                        indicative messages to the MS when data SDUs
                        bound for the MS are present while the MS is in
                        Idle Mode.
                        0 - no paging generation
                        1 - paging generation
             bit#28-35: Req/Tx Policy - An attribute is enabled by
                        setting the corresponding bit position to 1. For
                        attributes affecting UL BR types, a value of
                        zero indicates the default actions described in
                        the scheduling service description in 6.3.5
                        shall be used. A value of 1 indicates that the
                        action associated with the attribute bit
                        overrides the default action.
                 bit28: No broadcast BR opportunities. (UL only)
                 bit29: No use multicast BR opportunities. (UL only)
                 bit30: No piggyback requests with data. (UL only)
                 bit31: No fragment data.
                 bit32: No suppress payload headers (CS parameter).
                 bit33: No pack multiple SDUs (or fragments) into single
                        MAC PDUs.
                 bit34: Not include CRC in the MAC PDU.
                 bit35: Reserved
             bit#36-38: The value of this parameter specifies the UL
                        grant scheduling type that shall be enabled for
                        the associated UL service flow (see 6.3.5.2).
                 Value = 1: Undefined (BS implementation-dependenta)
                         2: BE (default)
                         3: nrtPS
                         4: rtPS
                         5: Extended rtPS
                         6: UGS"
        REFERENCE
            "Subclause 6.3.14.4.1 Table 124a in IEEE Std 802.16e-2005"
        SYNTAX      BITS {ulDlIndicator(0),
                          maxSustainedRate0(1),
                          maxSustainedRate1(2),
                          maxSustainedRate2(3),
                          maxSustainedRate3(4),
                          maxSustainedRate4(5),
                          maxSustainedRate5(6),
                          trafficIndication(7),
                          maxTrafficBurst0(8),
                          maxTrafficBurst1(9),
                          maxTrafficBurst2(10),
                          maxTrafficBurst3(11),
                          maxTrafficBurst4(12),
                          maxTrafficBurst5(13),
                          minReservedRate0(14),
                          minReservedRate1(15),
                          minReservedRate2(16),
                          minReservedRate3(17),
                          minReservedRate4(18),
                          minReservedRate5(19),
                          maxLatency0(20),
                          maxLatency1(21),
                          maxLatency2(22),
                          maxLatency3(23),
                          maxLatency4(24),
                          maxLatency5(25),
                          sduIndicator(26),
                          pagingGeneration(27),
                          noBroadcastBr(28),
                          noMulticastBr(29),
                          noPiggybackReq(30),
                          noFragmentData(31),
                          noSurpressPayload(32),
                          noPackedSdu(33),
                          noCrcInMacPdu(34),
                          ulGrantType0(35),
                          ulGrantType1(36),
                          ulGrantType2(37)}
                                                                                    
WmanIf2OfdmaFftSize ::= TEXTUAL-CONVENTION
        STATUS      current
        DESCRIPTION
            "FFT size for OFDMA PHY
               0b000 = 2048
               0b001 = 1024
               0b010 = 512
               0b100 = 128"
        REFERENCE
            "Subclause 11.18.1, Table 384b in IEEE Std 802.16e-2005"
        SYNTAX INTEGER {fft2048(0),
                        fft1024(1),
                        fft512(2),
                        reserved(3),
                        fft128(4)}

WmanIf2OfdmFftSize ::= TEXTUAL-CONVENTION
        STATUS      current
        DESCRIPTION
            "FFT size for OFDM PHY
               0b000: 2048
               0b011: 256"
        REFERENCE
            "Subclause 11.8.3.6.1, IEEE Std 802.16-2004"
        SYNTAX INTEGER {fft2048(0),
                        fft256(3)}

WmanIf2BsSsCapType ::= TEXTUAL-CONVENTION
        STATUS      current
        DESCRIPTION
            "xxxReq: Indicates that SS reports its capabilities in
                     RNG-REQ, SBC-REQ, or REG-REQ messages.
             xxxRsp: Indicates that BS confirms SS capabilities in
                     RNG-RSP, SBC-RSP, or REG-RSP messages."
        SYNTAX INTEGER {xxxReq (1),
                        xxxRsp (2)}

WmanIf2BsCapType ::= TEXTUAL-CONVENTION
        STATUS      current
        DESCRIPTION
            "inheritedBsCap: Indicates BS' basic HW and SW capabilities.
             configedBsCap: Indicates BS' capabilities that has been
                            configured."
        SYNTAX      INTEGER {inheritedBsCap (1),
                             configedBsCap (2)}

WmanIf2MaxNumBurstTx ::= TEXTUAL-CONVENTION
        STATUS      current
        DESCRIPTION 
            "Maximum number of bursts transmitted concurrently to the MS
             , including all bursts without CID or with CIDs matching
             the MS's CIDs."
        REFERENCE 
            "Subclause 11.7.8.13 in IEEE Std 802.16e-2005"
        SYNTAX      Integer32 (1..16)

WmanIf2MaxNumProvSf ::= TEXTUAL-CONVENTION
        STATUS      current
        DESCRIPTION 
            "When a BS is to transmit multiple DSA transactions for
             provisioned service flows, this object indicates how many
             DSA transactions with provisioned service flows will be
             transmitted."
        REFERENCE 
            "Subclause 11.7.19 in IEEE Std 802.16e-2005"
        SYNTAX      Integer32 (0..255)

WmanIf2MinNumFrmsPwrCtrl ::= TEXTUAL-CONVENTION
        STATUS      current
        DESCRIPTION 
            "Defines the minimum number of frames that SS takes to
             switch from the open loop power control scheme to the
             closed loop power control scheme or vice versa."
        REFERENCE 
            "Subclause 11.8.3.6.7 in IEEE Std 802.16-2008"
        SYNTAX      Integer32 (0..255)

WmanIf2OfdmaNoHarqChan ::= TEXTUAL-CONVENTION
        STATUS      current
        DESCRIPTION 
            "Specifies the number of H-ARQchannels (n) the SS supports,
             where n = 1..16. The value of this object should be 0..15."
        REFERENCE 
            "Subclause 11.8.3.7.2 (demodulator), 11.8.3.7.3 (modulator)
             in IEEE 802.16-2008."
        SYNTAX      Integer32 (0..15)

WmanIf2BasicCapOptions ::= TEXTUAL-CONVENTION
        STATUS      current
        DESCRIPTION 
            "This type combines all the basic SS capabilities
             (excluuding Phy and mobility specific) with the binary
             encodded fields. It reserves the space equivalent to the
             size of corresponding TLV and within this space it maps
             directly to the encoding specified in TLVs including all
             defined reserved bits."
        REFERENCE 
            "IEEE Std 802.16-2008 subclauses:
             bit 0:       11.7.8.1 (ARQ support)
                 1-7:     reserved
             bit 8-9:     11.7.4 (IP version)
                 10-15:   reserved
             bit 16-29:   11.7.7.1 (CS support)
                 30-47:   reserved
             bit 48-49:   11.7.7.3 (PHS support)
                 50-55:   reserved
             bit 56:      reserved
                 57:      11.8.1 (BW allocation - duplex support)
                 58-63:   reserved
             bit 64-65:   11.8.2 (PDU construction and transmission)
                 66-71:   reserved
             bit 72:      11.7.8.7 (Packing)
                 73-79:   reserved    
             bit 80:      11.7.8.8 (Extended rtPS)
                 81-87:   reserved
             bit 88-91:   11.7.11 (SMC IP address allocation method)
                 92-95:   reserved    
             bit 96-100:  11.7.23 (ARQ ACK type)
                 101-103: reserved
             bit 104-120: 11.7.25 (Mac header support)
                 121-127: reserved
             bit 128-129: 11.8.4.1 (Pkm version)
                 130-135: reserved
             bit 136-141: 11.8.4.2 (Authorization policy support)
                 142-143: reserved
             bit 144:     11.8.4.3 (MAC mode - HMAC)
                 145:     reserved
                 146-149: 11.8.4.3 (MAC mode - HMAC follow up)
                 150-151: reserved
             bit 152-154: 11.8.6 (Extended subheader support)
                 155-159: reserved"
        SYNTAX BITS {arqSupport(0),
                     reserved1(1),
                     reserved2(2),
                     reserved3(3),
                     reserved4(4),
                     reserved5(5),
                     reserved6(6),
                     reserved7(7),
                     ipv4Support(8),
                     ipv6Support(9),
                     reserved10(10),
                     reserved11(11),
                     reserved12(12),
                     reserved13(13),
                     reserved14(14),
                     reserved15(15),
                     csSupportAtm(16),
                     csSupportIpv4(17),
                     csSupportIpv6(18),
                     csSupport802Dot3(19),
                     csSupport802Dot1Q(20),
                     csSupportIpv4Over802Dot3(21),
                     csSupportIpv6Over802Dot3(22),
                     csSupportIpv4Over802Dot1Q(23),
                     csSupportIpv6Over802Dot1Q(24),
                     csSupport802Dot3RohcHc(25),
                     csSupport802Dot3EcrtpHc(26),
                     csSupportIpv4Over6RohcHc(27),
                     csSupportIpv4Over6EcrtpHc(28),
                     csSupportGpcs(29),
                     reserved30(30),
                     reserved31(31),
                     reserved32(32),
                     reserved33(33),
                     reserved34(34),
                     reserved35(35),
                     reserved36(36),
                     reserved37(37),
                     reserved38(38),
                     reserved39(39),
                     reserved40(40),
                     reserved41(41),
                     reserved42(42),
                     reserved43(43),
                     reserved44(44),
                     reserved45(45),
                     reserved46(46),
                     reserved47(47),
                     phsSupportAtm(48),
                     phsSupportPacket(49),
                     reserved50(50),
                     reserved51(51),
                     reserved52(52),
                     reserved53(53),
                     reserved54(54),
                     reserved55(55),
                     reserved56(56),
                     bwAllocSupportFullDuplex(57),
                     reserved58(58),
                     reserved59(59),
                     reserved60(60),
                     reserved61(61),
                     reserved62(62),
                     reserved63(63),
                     pduConstructionpiggybackedRequests(64),
                     pduConstructionFsn3Bits(65),
                     reserved66(66),
                     reserved67(67),
                     reserved68(68),
                     reserved69(69),
                     reserved70(70),
                     reserved71(71),
                     packingSupported(72),
                     reserved73(73),
                     reserved74(74),
                     reserved75(75),
                     reserved76(76),
                     reserved77(77),
                     reserved78(78),
                     reserved79(79),
                     extendedRtpsSupported(80),
                     reserved81(81),
                     reserved82(82),
                     reserved83(83),
                     reserved84(84),
                     reserved85(85),
                     reserved86(86),
                     reserved87(87),
                     smcIpAddressAllocDhcp(88),
                     smcIpAddressAllocMobileIpv4(89),
                     smcIpAddressAllocMobileDhcpv6(90),
                     smcIpAddressAllocMobileIpv6Autoconfig(91),
                     reserved92(92),
                     reserved93(93),
                     reserved94(94),
                     reserved95(95),
                     arqSelectiveAck(96),
                     arqCumulativeAck(97),
                     arqCumWithSelAckEntry(98),
                     arqCumWithBlockSeqAck(99),
                     arqSeqBlockAck(100),
                     reserved101(101),
                     reserved102(102),
                     reserved103(103),
                     headerSupportBwReqUlTxPowerReport(104),
                     headerSupportBwReqCinrReport(105),
                     headerSupportCqichAllocationReq(106),
                     headerSupportPhyChannelReport(107),
                     headerSupportBwReqUlSleepCntl(108),
                     headerSupportSnReport(109),
                     headerSupportFeedbackReport(110),
                     headerSupportSduSn(111),
                     headerSupportSduSnPeriod0(112),
                     headerSupportSduSnPeriod1(113),
                     headerSupportSduSnPeriod2(114),
                     headerSupportDlSleepControl(115),
                     headerSupportFeedbackRequest(116),
                     headerSupportMimcModeFeedback(117),
                     headerSupportUlTxPowerReport(118),
                     headerSupportMiniFeedback(119),
                     headerSupportSnRequest(120),
                     reserved121(121),
                     reserved122(122),
                     reserved123(123),
                     reserved124(124),
                     reserved125(125),
                     reserved126(126),
                     reserved127(127),
                     pkmVersionSupport1(128),
                     pkmVersionSupport2(129),
                     reserved130(130),
                     reserved131(131),
                     reserved132(132),
                     reserved133(133),
                     reserved134(134),
                     reserved135(135),
                     authPolicySupportRsaInitialEntry(136),
                     authPolicySupportEapInitialEntry(137),
                     authPolicySupportAuthEapInitialEntry(138),
                     authPolicySupportRsaReentry(139),
                     authPolicySupportEapReentry(140),
                     authPolicySupportAuthEapReentry(141),
                     reserved142(142),
                     reserved143(143),
                     macModeHmac(144),
                     reserved145(145),
                     macModeHmac64(146),
                     macModeHmac80(147),
                     macModeHmac96(148),
                     macModeCmac(149),
                     reserved150(150),
                     reserved151(151),
                     extSubheader(152),
                     headerSupportShortPduSn(153),
                     headerSupportLongPduSn(154),
                     reserved155(155),
                     reserved156(156),
                     reserved157(157),
                     reserved158(158),
                     reserved159(159)}

WmanIf2OfdmCapOptions ::= TEXTUAL-CONVENTION
        STATUS      current
        DESCRIPTION 
            "This type combines all OFDM specific SS capabilities with
             the binary encodded fields. It reserves the space
             equivalent to the size of corresponding TLV and within this
             space it maps directly to the encoding specified in TLVs
             including all defined reserved bits."
        REFERENCE 
            "IEEE Std 802.16-2008 subclauses:
             bits 0-1:     11.8.3.6.1 (OFDM FFT sizes)
                  2-7:     reserved
             bits 8-13:    11.8.3.6.2 (OFDM SS demodulator)
                  14-15:   reserved
             bits 16-21:   11.8.3.6.3 (OFDM SS modulator)
                  22-23:   reserved
             bits 24:      11.8.3.6.5 (OFDM TC sublayer)
                  25-31:   reserved
             bits 32-33:   11.8.3.6.6 (OFDM private map)
                  34-39:   reserved
             bits 40-41:   11.8.3.6.7 (OFDM SS uplink power control)
                  42-47:   reserved"
        SYNTAX BITS {ofdmFftSize256(0),
                     ofdmFftSize2048(1),
                     reserved2(2),
                     reserved3(3),
                     reserved4(4),
                     reserved5(5),
                     reserved6(6),
                     reserved7(7),
                     ofdmSsDemodulatorQam64(8),
                     ofdmSsDemodulatorBtc(9),
                     ofdmSsDemodulatorCtc(10),
                     ofdmSsDemodulatorStc(11),
                     ofdmSsDemodulatorAas(12),
                     ofdmSsDemodulatorSuchan(13),
                     reserved14(14),
                     reserved15(15),
                     ofdmSsModulatorQam64(16),
                     ofdmSsModulatorBtc(17),
                     ofdmSsModulatorCtc(18),
                     ofdmSsModulatorSubchan(19),
                     ofdmSsModulatorFocusedCtBwReq(20),
                     ofdmSsModulatorUlCyclicDelay(21),
                     reserved22(22),
                     reserved23(23),
                     ofdmTcSublayerSupport(24),
                     reserved25(25),
                     reserved26(26),
                     reserved27(27),
                     reserved28(28),
                     reserved29(29),
                     reserved30(30),
                     reserved31(31),
                     ofdmRegularMap(32),
                     ofdmCompressedMap(33),
                     reserved34(34),
                     reserved35(35),
                     reserved36(36),
                     reserved37(37),
                     reserved38(38),
                     reserved39(39),
                     ofdmUlOpenLoopPwrCtrl(40),
                     ofdmUlAasPreamblePwrCtrl(41),
                     reserved42(42),
                     reserved43(43),
                     reserved44(44),
                     reserved45(45),
                     reserved46(46),
                     reserved47(47),
                     reserved48(48)}

WmanIf2OfdmaCapOptions ::= TEXTUAL-CONVENTION
        STATUS      current
        DESCRIPTION 
            "This type combines all OFDMA specific SS capabilities with
             the binary encodded fields. It reserves the space
             equivalent to the size of corresponding TLV and within this
             space it maps directly to the encoding specified in TLVs
             including all defined reserved bits."
        REFERENCE 
            "IEEE Std 802.16-2008 subclauses:
             bits 0:          reserved
                  1-4:        11.8.3.7.1 (OFDMA FFT sizes)
                  5-7:        reserved
             bits 8-14,16-18: 11.8.3.7.2 (OFDMA SS demodulator)
                  15,19-23:   reserved
             bits 24-31:      11.8.3.7.3 (OFDMA SS modulator)
             bits 32-39:      11.8.3.7.4 (OFDMA permutation)
             bits 40-61:      11.8.3.7.5 (OFDMA SS demodulator for MIMO)
                  62-63:      reserved
             bits 64-71:      11.8.3.7.7 (OFDMA private map)
             bits 72-76:      11.8.3.7.8 (OFDMA AAS)
                  77-79:      reserved
             bits 80-87:      11.8.3.7.9 (OFDMA CINR measurements)
             bits 88-89:      11.8.3.7.11 (OFDMA power control)
                  90-95:      reserved
             bits 96-100:     11.8.3.7.12 (OFDMA map)
                  101-103:    reserved
             bits 104-106,108-111: 11.8.3.7.13 (OFDM uplink control)
                  107:        reserved
             bits 112-123:    11.8.3.7.14 (OFDMA CSIT capability)
                  124-127:    reserved
             bits 128-135:    11.8.3.7.15 (OFDMA max bursts in HARQ)
             bits 136-144:    11.8.3.7.16 (OFDMA modulator for MIMO)
                  145-151:    reserved
             bits 152-153:    11.8.3.7.18 (OFDMA multicast bursts)
                  154-159:    reserved
             bits 160-172:    11.8.3.7.19.1 (OFDMA HARQ incremental buf)
                  173-175:    reserved
             bits 176-190:    11.8.3.7.19.1 (OFDMA HARQ chase)
                  191:        reserved
             bits 192-198:    11.8.3.7.20 (OFDMA parameter set)
                  199:        reserved"
        SYNTAX BITS {reserved0(0),
                     ofdmaFftSize2048(1),
                     ofdmaFftSize128(2),
                     ofdmaFftSize512(3),
                     ofdmaFftSize1024(4),
                     reserved5(5),
                     reserved6(6),
                     reserved7(7),
                     ofdmaDemodulatorQam64(8),
                     ofdmaDemodulatorBtc(9),
                     ofdmaDemodulatorCtc(10),
                     ofdmaDemodulatorStc(11),
                     ofdmaDemodulatorCcWithInterleaver(12),
                     ofdmaDemodulatorHarqChase(13),
                     ofdmaDemodulatorHarqCtclr(14),
                     reserved15(15),
                     ofdmaDemodulatorHarqCclr(16),
                     ofdmaDemodulatorLdpc(17),
                     ofdmaDemodulatorDedicatedPilots(18),
                     reserved19(19),
                     reserved20(20),
                     reserved21(21),
                     reserved22(22),
                     reserved23(23),
                     ofdmaModulatorQam64(24),
                     ofdmaModulatorBtc(25),
                     ofdmaModulatorCtc(26),
                     ofdmaModulatorStc(27),
                     ofdmaModulatorHarqChase(28),
                     ofdmaModulatorHarqCtcIr(29),
                     ofdmaModulatorHarqCcIr(30),
                     ofdmaModulatorHarqLdpc(31),
                     odfmaPermutationOptionalPusc(32),
                     odfmaPermutationOptionalFusc(33),
                     odfmaPermutationAmc1x6(34),
                     odfmaPermutationAmc2x3(35),
                     odfmaPermutationAmc3x2(36),
                     odfmaPermutationAmcWithHarqMap(37),
                     odfmaPermutationTusc1(38),
                     odfmaPermutationTusc2(39),
                     ofdmaDemodMimo2AntStcMatrixA(40),
                     ofdmaDemodMimo2AntStcMatrixBVCoding(41),
                     ofdmaDemodMimo2AntStcMatrixBHCoding(42),
                     ofdmaDemodMimo4AntStcMatrixA(43),
                     ofdmaDemodMimo4AntStcMatrixBVCoding(44),
                     ofdmaDemodMimo4AntStcMatrixBHCoding(45),
                     ofdmaDemodMimo4AntStcMatrixCVCoding(46),
                     ofdmaDemodMimo4AntStcMatrixCHCoding(47),
                     ofdmaDemodMimo3AntStcMatrixA(48),
                     ofdmaDemodMimo3AntStcMatrixB(49),
                     ofdmaDemodMimo3AntStcMatrixCVCoding(50),
                     ofdmaDemodMimo3AntStcMatrixCHCoding(51),
                     ofdmaDemodMimoCalcPrecodeWight(52),
                     ofdmaDemodMimoAdaptiveRateCtrl(53),
                     ofdmaDemodMimoCalcChanMatrix(54),
                     ofdmaDemodMimoAntGroup(55),
                     ofdmaDemodMimoAntSelect(56),
                     ofdmaDemodMimoCodebookPrecode(57),
                     ofdmaDemodMimoLongTermPrecode(58),
                     ofdmaDemodMimoMidamble(59),
                     ofdmaDemodAllocGranDlPuscStc(60),
                     ofdmaDemodConcurentAllocDlPuscStc(61),
                     reserved62(62),
                     reserved63(63),
                     ofdmaPrivateMapHarqMap(64),
                     ofdmaPrivateMap(65),
                     ofdmaPrivateMapReduced(66),
                     ofdmaPrivateMapChainEnable(67),
                     ofdmaPrivateMapDlFrameOffset(68),
                     ofdmaPrivateMapUlFrameOffset(69),
                     ofdmaPrivateMapChainConcurency0(70),
                     ofdmaPrivateMapChainConcurency1(71),
                     ofdmaAasZone(72),
                     ofdmaAasDiverityMapScan(73),
                     ofdmaAasFeedbackRsp(74),
                     ofdmaAasDlPreamble(75),
                     ofdmaAasUlPreamble(76),
                     reserved77(77),
                     reserved78(78),
                     reserved79(79),
                     ofdmaCinrPhysicalPreamble(80),
                     ofdmaCinrPhysicalPilotSubc(81),
                     ofdmaCinrPhysicalDataSubc(82),
                     ofdmaCinrEffectivePreamble(83),
                     ofdmaCinrEffectivePilotSubc(84),
                     ofdmaCinrEffectiveDataSubc(85),
                     ofdmaCinr2CqiChannel(86),
                     ofdmaFreqSelectivityReport(87),
                     ofdmaPwrCtrlOpenLoop(88),
                     ofdmaPwrCtrlAasPreamble(89),
                     reserved90(90),
                     reserved91(91),
                     reserved92(92),
                     reserved93(93),
                     reserved94(94),
                     reserved95(95),
                     ofdmaMapHarq(96),
                     ofdmaMapExtendedHarqIe(97),
                     ofdmaMapSubMapForFirstZone(98),
                     ofdmaMapSubMapForOtherZones(99),
                     ofdmaMapDlRegionDefinition(100),
                     reserved101(101),
                     reserved102(102),
                     reserved103(103),
                     ofdmaUlCtrlt3BitMimoFastFeedback(104),
                     ofdmaUlCtrltEnhancedFastFeedback(105),
                     ofdmaUlCtrltUlAck(106),
                     reserved107(107),
                     ofdmaUlCtrltUepFastFeedback(108),
                     ofdmaUlCtrltFastDlMeasurementFeedback(109),
                     ofdmaUlCtrltPriSecFastFeedback(110),
                     ofdmaDiucCqiFastFeedback(111),
                     ofdmaCsitTypeA(112),
                     ofdmaCsitTypeB(113),
                     ofdmaPowerAssignment(114),
                     ofdmaSoundingRspTime0(115),
                     ofdmaSoundingRspTime1(116),
                     ofdmaSoundingRspTime2(117),
                     ofdmaMaxSimuSoundInst0(118),
                     ofdmaMaxSimuSoundInst1(119),
                     ofdmaMaxSimuSoundInst2(120),
                     ofdmaMaxSimuSoundInst3(121),
                     ofdmaNoP9Or18ForCsitTypeA(122),
                     ofdmaCsitNotSupported(123),
                     reserved124(124),
                     reserved125(125),
                     reserved126(126),
                     reserved127(127),
                     ofdmaMaxHarqBurstsUl0(128),
                     ofdmaMaxHarqBurstsUl1(129),
                     ofdmaMaxHarqBurstsUl2(130),
                     ofdmaMaxHarqBurstsUlNonHarqIncluded(131),
                     ofdmaMaxHarqBurstsDl0(132),
                     ofdmaMaxHarqBurstsDl1(133),
                     ofdmaMaxHarqBurstsDl2(134),
                     ofdmaMaxHarqBurstsDl3(135),
                     ofdmaMimoMod2AntStcMatrixA(136),
                     ofdmaMimoMod2AntStcMatrixBVCoding(137),
                     ofdmaMimoMod2AntStcMatrixBHCoding(138),
                     ofdmaMimoModBeamforming(139),
                     ofdmaMimoModAdaptiveRateControl(140),
                     ofdmaMimoModSingleAnt(141),
                     ofdmaMimoModCollaborativeSm1Ant(142),
                     ofdmaMimoModCollaborativeSm2Ants(143),
                     ofdmaMimoModDisableUlSubchRotation(144),
                     reserved145(145),
                     reserved146(146),
                     reserved147(147),
                     reserved148(148),
                     reserved149(149),
                     reserved150(150),
                     reserved151(151),
                     ofdmaMcastBurstsDlMultiFecTypes(152),
                     ofdmaMcastBurstsUlMultiFecTypes(153),
                     reserved154(154),
                     reserved155(155),
                     reserved156(156),
                     reserved157(157),
                     reserved158(158),
                     reserved159(159),
                     ofdmaHarqIncrBufDlNep0(160),
                     ofdmaHarqIncrBufDlNep1(161),
                     ofdmaHarqIncrBufDlNep2(162),
                     ofdmaHarqIncrBufDlNep3(163),
                     ofdmaHarqIncrBufDlAggFlag(164),
                     reserved165(165),
                     reserved166(166),
                     reserved167(167),
                     ofdmaHarqIncrBufUlNep0(168),
                     ofdmaHarqIncrBufUlNep1(169),
                     ofdmaHarqIncrBufUlNep2(170),
                     ofdmaHarqIncrBufUlNep3(171),
                     ofdmaHarqIncrBufUlAggFlag(172),
                     reserved173(173),
                     reserved174(174),
                     reserved175(175),
                     ofdmaHarqChaseBufDlComb0(176),
                     ofdmaHarqChaseBufDlComb1(177),
                     ofdmaHarqChaseBufDlComb2(178),
                     ofdmaHarqChaseBufDlComb3(179),
                     ofdmaHarqChaseBufDlComb4(180),
                     ofdmaHarqChaseBufDlComb5(181),
                     ofdmaHarqChaseBufDlAggFlag(182),
                     reserved183(183),
                     ofdmaHarqChaseBufUlComb0(184),
                     ofdmaHarqChaseBufUlComb1(185),
                     ofdmaHarqChaseBufUlComb2(186),
                     ofdmaHarqChaseBufUlComb3(187),
                     ofdmaHarqChaseBufUlComb4(188),
                     ofdmaHarqChaseBufUlComb5(189),
                     ofdmaHarqChaseBufUlAggFlag(190),
                     reserved191(191),
                     odfmaParamSetPhyA(192),
                     odfmaParamSetPhyB(193),
                     odfmaParamSetHarq0(194),
                     odfmaParamSetHarq1(195),
                     odfmaParamSetHarq2(196),
                     odfmaParamSetMacA(197),
                     odfmaParamSetMacB(198),
                     reserved199(199)}

--
-- wmanIf2BsFm group – containing tables and objects related to Fault
--                     Management (i.e. BS SNMP Trap objects)
--
wmanIf2BsTrapControl     OBJECT IDENTIFIER ::= {wmanIf2BsFm 1}
wmanIf2BsTrapDefinitions OBJECT IDENTIFIER ::= {wmanIf2BsFm 2}

-- This object groups all NOTIFICATION-TYPE objects for BS. 
-- It is defined following RFC2758 sections 8.5 and 8.6 
-- for the compatibility with SNMPv1.
wmanIf2BsTrapPrefix OBJECT IDENTIFIER ::= { wmanIf2BsTrapDefinitions 0 }
	
wmanIf2BsTrapControlRegister    OBJECT-TYPE
        SYNTAX      BITS {wmanIf2BsSsStatusNotification (0),
                          wmanIf2BsSsDynamicServiceFail (1),
                          wmanIf2BsSsRssiStatusChange   (2),
                          wmanIf2BsSsRegister           (3),
                          wmanIf2BsSsPkmFail            (4),
                          wmanIf2BsPerformanceCounters  (5)}
        MAX-ACCESS read-write
        STATUS     current
        DESCRIPTION
            "The object is used to enable or disable Base Station traps.
             From left to right, the set bit indicates the corresponding
             Base Station trap is enabled."
        ::= { wmanIf2BsTrapControl 1 }

wmanIf2BsStatusTrapControlRegister    OBJECT-TYPE
        SYNTAX      BITS {unused(0),
                          ssInitRangingSucc(1),
                          ssInitRangingFail(2),
                          ssRegistered(3),
                          ssRegistrationFail(4),
                          ssDeregistered(5),
                          ssBasicCapabilitySucc(6),
                          ssBasicCapabilityFail(7),
                          ssAuthorizationSucc(8),
                          ssAuthorizationFail(9),
                          tftpSucc(10),
                          tftpFail(11),
                          sfCreationSucc(12),
                          sfCreationFail(13)}
        MAX-ACCESS read-write
        STATUS     current
        DESCRIPTION
            "The object is used to enable or disable Base Station status
             notification traps. The set bit indicates the corresponding
             Base Station trap is enabled."
        ::= { wmanIf2BsTrapControl 2 }
        
--
-- BS threshold Definitions
--
wmanIf2BsThresholdConfigTable OBJECT-TYPE
        SYNTAX      SEQUENCE OF WmanIf2BsThresholdConfigEntry
        MAX-ACCESS  not-accessible
        STATUS      current
        DESCRIPTION
            "This table contains threshold objects that can be set
             to detect the threshold crossing events."
        ::= { wmanIf2BsTrapControl 3 }

wmanIf2BsThresholdConfigEntry OBJECT-TYPE
        SYNTAX      WmanIf2BsThresholdConfigEntry
        MAX-ACCESS  not-accessible
        STATUS      current
        DESCRIPTION
            ""
        INDEX     { ifIndex }
        ::= { wmanIf2BsThresholdConfigTable 1 }

WmanIf2BsThresholdConfigEntry ::= SEQUENCE {        
        wmanIf2BsRssiLowThreshold               Integer32,
        wmanIf2BsRssiHighThreshold              Integer32}

wmanIf2BsRssiLowThreshold OBJECT-TYPE
        SYNTAX      Integer32
        UNITS       "dBm"
        MAX-ACCESS  read-write
        STATUS      current
        DESCRIPTION
        	"Low threshold for generating the RSSI alarm."
        ::= { wmanIf2BsThresholdConfigEntry 1 }

wmanIf2BsRssiHighThreshold OBJECT-TYPE
        SYNTAX      Integer32
        UNITS       "dBm"
        MAX-ACCESS  read-write
        STATUS      current
        DESCRIPTION
        	"High threshold for clearing the RSSI alarm."
        ::= { wmanIf2BsThresholdConfigEntry 2 }

--
-- Subscriber station Notification Objects Definitions
--
wmanIf2BsSsNotificationObjectsTable OBJECT-TYPE
        SYNTAX      SEQUENCE OF WmanIf2BsSsNotificationObjectsEntry
        MAX-ACCESS  not-accessible
        STATUS      current
        DESCRIPTION
            "This table contains SS notification objects that have been
             reported by the trap."
        ::= { wmanIf2BsTrapDefinitions 1 }

wmanIf2BsSsNotificationObjectsEntry OBJECT-TYPE
        SYNTAX      WmanIf2BsSsNotificationObjectsEntry
        MAX-ACCESS  not-accessible
        STATUS      current
        DESCRIPTION
            "This table provides one row for each SS that has
             generated traps."
        INDEX     { ifIndex, wmanIf2BsSsNotificationMacAddr }
        ::= { wmanIf2BsSsNotificationObjectsTable 1 }

WmanIf2BsSsNotificationObjectsEntry ::= SEQUENCE {        
        wmanIf2BsSsNotificationMacAddr          MacAddress,
        wmanIf2BsSsStatusValue                  INTEGER,
        wmanIf2BsSsStatusInfo                   OCTET STRING,
        wmanIf2BsDynamicServiceType             INTEGER,
        wmanIf2BsDynamicServiceFailReason       OCTET STRING,
        wmanIf2BsSsRssiStatus                   INTEGER,
        wmanIf2BsSsRssiStatusInfo               OCTET STRING,
        wmanIf2BsSsRegisterStatus               INTEGER,
        wmanIf2BsDynamicServiceFailSfid         Unsigned32,
        wmanIf2BsEventNotificationTime          TimeStamp}
       
wmanIf2BsSsNotificationMacAddr OBJECT-TYPE
        SYNTAX      MacAddress
        MAX-ACCESS  read-only
        STATUS      current
        DESCRIPTION
            "The MAC address of the SS, reporting the notification."
        ::= { wmanIf2BsSsNotificationObjectsEntry 1 }
        
wmanIf2BsSsStatusValue  OBJECT-TYPE
        SYNTAX      INTEGER {ssInitRangingSucc(1),
                             ssInitRangingFail(2),
                             ssRegistered(3),
                             ssRegistrationFail(4),
                             ssDeregistered(5),
                             ssBasicCapabilitySucc(6),
                             ssBasicCapabilityFail(7),
                             ssAuthorizationSucc(8),
                             ssAuthorizationFail(9),
                             tftpSucc(10),
                             tftpFail(11),
                             sfCreationSucc(12),
                             sfCreationFail(13)} 
        MAX-ACCESS  read-only
        STATUS      current
        DESCRIPTION
            "This object indicates the status of a SS, as it goes 
             through network entry and initialization procedure."
        ::= { wmanIf2BsSsNotificationObjectsEntry 2 }
                
wmanIf2BsSsStatusInfo  OBJECT-TYPE
        SYNTAX      OCTET STRING (SIZE(0..255))
        MAX-ACCESS  read-only
        STATUS      current
        DESCRIPTION
            "This object indicates the reason of SS's status change."
        ::= { wmanIf2BsSsNotificationObjectsEntry 3 }
                                     
wmanIf2BsDynamicServiceType  OBJECT-TYPE
        SYNTAX      INTEGER {bsSfCreationReq(1),
                             bsSfCreationRsp(2),
                             bsSfCreationAck(3)} 
        MAX-ACCESS  read-only
        STATUS      current
        DESCRIPTION
            "This object indicates the dynamic service flow
             creation command type."
        ::= { wmanIf2BsSsNotificationObjectsEntry 4 }
                
wmanIf2BsDynamicServiceFailReason  OBJECT-TYPE
        SYNTAX      OCTET STRING (SIZE(0..255))
        MAX-ACCESS  read-only
        STATUS      current
        DESCRIPTION
            "This object indicates the reason why the service flow
             creation has failed."
        ::= { wmanIf2BsSsNotificationObjectsEntry 5 }
                                                          
wmanIf2BsSsRssiStatus  OBJECT-TYPE
        SYNTAX      INTEGER {bsRssiAlarm(1),
                             bsRssiNoAlarm(2)} 
        MAX-ACCESS  read-only
        STATUS      current
        DESCRIPTION
            "A RSSI alarm is generated when RSSI becomes lower than
             wmanIf2BsLowRssiThreshold and is cleared when RSSI becomes
             higher than wmanIf2BsLowRssiThreshold."
        ::= { wmanIf2BsSsNotificationObjectsEntry 6 }
                
wmanIf2BsSsRssiStatusInfo  OBJECT-TYPE
        SYNTAX      OCTET STRING (SIZE(0..255))
        MAX-ACCESS  read-only
        STATUS      current
        DESCRIPTION
            "This object indicates the reason why RSSI alarm is
             generated."
        ::= { wmanIf2BsSsNotificationObjectsEntry 7 }

wmanIf2BsSsRegisterStatus OBJECT-TYPE
        SYNTAX      INTEGER {ssRegister(1),
                             ssDeregister(2)}
        MAX-ACCESS  read-only
        STATUS      current
        DESCRIPTION
            "This object indicates the status of SS registration."
        ::= { wmanIf2BsSsNotificationObjectsEntry 8 }

wmanIf2BsDynamicServiceFailSfid OBJECT-TYPE
        SYNTAX      Unsigned32 (1..4294967295)
        MAX-ACCESS  read-only
        STATUS      current
        DESCRIPTION
            "This object identifies the dynamic service flow
             for notification purposes."
        ::= { wmanIf2BsSsNotificationObjectsEntry 9 }

wmanIf2BsEventNotificationTime OBJECT-TYPE
        SYNTAX      TimeStamp
        MAX-ACCESS  read-only
        STATUS      current
        DESCRIPTION
            "Indicates the date and time when the event notification
             trap was generated."
        ::= { wmanIf2BsSsNotificationObjectsEntry 10 }
                                             
--
-- Subscriber station Notification Trap Definitions        
--
wmanIf2BsSsStatusNotificationTrap NOTIFICATION-TYPE
        OBJECTS     {ifIndex,
                     wmanIf2BsSsNotificationMacAddr,
                     wmanIf2BsSsStatusValue,
                     wmanIf2BsSsStatusInfo}
        STATUS      current
        DESCRIPTION
            "This trap reports the status of a SS. Based on this
             notification the NMS will issue an alarm with certain
             severity depending on the status and the reason received."
        ::= { wmanIf2BsTrapPrefix 1 }

wmanIf2BsSsRssiStatusChangeTrap NOTIFICATION-TYPE
        OBJECTS     {ifIndex,
                     wmanIf2BsSsNotificationMacAddr,
                     wmanIf2BsSsRssiStatus,
                     wmanIf2BsSsRssiStatusInfo}
        STATUS      current
        DESCRIPTION
            "An event to report that the uplink RSSI is below
             wmanIf2BsLowRssiThreshold, or above
             wmanIf2BsHighRssiThreshold after restore."
        ::= { wmanIf2BsTrapPrefix 2 }

wmanIf2BsSsPkmFailTrap NOTIFICATION-TYPE
        OBJECTS     {wmanIf2BsSsNotificationMacAddr}
        STATUS      current
        DESCRIPTION
            "An event to report the failure of a Pkm operation."
        ::= { wmanIf2BsTrapPrefix 3 }

wmanIf2BsSsDynamicServiceFailTrap NOTIFICATION-TYPE
        OBJECTS     {ifIndex,
                     wmanIf2BsSsNotificationMacAddr,
                     wmanIf2BsDynamicServiceType,
                     wmanIf2BsDynamicServiceFailReason,
                     wmanIf2BsDynamicServiceFailSfid}
        STATUS      current
        DESCRIPTION
            "An event reporting failure of DSx operation for a service
             flow identified by wmanIf2BsDynamicServiceFailSfid and
             detected in the Bs side."
        ::= { wmanIf2BsTrapPrefix 4 }

wmanIf2BsSsRegisterTrap NOTIFICATION-TYPE
        OBJECTS     {ifIndex,
                     wmanIf2BsSsNotificationMacAddr,
                     wmanIf2BsSsRegisterStatus}
        STATUS      current
        DESCRIPTION
            "An event to report SS registration status for a given sector
             identified by ifIndex."
        ::= { wmanIf2BsTrapPrefix 5 }

wmanIf2BsPerformanceCountersTrap NOTIFICATION-TYPE
        OBJECTS     {ifIndex,
                     wmanIf2BsSsAuthenAttempt, 
                     wmanIf2BsSsAuthenSuccess,
                     wmanIf2BsSsAuthenSuccessRate,
                     wmanIf2BsSsRangingAttempt, 
                     wmanIf2BsSsRangingSuccess,
                     wmanIf2BsSsRangingSuccessRate,
                     wmanIf2BsAvgDlUserThroughput,
                     wmanIf2BsAvgUlUserThroughput,
                     wmanIf2BsAvgDlMacThroughput,
                     wmanIf2BsAvgUlMacThroughput,
                     wmanIf2BsAvgDlPhyThroughput,
                     wmanIf2BsAvgUlPhyThroughput,        
                     wmanIf2BsPeakDlUserThroughput,
                     wmanIf2BsPeakUlUserThroughput,
                     wmanIf2BsPeakDlMacThroughput,
                     wmanIf2BsPeakUlMacThroughput,
                     wmanIf2BsPeakDlPhyThroughput,
                     wmanIf2BsPeakUlPhyThroughput,
                     wmanIf2BsAvgDlCellEdgeThroughput,
                     wmanIf2BsAvgUlCellEdgeThroughput,
                     wmanIf2BsDataRateMeasurements,
                     wmanIf2BsAvgNetworkEntryTime,
                     wmanIf2BsMaxNetworkEntryTime,
                     wmanIf2BsAvgNetworkReEntryTime,
                     wmanIf2BsMaxNetworkReEntryTime,
                     wmanIf2BsNumOfNetworkEntries,
                     wmanIf2BsNumOfNetworkReEntries,
                     wmanIf2BsDlPacketsSend, 
                     wmanIf2BsDlPacketsErrored,
                     wmanIf2BsDlPacketErrorRate,                     
                     wmanIf2BsEventNotificationTime,
                     wmanIf2BsSsHandoverAttempt, 
                     wmanIf2BsSsHandoverSuccess,
                     wmanIf2BsSsHandoverSuccessRate,
                     wmanIf2BsSsHandoverCancel, 
                     wmanIf2BsSsHandoverReject,
                     wmanIf2BsSsHandoverCancelRate,
                     wmanIf2BsSsHandoverRejectRate,
                     wmanIf2BsSsAvgHandoverTime,
                     wmanIf2BsSsUnexpectedHandover,
                     wmanIf2BsSsActiveUsers, 
                     wmanIf2BsSsPeakNormalModeUsers,
                     wmanIf2BsSsPeakSleepModeUsers,
                     wmanIf2BsSsPeakIdleModeUsers,
                     wmanIf2BsSsBasicAndPrimaryCids, 
                     wmanIf2BsSsMaximumUserCids,
                     wmanIf2BsSsAvgUserCids}
        STATUS      current
        DESCRIPTION
            "This event should be automatically generated every
             wmanIf2BsCountersReportInterval interval to report the
             performance counters for a given BS sector identified by
             ifIndex. The performance counters will be reset after this
             event being sent to EMS."
        ::= { wmanIf2BsTrapPrefix 6 }

--
-- wmanIf2BsCm group – containing tables and objects related to
--                     Configuration Management
--
wmanIf2BsRegisteredSsTable OBJECT-TYPE
        SYNTAX      SEQUENCE OF WmanIf2BsRegisteredSsEntry
        MAX-ACCESS  not-accessible
        STATUS      current
        DESCRIPTION
            "This table contains the basic capability information
             of SSs that have been negotiated and agreed between
             BS and SS via REG-REQ and REG-RSP messages. An entry
             in this table indicates the SS has entered and registered
             into the BS."
        REFERENCE
            "Subclause 6.3.2.3.7 in IEEE Std 802.16-2004"
        ::= { wmanIf2BsCm 1 }

wmanIf2BsRegisteredSsEntry OBJECT-TYPE
        SYNTAX      WmanIf2BsRegisteredSsEntry
        MAX-ACCESS  not-accessible
        STATUS      current
        DESCRIPTION
            "This table provides one row for each SS that has been
             registered in the BS. The primary index is the ifIndex
             with an ifType of ieee80216WMAN, indicating the BS sector
             with which the SS is associated. wmanIf2BsSsMacAddress
             identifies the SS being registered."
        INDEX     { ifIndex, wmanIf2BsSsMacAddress }
        ::= { wmanIf2BsRegisteredSsTable 1 }

WmanIf2BsRegisteredSsEntry ::= SEQUENCE {        
        wmanIf2BsSsMacAddress                   MacAddress,
        wmanIf2BsSsBasicCid                     WmanIf2CidType,
        wmanIf2BsSsPrimaryCid                   WmanIf2CidType,
        wmanIf2BsSsSecondaryCid                 WmanIf2CidType,
        wmanIf2BsSsManagementSupport            INTEGER,
        wmanIf2BsSsIpManagementMode             INTEGER,
        wmanIf2BsSs2ndMgmtArqEnable             TruthValue,
        wmanIf2BsSs2ndMgmtArqWindowSize         INTEGER,
        wmanIf2BsSs2ndMgmtArqDnLinkTxDelay      INTEGER,
        wmanIf2BsSs2ndMgmtArqUpLinkTxDelay      INTEGER,
        wmanIf2BsSs2ndMgmtArqDnLinkRxDelay      INTEGER,
        wmanIf2BsSs2ndMgmtArqUpLinkRxDelay      INTEGER,
        wmanIf2BsSs2ndMgmtArqBlockLifetime      INTEGER,
        wmanIf2BsSs2ndMgmtArqSyncLossTimeout    INTEGER,
        wmanIf2BsSs2ndMgmtArqDeliverInOrder     TruthValue,
        wmanIf2BsSs2ndMgmtArqRxPurgeTimeout     INTEGER,
        wmanIf2BsSs2ndMgmtArqBlockSize          INTEGER,
        wmanIf2BsSsVendorIdEncoding             OCTET STRING,
        wmanIf2BsSsAasBroadcastPermission       INTEGER, 
        wmanIf2BsSsMaxTxPowerBpsk               WmanIf2MaxTxPowerType,
        wmanIf2BsSsMaxTxPowerQpsk               WmanIf2MaxTxPowerType,
        wmanIf2BsSsMaxTxPower16Qam              WmanIf2MaxTxPowerType,
        wmanIf2BsSsMaxTxPower64Qam              WmanIf2MaxTxPowerType,
        wmanIf2BsSsMacVersion                   WmanIf2MacVersion}

wmanIf2BsSsMacAddress OBJECT-TYPE        
        SYNTAX      MacAddress 
        MAX-ACCESS  not-accessible
        STATUS      current
        DESCRIPTION
            "The MAC address of SS is received from the RNG-REQ
             message. When SS registers, this MAC address is entered
             into the table, and used as the identifier to the SS."
        REFERENCE
            "Subclause 6.3.2.3.5 in IEEE Std 802.16-2004"
        ::= { wmanIf2BsRegisteredSsEntry 1 }
                       
wmanIf2BsSsBasicCid OBJECT-TYPE
        SYNTAX      WmanIf2CidType 
        MAX-ACCESS  read-only
        STATUS      current
        DESCRIPTION
            "The value of this object indicates the SS's basic CID
             that was sent in the RNG-RSP message."
        REFERENCE
            "Subclause 6.3.2.3.6 in IEEE Std 802.16-2004"
        ::= { wmanIf2BsRegisteredSsEntry 2 }
        
wmanIf2BsSsPrimaryCid OBJECT-TYPE
        SYNTAX      WmanIf2CidType 
        MAX-ACCESS  read-only
        STATUS      current
        DESCRIPTION
            "The value of this object indicates the primary CID of the
             SS received from the RNG-RSP message."
        REFERENCE
            "Subclause 6.3.2.3.6 in IEEE Std 802.16-2004"
        ::= { wmanIf2BsRegisteredSsEntry 3 }
        
wmanIf2BsSsSecondaryCid OBJECT-TYPE
        SYNTAX      WmanIf2CidType 
        MAX-ACCESS  read-only
        STATUS      current
        DESCRIPTION
            "The value of this object indicates the secondary
             management CID present in the REG-RSP message. The value
             should be null if the 2nd management connection is not
             available."
        REFERENCE
            "Subclause 6.4.2.3.8 in IEEE Std 802.16-2004"
        ::= { wmanIf2BsRegisteredSsEntry 4 }
        
wmanIf2BsSsManagementSupport OBJECT-TYPE
        SYNTAX      INTEGER {unmanagedSs(0),
                             managedSs(1)} 
        MAX-ACCESS  read-only
        STATUS      current
        DESCRIPTION
            "This object indicates whether or not the SS is managed."
        REFERENCE
            "Subclause 11.7.2 in IEEE Std 802.16-2004"
        ::= { wmanIf2BsRegisteredSsEntry 5 }
                                                                                        
wmanIf2BsSsIpManagementMode OBJECT-TYPE
        SYNTAX      INTEGER {unmanaged(0),
                             ipManaged(1)} 
        MAX-ACCESS  read-only
        STATUS      current
        DESCRIPTION
            "The IP management mode parameter dictates whether
             the provider intends to manage the SS on an ongoing
             basis via IP-based mechanisms."
        REFERENCE
            "Subclause 11.7.3 in IEEE Std 802.16-2004"
        ::= { wmanIf2BsRegisteredSsEntry 6 }

wmanIf2BsSs2ndMgmtArqEnable OBJECT-TYPE
        SYNTAX      TruthValue
        MAX-ACCESS  read-only
        STATUS      current
        DESCRIPTION
            "True(1) ARQ enabling is requested for the 2nd
             management channel."
        REFERENCE
            "Subclause 11.13.18.1 in IEEE Std 802.16-2004"
        ::= { wmanIf2BsRegisteredSsEntry 7 }

wmanIf2BsSs2ndMgmtArqWindowSize	 OBJECT-TYPE
        SYNTAX      INTEGER (1 .. 1024)
        MAX-ACCESS  read-only
        STATUS      current
        DESCRIPTION
            "Indicates the maximum number of unacknowledged 
             fragments at any time for 2nd management connection."
        REFERENCE
            "Subclause 11.13.18.2 in IEEE Std 802.16-2004"
        ::= { wmanIf2BsRegisteredSsEntry 8 }

wmanIf2BsSs2ndMgmtArqDnLinkTxDelay OBJECT-TYPE
        SYNTAX      INTEGER (0 .. 65535)
        UNITS       "microsecond"
        MAX-ACCESS  read-only
        STATUS      current
        DESCRIPTION
            "The object defines the ARQ transmitter delay for
             downlink transmission."
        REFERENCE
            "Subclause 11.13.18.3 in IEEE Std 802.16-2004"
        ::= { wmanIf2BsRegisteredSsEntry 9 }

wmanIf2BsSs2ndMgmtArqUpLinkTxDelay OBJECT-TYPE
        SYNTAX      INTEGER (0 .. 65535)
        UNITS       "microsecond"
        MAX-ACCESS  read-only
        STATUS      current
        DESCRIPTION
            "The object defines the ARQ transmitter delay for
             uplink transmission."
        REFERENCE
            "Subclause 11.13.18.3 in IEEE Std 802.16-2004"
        ::= { wmanIf2BsRegisteredSsEntry 10 }

wmanIf2BsSs2ndMgmtArqDnLinkRxDelay OBJECT-TYPE
        SYNTAX      INTEGER (0 .. 65535)
        UNITS       "microsecond"
        MAX-ACCESS  read-only
        STATUS      current
        DESCRIPTION
            "The object defines the ARQ receiver delay for
             downlink transmission."
        REFERENCE
            "Subclause 11.13.18.3 in IEEE Std 802.16-2004"
        ::= { wmanIf2BsRegisteredSsEntry 11 }

wmanIf2BsSs2ndMgmtArqUpLinkRxDelay OBJECT-TYPE
        SYNTAX      INTEGER (0 .. 65535)
        UNITS       "microsecond"
        MAX-ACCESS  read-only
        STATUS      current
        DESCRIPTION
            "The object defines the ARQ receiver delay for
             uplink transmission."
        REFERENCE
            "Subclause 11.13.18.3 in IEEE Std 802.16-2004"
        ::= { wmanIf2BsRegisteredSsEntry 12 }
                
wmanIf2BsSs2ndMgmtArqBlockLifetime OBJECT-TYPE
        SYNTAX      INTEGER (0 .. 65535)
        UNITS       "10 us"
        MAX-ACCESS  read-only
        STATUS      current
        DESCRIPTION
            "The maximum time interval an ARQ fragment will be
             managed by the transmitter ARQ machine, once
             initial transmission of the fragment has occured.
             If transmission or retransmission of the fragment
             is not acknowledged by the receiver before the 
             time limit is reached, the fragment is discarded.
             A value of 0 means Infinite."
        REFERENCE
            "Subclause 11.13.18.4 in IEEE Std 802.16-2004"
        DEFVAL		{0}
        ::= { wmanIf2BsRegisteredSsEntry 13 }

wmanIf2BsSs2ndMgmtArqSyncLossTimeout OBJECT-TYPE
        SYNTAX      INTEGER (0 .. 65535)
        UNITS       "10 us"
        MAX-ACCESS  read-only
        STATUS      current
        DESCRIPTION
            "The maximum interval before declaring a loss
             of synchronization of the sender and receiver
             state machines. A value of 0 means Infinite."
        REFERENCE
            "Subclause 11.13.18.5 in IEEE Std 802.16-2004"
        DEFVAL	    {0}
        ::= { wmanIf2BsRegisteredSsEntry 14 }

wmanIf2BsSs2ndMgmtArqDeliverInOrder  OBJECT-TYPE
        SYNTAX      TruthValue
        MAX-ACCESS  read-only
        STATUS      current
        DESCRIPTION
            "Indicates whether or not data is to be delivered
             by the receiving MAC to its client application
             in the order in which data was handed off to the
             originating MAC."
        REFERENCE
            "Subclause 11.13.18.6 in IEEE Std 802.16-2004"
        ::= { wmanIf2BsRegisteredSsEntry 15 }

wmanIf2BsSs2ndMgmtArqRxPurgeTimeout  OBJECT-TYPE
        SYNTAX      INTEGER (0 .. 65535)
        UNITS       "10 us"
        MAX-ACCESS  read-only
        STATUS      current
        DESCRIPTION
            "Indicates the time interval the ARQ window is advanced
             after a fragment is received. A value of 0 means Infinite."
        REFERENCE
            "Subclause 11.13.18.7 in IEEE Std 802.16-2004"
        DEFVAL	    {0}
        ::= { wmanIf2BsRegisteredSsEntry 16 }                                               

wmanIf2BsSs2ndMgmtArqBlockSize OBJECT-TYPE
        SYNTAX      INTEGER (1 .. 2040)
        MAX-ACCESS  read-only
        STATUS      current
        DESCRIPTION
            "This parameter specifies the size of a ARQ block. This
             parameter shall be established by negotiation during the
             connection setup. The requester includes its desired
             setting in the REQ message. The receiver of the REQ
             message shall take the smaller of the value it prefers and
             value in the REQ message. The minimum value is included in
             the RSP message."
        REFERENCE
            "Subclause 11.13.18.8 in IEEE Std 802.16-2004"
        ::= { wmanIf2BsRegisteredSsEntry 17 }
        
wmanIf2BsSsVendorIdEncoding OBJECT-TYPE
        SYNTAX      OCTET STRING (SIZE(3))
        MAX-ACCESS  read-only
        STATUS      current
        DESCRIPTION
            "The value field contains the vendor identification
             specified by the 3 byte vendor-specific organizationally
             unique identifier of the SS or BS MAC address.A vendor ID
             used in a REG-REQ shall be the Vendor ID of the SS sending
             the request. A vendor ID used in a REG-RSP shall be the
             Vendor ID of the BS sending the response."
        REFERENCE
            "Subclause 11.1.5 in IEEE Std 802.16-2004"
        ::= { wmanIf2BsRegisteredSsEntry 18 }

wmanIf2BsSsAasBroadcastPermission OBJECT-TYPE
        SYNTAX	    INTEGER {contBasedBwReqPermitted(0),
                             contBasedBwReqNotPermitted(1)}
        MAX-ACCESS  read-only
        STATUS      current
        DESCRIPTION
            "This parameter specifies if SS can issue contention-based
             bandwidth request or not."
        REFERENCE
            "Subclause 11.6 in IEEE Std 802.16-2004"
        ::= { wmanIf2BsRegisteredSsEntry 19 }

wmanIf2BsSsMaxTxPowerBpsk OBJECT-TYPE
        SYNTAX      WmanIf2MaxTxPowerType                         
        MAX-ACCESS  read-only
        STATUS      current
        DESCRIPTION
            "The maximum available power for BPSK. The maximum power
             parameters are reported in dBm and quantized in 0.5 dBm
             steps ranging from -64 dBm (encoded 0x00) to 63.5 dBm
             (encoded 0xFF). Values outside this range shall be assigned
             the closest extreme. This parameter is only applicable to
             systems supporting the OFDM or OFDMA PHY."
        REFERENCE
            "Subclause 11.8.3.2 in IEEE Std 802.16-2004"
        ::= { wmanIf2BsRegisteredSsEntry 20 }

wmanIf2BsSsMaxTxPowerQpsk OBJECT-TYPE
        SYNTAX      WmanIf2MaxTxPowerType                         
        MAX-ACCESS  read-only
        STATUS      current
        DESCRIPTION
            "The maximum available power for QPSK. The maximum power
             parameters are reported in dBm and quantized in 0.5 dBm
             steps ranging from -64 dBm (encoded 0x00) to 63.5 dBm
             (encoded 0xFF). Values outside this range shall be assigned
             to closest extreme. This parameter is only applicable to
             systems supporting the OFDM or OFDMA PHY."
        REFERENCE
            "Subclause 11.8.3.2 in IEEE Std 802.16-2004"
        ::= { wmanIf2BsRegisteredSsEntry 21 }
        
wmanIf2BsSsMaxTxPower16Qam OBJECT-TYPE
        SYNTAX      WmanIf2MaxTxPowerType                         
        MAX-ACCESS  read-only
        STATUS      current
        DESCRIPTION
            "The maximum available power for 16-QAM constellations.
             The maximum power parameters are reported in dBm and
             quantized in 0.5 dBm steps ranging from -64 dBm (encoded
             0x00) to 63.5 dBm (encoded 0xFF). Values outside this
             range shall be assigned the closest extreme. This parameter
             is only applicable to systems supporting the OFDM or
             OFDMA PHY."
        REFERENCE
            "Subclause 11.8.3.2 in IEEE Std 802.16-2004"
        ::= { wmanIf2BsRegisteredSsEntry 22 }
        
wmanIf2BsSsMaxTxPower64Qam OBJECT-TYPE
        SYNTAX      WmanIf2MaxTxPowerType                         
        MAX-ACCESS  read-only
        STATUS      current
        DESCRIPTION
            "The maximum available power for 64-QAM constellations.
             The maximum power parameters are reported in dBm and
             quantized in 0.5 dBm steps ranging from -64 dBm (encoded
             0x00) to 63.5 dBm (encoded 0xFF). Values outside this
             range shall be assigned the closest extreme. SSs that do
             not support QAM64 shall report the value of 0x00. This
             parameter is only applicable to systems supporting the OFDM
             or OFDMA PHY."
        REFERENCE
            "Subclause 11.8.3.2 in IEEE Std 802.16-2004"
        ::= { wmanIf2BsRegisteredSsEntry 23 }
                
wmanIf2BsSsMacVersion OBJECT-TYPE
        SYNTAX      WmanIf2MacVersion                         
        MAX-ACCESS  read-only
        STATUS      current
        DESCRIPTION
            "This parameter specifies the version of 802.16 to which the
             message originator conforms."
        REFERENCE
            "Subclause 11.1.3 in IEEE Std 802.16-2004"
        ::= { wmanIf2BsRegisteredSsEntry 24 }  
               
--
-- wmanIf2BsConfigurationTable contains global parameters common in BS       
--
wmanIf2BsConfigurationTable OBJECT-TYPE
        SYNTAX      SEQUENCE OF WmanIf2BsConfigurationEntry
        MAX-ACCESS  not-accessible
        STATUS      current
        DESCRIPTION
            "This table provides one row for each BS sector that
             contains the BS system parameters as defined in Subclause
             10.1 of [3]. The objects in this table define the default
             behaviour of the BS for 2nd Management connection
             scheduling and SFID allocation as well as configuration
             parameters of the CPS scheduler and AAS system."
        REFERENCE
            "Subclause 10.1, Table 342 in IEEE Std 802.16e-2005"
        ::= { wmanIf2BsCm 2 }

wmanIf2BsConfigurationEntry OBJECT-TYPE
        SYNTAX      WmanIf2BsConfigurationEntry
        MAX-ACCESS  not-accessible
        STATUS      current
        DESCRIPTION
            ""
        INDEX     { ifIndex }
        ::= { wmanIf2BsConfigurationTable 1 }

WmanIf2BsConfigurationEntry ::= SEQUENCE {
        wmanIf2BsDcdInterval                    INTEGER,
        wmanIf2BsUcdInterval                    INTEGER,
        wmanIf2BsUcdTransition                  INTEGER,
        wmanIf2BsDcdTransition                  INTEGER,
        wmanIf2BsInitialRangingInterval         INTEGER,
        wmanIf2BsSsULMapProcTime                Unsigned32,
        wmanIf2BsSsRangRespProcTime             Unsigned32,
        wmanIf2BsT9Timeout                      INTEGER,
        wmanIf2BsT13Timeout                     INTEGER,
        wmanIf2BsT15Timeout                     INTEGER,
        wmanIf2BsT17Timeout                     INTEGER,
        wmanIf2BsT27IdleTimer                   Unsigned32,
        wmanIf2BsT27ActiveTimer                 Unsigned32,
        wmanIf2Bs2ndMgmtDlQoSProfileIndex       INTEGER,
        wmanIf2Bs2ndMgmtUlQoSProfileIndex       INTEGER,
        wmanIf2BsAutoSfidEnabled                INTEGER,
        wmanIf2BsAutoSfidRangeMin               Unsigned32,
        wmanIf2BsAutoSfidRangeMax               Unsigned32,
        wmanIf2BsAasChanFbckReqFreq             INTEGER,
        wmanIf2BsAasBeamSelectFreq              INTEGER,
        wmanIf2BsAasChanFbckReqResolution       INTEGER,
        wmanIf2BsAasBeamReqResolution           INTEGER,
        wmanIf2BsAasNumOptDiversityZones        INTEGER,
        wmanIf2BsResetSector                    INTEGER,
        wmanIf2BsSaChallengeTimer               INTEGER,
        wmanIf2BsSaChallengeMaxResends          INTEGER,
        wmanIf2BsSaTekTimer                     INTEGER,
        wmanIf2BsSaTekReqMaxResends             INTEGER,
        wmanIf2Bs2ndEapTimeout                  INTEGER,
        wmanIf2BsEapCompleteResends             INTEGER,
        wmanIf2BsInvitedRangRetries             INTEGER,
        wmanIf2BsDSxReqRetries                  Unsigned32,
        wmanIf2BsDSxRespRetries                 Unsigned32,
        wmanIf2BsT7Timeout                      INTEGER,
        wmanIf2BsT8Timeout                      INTEGER,
        wmanIf2BsT10Timeout                     INTEGER,
        wmanIf2BsT22Timeout                     INTEGER}

wmanIf2BsDcdInterval OBJECT-TYPE        
        SYNTAX      INTEGER (0..10000)
        UNITS       "milliseconds"
        MAX-ACCESS  read-write
        STATUS      current
        DESCRIPTION
            "Time between transmission of DCD messages in ms."
        ::= { wmanIf2BsConfigurationEntry 1 }

wmanIf2BsUcdInterval OBJECT-TYPE
        SYNTAX      INTEGER (0..10000)
        UNITS       "milliseconds"
        MAX-ACCESS  read-write
        STATUS      current
        DESCRIPTION
            "Time between transmission of UCD messages in ms."
        ::= { wmanIf2BsConfigurationEntry 2 }

wmanIf2BsUcdTransition OBJECT-TYPE
        SYNTAX      INTEGER (2..65535)
        UNITS       "Number of MAC Frames"
        MAX-ACCESS  read-write
        STATUS      current
        DESCRIPTION
            "The number of frames from the end of the frame carrying
             the UCD message the BS shall wait after transmitting a
             UCD message with an incremented Configuration Change
             Count before issuing a UL-MAP message referring to
             Uplink_Burst_Profiles defined in that UCD message.
             Minimum value = 20ms following the last fragment of the
             message"
        ::= { wmanIf2BsConfigurationEntry 3 }
                                
wmanIf2BsDcdTransition OBJECT-TYPE
        SYNTAX      INTEGER (2..65535)
        UNITS       "Number of MAC Frames"
        MAX-ACCESS  read-write
        STATUS      current
        DESCRIPTION
            "The number of frames from the end of the frame carrying
             the DCD message the BS shall wait after transmitting a
             DCD message with an incremented Configuration Change
             Count before issuing a DL-MAP message referring to
             Downlink_Burst_Profiles defined in that DCD message.
             Minimum value = 20ms following the last fragment of the
             message"
        ::= { wmanIf2BsConfigurationEntry 4 }

wmanIf2BsInitialRangingInterval OBJECT-TYPE
        SYNTAX      INTEGER(0..2000)
        UNITS       "milliseconds"
        MAX-ACCESS  read-write
        STATUS      current
        DESCRIPTION
            "Time between Initial Ranging regions assigned by the BS
             in ms."
        ::= { wmanIf2BsConfigurationEntry 5 }

wmanIf2BsSsULMapProcTime OBJECT-TYPE
        SYNTAX      Unsigned32 (200 .. 4294967295) 
        UNITS       "micro seconds"
        MAX-ACCESS  read-write
        STATUS      current
        DESCRIPTION
            "Time provided between arrival of the last bit of a UL-MAP
             at an SS and effectiveness of that map in us. For OFDMA
             mode, the time shall be counted starting from the end of
             the burst carrying the UL-MAP.
             Minimum value: SC = 200us
                            OFDM = 1ms
                            OFDMA = frame duration"
        ::= { wmanIf2BsConfigurationEntry 6 }

wmanIf2BsSsRangRespProcTime OBJECT-TYPE
        SYNTAX      Unsigned32 (10000 .. 4294967295)
        UNITS       "micro seconds"
        MAX-ACCESS  read-write
        STATUS      current
        DESCRIPTION
            "Time allowed for an SS following receipt of a ranging
             response before it is expected to reply to an invited
             ranging request in us."
        ::= { wmanIf2BsConfigurationEntry 7 }

wmanIf2BsT9Timeout OBJECT-TYPE
        SYNTAX      INTEGER (300 .. 65535)
        UNITS       "milliseconds"
        MAX-ACCESS  read-write
        STATUS      current
        DESCRIPTION
        	"Registration Timeout, the time allowed between the BS
        	 sending a RNG-RSP (success) to an SS, and receiving a
        	 SBC-REQ from that same SS in ms."
        ::= { wmanIf2BsConfigurationEntry 9 }

wmanIf2BsT13Timeout OBJECT-TYPE
        SYNTAX      INTEGER (15 .. 65535)
        UNITS       "minutes"
        MAX-ACCESS  read-write
        STATUS      current
        DESCRIPTION
            "The time allowed for an SS, following receipt of a
             REG-RSP message to send a TFTP-CPLT message to the BS
             in min."
        ::= { wmanIf2BsConfigurationEntry 10 }

wmanIf2BsT15Timeout OBJECT-TYPE
        SYNTAX      INTEGER (20 .. 65535)
        UNITS       "milliseconds"
        MAX-ACCESS  read-write
        STATUS      current
        DESCRIPTION
            "Wait for MCA-RSP in ms."
        ::= { wmanIf2BsConfigurationEntry 11 }

wmanIf2BsT17Timeout OBJECT-TYPE
        SYNTAX      INTEGER (5 .. 65535)
        UNITS       "minutes"
        MAX-ACCESS  read-write
        STATUS      current
        DESCRIPTION
            "Time allowed for SS to complete SS Authorization and
             Key Exchange in minutes."
        ::= { wmanIf2BsConfigurationEntry 12 }

wmanIf2BsT27IdleTimer OBJECT-TYPE
        SYNTAX      Unsigned32 (10000 .. 4294967295)
        UNITS       "microsecond"
        MAX-ACCESS  read-write
        STATUS      current
        DESCRIPTION
            "Maximum time between unicast grants to SS when BS believes 
             SS uplink transmission quality is good enough."
        ::= { wmanIf2BsConfigurationEntry 13 }

wmanIf2BsT27ActiveTimer OBJECT-TYPE
        SYNTAX      Unsigned32 (10000 .. 4294967295)
        UNITS       "microsecond"
        MAX-ACCESS  read-write
        STATUS      current
        DESCRIPTION
            "Maximum time between unicast grants to SS when BS believes 
             SS uplink transmission quality is not good enough."
        ::= { wmanIf2BsConfigurationEntry 14 }

wmanIf2Bs2ndMgmtDlQoSProfileIndex OBJECT-TYPE
        SYNTAX      INTEGER (1..65535)
        MAX-ACCESS  read-write
        STATUS      current
        DESCRIPTION
            "This object defines the index of a row in
             wmanIf2BsServiceClassTable which is used to obtain all QoS
             parameters required for the BS downlink scheduler to
             properly allocate and manage the bandwidth and schedule
             the 2nd Management Connection traffic. The 2nd Management
             Connection traffic doesn't differ from Traffic Connection
             traffic in the area of QoS management."
         ::= { wmanIf2BsConfigurationEntry 15 }

wmanIf2Bs2ndMgmtUlQoSProfileIndex OBJECT-TYPE
        SYNTAX      INTEGER (1..65535)
        MAX-ACCESS  read-write
        STATUS      current
        DESCRIPTION
            "This object defines the index of a row in
             wmanIf2BsServiceClassTable which is used to obtain all QoS
             parameters required for the BS uplink scheduler to
             properly allocate and manage the bandwidth and schedule
             the 2nd Management Connection traffic. The 2nd Management
             Connection traffic doesn't differ from Traffic Connection
             traffic in the area of QoS management."
        ::= { wmanIf2BsConfigurationEntry 16 }

wmanIf2BsAutoSfidEnabled OBJECT-TYPE
        SYNTAX      INTEGER {autoSfidDisabled(0),
                             autoSfidEnabled(1)}
        MAX-ACCESS  read-write
        STATUS      current
        DESCRIPTION
            "This object defines whether the BS is allowed to
             autonomously allocate SFIDs. When the object is set to
             autoSfidEnabled, the BS is allowed to autonomously allocate
             SFIDs from the range of allowed values defined by
             wmanIf2BsConfigExtAutoSfidRangeMin and 
             wmanIf2BsConfigExtAutoSfidRangeMax. A SF is created
             autonomously when it has not been provisioned in the
             wmanIf2BsProvisionedSfTable and may be initiated by either
             the SS or BS. The BS should always initiate SF creation
             based on the provisioned Service flows configured in
             wmanIf2BsProvisionedSfTable."
        REFERENCE
            "Subclause 11.13.1 in IEEE Std 802.16-2004"
         ::= { wmanIf2BsConfigurationEntry 17 }

wmanIf2BsAutoSfidRangeMin OBJECT-TYPE
        SYNTAX      Unsigned32 ( 1 .. 4294967295)
        MAX-ACCESS  read-write
        STATUS      current
        DESCRIPTION
            "This object defines the minimum value of the range of SFID
             values allocated for the BS sector for the purpose of
             autonomous creation of service flows. This value is used
             when the object wmanIf2BsAutoSfidEnabled allows
             autonomous creation of SFIDs."
        REFERENCE
            "Subclause 11.13.1 in IEEE Std 802.16-2004"
        ::= { wmanIf2BsConfigurationEntry 18 }

wmanIf2BsAutoSfidRangeMax OBJECT-TYPE
        SYNTAX      Unsigned32 ( 1 .. 4294967295)
        MAX-ACCESS  read-write
        STATUS      current
        DESCRIPTION
            "This object defines the maximum value of the range of SFID
             values allocated for the BS sector for the purpose of
             autonomous creation of the service flows. This value is
             used when the object wmanIf2BsAutoSfidEnabled allows
             autonomous creation of SFIDs."
        REFERENCE
            "Subclause 11.13.1 in IEEE Std 802.16-2004"
        ::= { wmanIf2BsConfigurationEntry 19 }

wmanIf2BsAasChanFbckReqFreq OBJECT-TYPE
        SYNTAX      INTEGER (5..10000)
        UNITS       "millisecond"
        MAX-ACCESS  read-write
        STATUS      current
        DESCRIPTION
            "This object defines AAS channel feedback request frequency.
             It controls the frequency of downlink beam measurements.
             The relevant MAC messages are AAS-FBCK-REQ/RSP"
        REFERENCE
            "Subclause 6.3.2.3.40 in IEEE Std 802.16-2004"
        ::= { wmanIf2BsConfigurationEntry 20 }

wmanIf2BsAasBeamSelectFreq OBJECT-TYPE
        SYNTAX      INTEGER (5..10000)
        UNITS       "millisecond"
        MAX-ACCESS  read-write
        STATUS      current
        DESCRIPTION
            "This object defines AAS beam select frequency.
             It controls how often SS issues beam select messages.
             The relevant MAC message is AAS_Beam_Select"
        REFERENCE
            "Subclause 6.3.2.3.41 in IEEE Std 802.16-2004"
        ::= { wmanIf2BsConfigurationEntry 21 }

wmanIf2BsAasChanFbckReqResolution OBJECT-TYPE
        SYNTAX      INTEGER {aasChanFbckRes00(0),
                             aasChanFbckRes01(1),
                             aasChanFbckRes10(2),
                             aasChanFbckRes11(3)}
        MAX-ACCESS  read-write
        STATUS      current
        DESCRIPTION
            "This object defines AAS feedback request frequency
             measurements resolution. It is coded as follows:
             aasChanFbckRes00 - every 4th carrier
                                (-100, -96, -92, .., 100)
             aasChanFbckRes01 - every 8th carrier
                                (-100, -92, -84, .., 100)
             aasChanFbckRes10 - every 16th carrier
                                (-100, -84, -68, .., 100)
             aasChanFbckRes11 - every 32th carrier
                                (-100, -68, -36, .., 100)"
        REFERENCE
            "Subclause 8.3.6.4 in IEEE Std 802.16-2004"
        ::= { wmanIf2BsConfigurationEntry 22 }

wmanIf2BsAasBeamReqResolution OBJECT-TYPE
        SYNTAX      INTEGER {aasBeamReqRes000(0),
                             aasBeamReqRes001(1),
                             aasBeamReqRes010(2),
                             aasBeamReqRes011(3),
                             aasBeamReqRes100(4)}
        MAX-ACCESS  read-write
        STATUS      current
        DESCRIPTION
            "This object defines AAS beam select request resolution
             parameter. It is coded as follows:
             aasBeamReqRes000 - every 4th carrier
             aasBeamReqRes001 - every 8th carrier
             aasBeamReqRes010 - every 16th carrier
             aasBeamReqRes011 - every 32th carrier
             aasBeamReqRes100 - every 64th carrier"
        REFERENCE
            "Subclause 8.3.6.5 in IEEE Std 802.16-2004"
        ::= { wmanIf2BsConfigurationEntry 23 }

wmanIf2BsAasNumOptDiversityZones OBJECT-TYPE
        SYNTAX      INTEGER (0..65535)
        MAX-ACCESS  read-write
        STATUS      current
        DESCRIPTION
            "This object defines the number of optional diversity zones
             transmitted in downlink."
        REFERENCE
            "Figure 209 in IEEE Std 802.16-2004"
        ::= { wmanIf2BsConfigurationEntry 24 }

wmanIf2BsResetSector OBJECT-TYPE
        SYNTAX      INTEGER {noAction(0),
                             sectorReset(1)}
        MAX-ACCESS  read-write
        STATUS      current
        DESCRIPTION 
            "This object should be implemented as follows:
             - When set to actionsResetSector value, instructs BS to
               reset the sector identified by ifIndex. As a result of
               this action the PHY and MAC of this sector should be
               reinitialised.
             - When set to value different than actionsResetSector it
               should be ignored
             - When read it should return actionsResetSectorNoAction"
        ::= { wmanIf2BsConfigurationEntry 25 }

wmanIf2BsSaChallengeTimer OBJECT-TYPE
        SYNTAX      INTEGER (500 .. 2000)
        UNITS       "milliseconds"
        MAX-ACCESS  read-write
        STATUS      current
        DESCRIPTION
            "Time prior to re-send of SATEK-Challenge."
        DEFVAL      { 1000 }
        ::= { wmanIf2BsConfigurationEntry 27 }

wmanIf2BsSaChallengeMaxResends OBJECT-TYPE
        SYNTAX      INTEGER (1 .. 3)
        MAX-ACCESS  read-write
        STATUS      current
        DESCRIPTION
            "Maximum number of transmissions of SA-TEK-Challenge."
        DEFVAL      { 3 }
        ::= { wmanIf2BsConfigurationEntry 28 }

wmanIf2BsSaTekTimer OBJECT-TYPE
        SYNTAX      INTEGER (100 .. 1000)
        UNITS       "milliseconds"
        MAX-ACCESS  read-write
        STATUS      current
        DESCRIPTION
            "Time prior to re-send of SATEK-Request."
        DEFVAL      { 300 }
        ::= { wmanIf2BsConfigurationEntry 29 }

wmanIf2BsSaTekReqMaxResends OBJECT-TYPE
        SYNTAX      INTEGER (1 .. 3)
        MAX-ACCESS  read-write
        STATUS      current
        DESCRIPTION
            "Maximum number of transmissions of SA-TEK-Request."
        DEFVAL      { 3 }
        ::= { wmanIf2BsConfigurationEntry 30 }

wmanIf2Bs2ndEapTimeout OBJECT-TYPE
        SYNTAX      INTEGER (300 .. 1000)
        UNITS       "milliseconds"
        MAX-ACCESS  read-write
        STATUS      current
        DESCRIPTION
            "Time, in seconds, to wait for PKMv2_EAP_Start or
             PKMv2_Authenticated_EAP_Start after the success of the
             first EAP in double EAP mode."
        DEFVAL      { 1000 }
        ::= { wmanIf2BsConfigurationEntry 31 }

wmanIf2BsEapCompleteResends OBJECT-TYPE
        SYNTAX      INTEGER (1 .. 3)
        MAX-ACCESS  read-write
        STATUS      current
        DESCRIPTION
            "Total number of sending PKMv2_EAP_Complete message in
             double EAP mode."
        DEFVAL      { 3 }
        ::= { wmanIf2BsConfigurationEntry 32 }

wmanIf2BsInvitedRangRetries OBJECT-TYPE
        SYNTAX      INTEGER (16..65535)
        MAX-ACCESS  read-write
        STATUS      current
        DESCRIPTION
            "Number of retries on inviting Ranging Requests."
        ::= { wmanIf2BsConfigurationEntry 33 }

wmanIf2BsDSxReqRetries OBJECT-TYPE
        SYNTAX      Unsigned32
        MAX-ACCESS  read-write
        STATUS      current
        DESCRIPTION
            "Number of Timeout Retries on DSA/DSC/DSD Requests."
        DEFVAL      { 3 }
        ::= { wmanIf2BsConfigurationEntry 34 }

wmanIf2BsDSxRespRetries OBJECT-TYPE
        SYNTAX      Unsigned32
        MAX-ACCESS  read-write
        STATUS      current
        DESCRIPTION
            "Number of Timeout Retries on DSA/DSC/DSD Responses."
        DEFVAL      { 3 }
        ::= { wmanIf2BsConfigurationEntry 35 }

wmanIf2BsT7Timeout OBJECT-TYPE
        SYNTAX      INTEGER (0 .. 1000)
        UNITS       "milliseconds"
        MAX-ACCESS  read-write
        STATUS      current
        DESCRIPTION
            "Wait for DSA/DSC/DSD Response Timeout in ms."
        ::= { wmanIf2BsConfigurationEntry 36 }

wmanIf2BsT8Timeout OBJECT-TYPE
        SYNTAX      INTEGER (0 .. 300)
        UNITS       "milliseconds"
        MAX-ACCESS  read-write
        STATUS      current
        DESCRIPTION
            "Wait for DSA/DSC/DSD Acknowledge Timeout in ms."
        ::= { wmanIf2BsConfigurationEntry 37 }

wmanIf2BsT10Timeout OBJECT-TYPE
        SYNTAX      INTEGER (0 .. 3000)
        UNITS       "milliseconds"
        MAX-ACCESS  read-write
        STATUS      current
        DESCRIPTION
            "Wait for Transaction End timeout in ms."
        ::= { wmanIf2BsConfigurationEntry 38 }

wmanIf2BsT22Timeout OBJECT-TYPE
        SYNTAX      INTEGER (0 .. 500)
        UNITS       "milliseconds"
        MAX-ACCESS  read-write
        STATUS      current
        DESCRIPTION
            "Wait for ARQ Reset in ms."
        ::= { wmanIf2BsConfigurationEntry 39 }

wmanIf2BsSsReqCapabilitiesTable OBJECT-TYPE
        SYNTAX      SEQUENCE OF WmanIf2BsSsReqCapabilitiesEntry
        MAX-ACCESS  not-accessible
        STATUS      current
        DESCRIPTION
            "This table contains the basic capability information of SSs
             that have been reported by SSs to BS using RNG-REQ, SBC-REQ
             and REG-REQ messages. Entries in this table should be
             created when an SS registers with a BS."
        ::= { wmanIf2BsCm 3 }

wmanIf2BsSsReqCapabilitiesEntry OBJECT-TYPE
        SYNTAX      WmanIf2BsSsReqCapabilitiesEntry
        MAX-ACCESS  not-accessible
        STATUS      current
        DESCRIPTION
            "This table provides one row for each SS that has been
             registered in the BS. This table augments the table 
             wmanIf2BsRegisteredSsTable."
        AUGMENTS { wmanIf2BsRegisteredSsEntry }
        ::= { wmanIf2BsSsReqCapabilitiesTable 1 }

WmanIf2BsSsReqCapabilitiesEntry ::= SEQUENCE {        
        wmanIf2BsSsReqCapUplinkCidSupport       WmanIf2NumOfCid,
        wmanIf2BsSsReqCapDsxFlowControl         WmanIf2MaxDsxFlowType,
        wmanIf2BsSsReqCapMcaFlowControl         WmanIf2MaxMcaFlowType,
        wmanIf2BsSsReqCapMcpGroupCidSupport     WmanIf2MaxMcpGroupCid,
        wmanIf2BsSsReqCapPkmFlowControl         WmanIf2MaxPkmFlowType,
        wmanIf2BsSsReqCapMaxNumOfSupportedSA    WmanIf2MaxNumOfSaType,
        wmanIf2BsSsReqCapMaxNumOfClassifier     WmanIf2MaxClassifiers,        
        wmanIf2BsSsReqCapTtgTransitionGap       WmanIf2SsTransitionGap,
        wmanIf2BsSsReqCapRtgTransitionGap       WmanIf2SsTransitionGap,
        wmanIf2BsSsReqCapDownlinkCidSupport     WmanIf2NumOfCid,         
        wmanIf2BsSsReqCapMaxNumBurstToMs        WmanIf2MaxNumBurstTx,
        wmanIf2BsSsReqCapMaxMacLevelDlFrame     WmanIf2MaxMacLevel,
        wmanIf2BsSsReqCapMaxMacLevelUlFrame     WmanIf2MaxMacLevel,
        wmanIf2BsSsReqCapPnWindowSize           INTEGER,
        wmanIf2BsSsOfdmReqCapLoopPwrControlSw   Unsigned32,
        wmanIf2BsSsOfdmaReqCapSdmaPilot         WmanIf2SdmaPilotCap,
        wmanIf2BsSsOfdmaReqCapNoUlHarqChannel   WmanIf2OfdmaNoHarqChan,
        wmanIf2BsSsOfdmaReqCapNoDlHarqChannel   WmanIf2OfdmaNoHarqChan,
        wmanIf2BsSsReqCapOptionsBasic           WmanIf2BasicCapOptions,
        wmanIf2BsSsReqCapOptionsOfdm            WmanIf2OfdmCapOptions,
        wmanIf2BsSsReqCapOptionsOfdma           WmanIf2OfdmaCapOptions}
        
wmanIf2BsSsReqCapUplinkCidSupport OBJECT-TYPE
        SYNTAX      WmanIf2NumOfCid
        MAX-ACCESS  read-only
        STATUS      current
        DESCRIPTION 
           "This object shows the number of Uplink transport CIDs the SS
            can support."
        REFERENCE
           "Subclause 11.7.6.1"
        ::= { wmanIf2BsSsReqCapabilitiesEntry 1 }
        
wmanIf2BsSsReqCapDsxFlowControl OBJECT-TYPE
        SYNTAX      WmanIf2MaxDsxFlowType
        MAX-ACCESS  read-only
        STATUS      current
        DESCRIPTION
            "This object specifies the maximum number of concurrent
             DSA, DSC, or DSD transactions that SS is capable of having
             outstanding."
        DEFVAL		{ 0 }
        ::= { wmanIf2BsSsReqCapabilitiesEntry 2 }
        
wmanIf2BsSsReqCapMcaFlowControl OBJECT-TYPE
        SYNTAX      WmanIf2MaxMcaFlowType
        MAX-ACCESS  read-only
        STATUS      current
        DESCRIPTION
            "This object specifies the maximum number of concurrent MCA
             transactions that SS is capable of having outstanding."
        DEFVAL		{ 0 }
        ::= { wmanIf2BsSsReqCapabilitiesEntry 3 }
        
wmanIf2BsSsReqCapMcpGroupCidSupport OBJECT-TYPE
        SYNTAX      WmanIf2MaxMcpGroupCid
        MAX-ACCESS  read-only
        STATUS      current
        DESCRIPTION
            "This object indicates the maximum number of
             simultaneous Multicast Polling Groups the SS is
             capable of belonging to."
        DEFVAL		{ 0 }    
        ::= { wmanIf2BsSsReqCapabilitiesEntry 4 }
        
wmanIf2BsSsReqCapPkmFlowControl OBJECT-TYPE
        SYNTAX      WmanIf2MaxPkmFlowType
        MAX-ACCESS  read-only
        STATUS      current
        DESCRIPTION
            "This object specifies the maximum number of concurrent PKM
             transactions that SS is capable of having outstanding."
        DEFVAL		{ 0 }
        ::= { wmanIf2BsSsReqCapabilitiesEntry 5 }
                
wmanIf2BsSsReqCapMaxNumOfSupportedSA OBJECT-TYPE
        SYNTAX      WmanIf2MaxNumOfSaType
        MAX-ACCESS  read-only
        STATUS      current
        DESCRIPTION
            "This field specifies the maximum number of supported
             security associations of the SS."
        DEFVAL		{ 1 }
        ::= { wmanIf2BsSsReqCapabilitiesEntry 6 }
                                                                                
wmanIf2BsSsReqCapMaxNumOfClassifier OBJECT-TYPE
        SYNTAX      WmanIf2MaxClassifiers
        MAX-ACCESS  read-only
        STATUS      current
        DESCRIPTION
            "This object indicates the maximum number of admitted
             Classifiers that the SS can support."
        DEFVAL      { 0 }
        ::= { wmanIf2BsSsReqCapabilitiesEntry 7 }

wmanIf2BsSsReqCapTtgTransitionGap OBJECT-TYPE
        SYNTAX      WmanIf2SsTransitionGap
        UNITS       "microsecond"
        MAX-ACCESS  read-only
        STATUS      current
        DESCRIPTION
            "This field indicates the SS's transition speed SSTTG
             for TDD and H-FDD SSs. The usage is defined by
             WmanIf2SsTransitionGap."
        ::= { wmanIf2BsSsReqCapabilitiesEntry 8 }

wmanIf2BsSsReqCapRtgTransitionGap OBJECT-TYPE
        SYNTAX      WmanIf2SsTransitionGap
        UNITS       "microsecond"
        MAX-ACCESS  read-only
        STATUS      current
        DESCRIPTION
            "This field indicates the SS's transition speed SSRTG
             for TDD and H-FDD SSs. The usage is defined by
             WmanIf2SsTransitionGap."
        ::= { wmanIf2BsSsReqCapabilitiesEntry 9 }

wmanIf2BsSsReqCapDownlinkCidSupport OBJECT-TYPE
        SYNTAX      WmanIf2NumOfCid
        MAX-ACCESS  read-only
        STATUS      current
        DESCRIPTION 
           "This object shows the number of Downlink transport CIDs the
            SS can support."
        REFERENCE
           "Subclause 11.7.6.1"
        ::= { wmanIf2BsSsReqCapabilitiesEntry 10 }

wmanIf2BsSsReqCapMaxNumBurstToMs OBJECT-TYPE
        SYNTAX      WmanIf2MaxNumBurstTx 
        MAX-ACCESS  read-only
        STATUS      current
        DESCRIPTION 
            "Maximum number of bursts transmitted concurrently to the MS
            , including all bursts without CID or with CIDs matching
             the MS's CIDs."
        REFERENCE
            "Subclause 11.7.8.9"
        ::= { wmanIf2BsSsReqCapabilitiesEntry 11 }

wmanIf2BsSsReqCapMaxMacLevelDlFrame OBJECT-TYPE
        SYNTAX      WmanIf2MaxMacLevel
        MAX-ACCESS  read-only
        STATUS      current
        DESCRIPTION 
           "Maximum amount of MAC level data the MS is capable of
            processing per DL frame."
        REFERENCE
            "Subclause 11.7.8.6"
        DEFVAL      { 0 }
        ::= { wmanIf2BsSsReqCapabilitiesEntry 12 }

wmanIf2BsSsReqCapMaxMacLevelUlFrame OBJECT-TYPE
        SYNTAX      WmanIf2MaxMacLevel
        MAX-ACCESS  read-only
        STATUS      current
        DESCRIPTION 
           "Maximum amount of MAC level data the MS is capable of
            processing per UL frame."
        REFERENCE
            "Subclause 11.7.8.10.6"
        DEFVAL      { 0 }
        ::= { wmanIf2BsSsReqCapabilitiesEntry 13 }                             
        
wmanIf2BsSsReqCapPnWindowSize OBJECT-TYPE
        SYNTAX      INTEGER (0 .. 65535)
        MAX-ACCESS  read-only
        STATUS      current
        DESCRIPTION 
           "Specifies the size capability of the receiver PN window for
            SAs and management connections. The receiver shall track
            PNs within this window to prevent replay attacks (see
            7.5.1.2.4)."
        REFERENCE
            "Subclause 11.8.4.4 in IEEE Std 802.16e-2005"
        ::= { wmanIf2BsSsReqCapabilitiesEntry 14 }
        
wmanIf2BsSsOfdmReqCapLoopPwrControlSw OBJECT-TYPE
        SYNTAX      Unsigned32
        MAX-ACCESS  read-only
        STATUS      current
        DESCRIPTION
            "This field indicates he minimum number of frames that SS
             takes to switch from the open loop power control scheme to
             the closed loop power control scheme or vice versa."
        ::= { wmanIf2BsSsReqCapabilitiesEntry 15 }

wmanIf2BsSsOfdmaReqCapSdmaPilot OBJECT-TYPE
        SYNTAX      WmanIf2SdmaPilotCap
        MAX-ACCESS  read-only
        STATUS      current
        DESCRIPTION
            "This field indicates the SDMA pilot pattern support for AMC
             zone."
        REFERENCE
            "Subclause 11.8.3.7.17"
        ::= { wmanIf2BsSsReqCapabilitiesEntry 16 }

wmanIf2BsSsOfdmaReqCapNoUlHarqChannel OBJECT-TYPE
        SYNTAX      WmanIf2OfdmaNoHarqChan
        MAX-ACCESS  read-only
        STATUS      current
        DESCRIPTION
            "This field specifies the number of uplink H-ARQ channels
            (n) the SS supports, where n = 1..16. The value of this
            object should be 0..15."
        ::= { wmanIf2BsSsReqCapabilitiesEntry 17 }

wmanIf2BsSsOfdmaReqCapNoDlHarqChannel OBJECT-TYPE
        SYNTAX      WmanIf2OfdmaNoHarqChan
        MAX-ACCESS  read-only
        STATUS      current
        DESCRIPTION
            "This field specifies the number of downlink H-ARQ channels
            (n) the SS supports, where n = 1..16. The value of this
            object should be 0..15."
        ::= { wmanIf2BsSsReqCapabilitiesEntry 18 }

wmanIf2BsSsReqCapOptionsBasic OBJECT-TYPE
        SYNTAX      WmanIf2BasicCapOptions
        MAX-ACCESS  read-only
        STATUS      current
        DESCRIPTION
            "Combined BITS encoded general capability options as
             reported by SS."
        ::= { wmanIf2BsSsReqCapabilitiesEntry 19 }

wmanIf2BsSsReqCapOptionsOfdm OBJECT-TYPE
        SYNTAX      WmanIf2OfdmCapOptions
        MAX-ACCESS  read-only
        STATUS      current
        DESCRIPTION
            "Combined BITS encoded OFDM specific capability options as
             reported by SS."
        ::= { wmanIf2BsSsReqCapabilitiesEntry 20 }

wmanIf2BsSsReqCapOptionsOfdma OBJECT-TYPE
        SYNTAX      WmanIf2OfdmaCapOptions
        MAX-ACCESS  read-only
        STATUS      current
        DESCRIPTION
            "Combined BITS encoded OFDMA specific capability options as
             reported by SS."
        ::= { wmanIf2BsSsReqCapabilitiesEntry 21 }
                        
wmanIf2BsSsRspCapabilitiesTable OBJECT-TYPE
        SYNTAX      SEQUENCE OF WmanIf2BsSsRspCapabilitiesEntry
        MAX-ACCESS  not-accessible
        STATUS      current
        DESCRIPTION
            "This table contains the basic capability information of SSs
             that have been negotiated and agreed between BS and SS via
             RNG-REQ/RSP, SBC-REQ/RSP and REG-REQ/RSP messages. 
             This table augments the wmanIf2BsRegisteredSsTable."
        REFERENCE
            "Subclause 6.3.2.3.7 in IEEE Std 802.16-2004"
        ::= { wmanIf2BsCm 4 }

wmanIf2BsSsRspCapabilitiesEntry OBJECT-TYPE
        SYNTAX      WmanIf2BsSsRspCapabilitiesEntry
        MAX-ACCESS  not-accessible
        STATUS      current
        DESCRIPTION
            "This table provides one row for each SS that has been
             registered in the BS. This table augments the
             wmanIf2BsRegisteredSsTable. "
        AUGMENTS { wmanIf2BsRegisteredSsEntry }
        ::= { wmanIf2BsSsRspCapabilitiesTable 1 }

WmanIf2BsSsRspCapabilitiesEntry ::= SEQUENCE {        
        wmanIf2BsSsRspCapUplinkCidSupport       WmanIf2NumOfCid,
        wmanIf2BsSsRspCapDsxFlowControl         WmanIf2MaxDsxFlowType,
        wmanIf2BsSsRspCapMcaFlowControl         WmanIf2MaxMcaFlowType,
        wmanIf2BsSsRspCapMcpGroupCidSupport     WmanIf2MaxMcpGroupCid,
        wmanIf2BsSsRspCapPkmFlowControl         WmanIf2MaxPkmFlowType,
        wmanIf2BsSsRspCapMaxNumOfSupportedSA    WmanIf2MaxNumOfSaType,
        wmanIf2BsSsRspCapMaxNumOfClassifier     WmanIf2MaxClassifiers,
        wmanIf2BsSsRspCapTtgTransitionGap       WmanIf2SsTransitionGap,
        wmanIf2BsSsRspCapRtgTransitionGap       WmanIf2SsTransitionGap,
        wmanIf2BsSsRspCapDownlinkCidSupport     WmanIf2NumOfCid,
        wmanIf2BsSsRspCapMaxNumBurstToMs        INTEGER,
        wmanIf2BsSsRspCapMaxMacLevelDlFrame     WmanIf2MaxMacLevel,
        wmanIf2BsSsRspCapMaxMacLevelUlFrame     WmanIf2MaxMacLevel,
        wmanIf2BsSsRspCapNumOfProvisionedSf     Unsigned32,
        wmanIf2BsSsRspCapPnWindowSize           INTEGER,
        wmanIf2BsSsOfdmRspCapLoopPwrControlSw   Unsigned32,
        wmanIf2BsSsOfdmaRspCapSdmaPilot         WmanIf2SdmaPilotCap,
        wmanIf2BsSsOfdmaRspCapNoUlHarqChannel   WmanIf2OfdmaNoHarqChan,
        wmanIf2BsSsOfdmaRspCapNoDlHarqChannel   WmanIf2OfdmaNoHarqChan,
        wmanIf2BsSsRspCapOptionsBasic           WmanIf2BasicCapOptions,
        wmanIf2BsSsRspCapOptionsOfdm            WmanIf2OfdmCapOptions,
        wmanIf2BsSsRspCapOptionsOfdma           WmanIf2OfdmaCapOptions}

wmanIf2BsSsRspCapUplinkCidSupport OBJECT-TYPE
        SYNTAX      WmanIf2NumOfCid
        MAX-ACCESS  read-only
        STATUS      current
        DESCRIPTION
            "Negotiated number of Uplink transport CIDs the SS can
             support."
        REFERENCE
           "Subclause 11.7.6.1"
        ::= { wmanIf2BsSsRspCapabilitiesEntry 1 }
        
wmanIf2BsSsRspCapDsxFlowControl OBJECT-TYPE
        SYNTAX      WmanIf2MaxDsxFlowType
        MAX-ACCESS  read-only
        STATUS      current
        DESCRIPTION 
            "Negotiated maximum number of concurrent DSA, DSC, or DSD
             transactions that may be outstanding."
        ::= { wmanIf2BsSsRspCapabilitiesEntry 2 }
        
wmanIf2BsSsRspCapMcaFlowControl OBJECT-TYPE
        SYNTAX      WmanIf2MaxMcaFlowType
        MAX-ACCESS  read-only
        STATUS      current
        DESCRIPTION
            "Negotiated maximum number of concurrent
             MCA transactions that may be outstanding."
        DEFVAL      { 0 }
        ::= { wmanIf2BsSsRspCapabilitiesEntry 3 }
        
wmanIf2BsSsRspCapMcpGroupCidSupport OBJECT-TYPE
        SYNTAX      WmanIf2MaxMcpGroupCid
        MAX-ACCESS  read-only
        STATUS      current
        DESCRIPTION
            "Negotiated maximum number of simultaneous Multicast
             Polling Groups the SS is capable of belonging to."
        DEFVAL      { 0 }    
        ::= { wmanIf2BsSsRspCapabilitiesEntry 4 }
        
wmanIf2BsSsRspCapPkmFlowControl OBJECT-TYPE
        SYNTAX      WmanIf2MaxPkmFlowType
        MAX-ACCESS  read-only
        STATUS      current
        DESCRIPTION
            "Negotiated maximum number of concurrent PKM
             transactions that may be outstanding."
        DEFVAL      { 0 }
        ::= { wmanIf2BsSsRspCapabilitiesEntry 5 }
                
wmanIf2BsSsRspCapMaxNumOfSupportedSA OBJECT-TYPE
        SYNTAX      WmanIf2MaxNumOfSaType
        MAX-ACCESS  read-only
        STATUS      current
        DESCRIPTION
            "Negotiated maximum number of supported security
             association of the SS."
        DEFVAL      { 1 }
        ::= { wmanIf2BsSsRspCapabilitiesEntry 6 }
                                                                                
wmanIf2BsSsRspCapMaxNumOfClassifier OBJECT-TYPE
        SYNTAX      WmanIf2MaxClassifiers
        MAX-ACCESS  read-only
        STATUS      current
        DESCRIPTION
            "Negotiated maximum number of admitted Classifiers
             that the SS is allowed to have."
        DEFVAL      { 0 }
        ::= { wmanIf2BsSsRspCapabilitiesEntry 7 }

wmanIf2BsSsRspCapTtgTransitionGap OBJECT-TYPE
        SYNTAX      WmanIf2SsTransitionGap
        UNITS       "microsecond"
        MAX-ACCESS  read-only
        STATUS      current
        DESCRIPTION
            "This field indicates the negotiated transition speed
             SSTTG for TDD and H-FDD SSs. The usage is defined by
             WmanIf2SsTransitionGap."
        ::= { wmanIf2BsSsRspCapabilitiesEntry 8 }

wmanIf2BsSsRspCapRtgTransitionGap OBJECT-TYPE
        SYNTAX      WmanIf2SsTransitionGap
        UNITS       "microsecond"
        MAX-ACCESS  read-only
        STATUS      current
        DESCRIPTION
            "This field indicates the negotiated transition speed
             SSRTG for TDD and H-FDD SSs. The usage is defined by
             WmanIf2SsTransitionGap."
        ::= { wmanIf2BsSsRspCapabilitiesEntry 9 }

wmanIf2BsSsRspCapDownlinkCidSupport OBJECT-TYPE
        SYNTAX      WmanIf2NumOfCid
        MAX-ACCESS  read-only
        STATUS      current
        DESCRIPTION 
            "This object shows the number of Downlink transport CIDs the
             SS can support."
        REFERENCE
           "Subclause 11.7.6.1"
        ::= { wmanIf2BsSsRspCapabilitiesEntry 10 }

wmanIf2BsSsRspCapMaxNumBurstToMs OBJECT-TYPE
        SYNTAX      INTEGER (1..16) 
        MAX-ACCESS  read-only
        STATUS      current
        DESCRIPTION 
            "Maximum number of bursts transmitted concurrently to the MS
             , including all bursts without CID or with CIDs matching
             the MS CIDs."
        REFERENCE
            "Subclause 11.7.8.9"
        ::= { wmanIf2BsSsRspCapabilitiesEntry 11 }

wmanIf2BsSsRspCapMaxMacLevelDlFrame OBJECT-TYPE
        SYNTAX      WmanIf2MaxMacLevel
        MAX-ACCESS  read-only
        STATUS      current
        DESCRIPTION 
           "Maximum amount of MAC level data the MS is capable of
            processing per DL frame. A value of 0 indicates such
            limitation does not exist, except the limitation of
            the physical medium"
        REFERENCE
            "Subclause 11.7.8.6"
        DEFVAL      { 0 }
        ::= { wmanIf2BsSsRspCapabilitiesEntry 12 }

wmanIf2BsSsRspCapMaxMacLevelUlFrame OBJECT-TYPE
        SYNTAX      WmanIf2MaxMacLevel
        MAX-ACCESS  read-only
        STATUS      current
        DESCRIPTION 
           "Maximum amount of MAC level data the MS is capable of
            processing per UL frame. A value of 0 indicates such
            limitation does not exist, except the limitation of
            the physical medium"
        REFERENCE
            "Subclause 11.7.8.6"
        DEFVAL      { 0 }
        ::= { wmanIf2BsSsRspCapabilitiesEntry 13 }

wmanIf2BsSsRspCapNumOfProvisionedSf OBJECT-TYPE
        SYNTAX      Unsigned32 (0 .. 255) 
        MAX-ACCESS  read-only
        STATUS      current
        DESCRIPTION 
            "When a BS is to transmit multiple DSA transactions for
             provisioned service flows, this object indicates how many
             DSA transactions with provisioned service flows will be
             transmitted."
        REFERENCE
            "Subclause 11.7.19 in IEEE Std 802.16e-2005"
        ::= { wmanIf2BsSsRspCapabilitiesEntry 14 }                             
        
wmanIf2BsSsRspCapPnWindowSize OBJECT-TYPE
        SYNTAX      INTEGER (0 .. 65535)
        MAX-ACCESS  read-only
        STATUS      current
        DESCRIPTION 
           "Specifies the size capability of the receiver PN window for
            SAs and management connections. The receiver shall track
            PNs within this window to prevent replay attacks (see
            7.5.1.2.4)."
        REFERENCE
            "Subclause 11.8.4.4 in IEEE Std 802.16e-2005"
        ::= { wmanIf2BsSsRspCapabilitiesEntry 15 }

wmanIf2BsSsOfdmRspCapLoopPwrControlSw OBJECT-TYPE
        SYNTAX      Unsigned32
        MAX-ACCESS  read-only
        STATUS      current
        DESCRIPTION
            "This field indicates he minimum number of frames that SS
             takes to switch from the open loop power control scheme to
             the closed loop power control scheme or vice versa."
        ::= { wmanIf2BsSsRspCapabilitiesEntry 16 }

wmanIf2BsSsOfdmaRspCapSdmaPilot OBJECT-TYPE
        SYNTAX      WmanIf2SdmaPilotCap
        MAX-ACCESS  read-only
        STATUS      current
        DESCRIPTION
            "This field indicates the SDMA pilot pattern support for AMC
             zone."
        REFERENCE
            "Subclause 11.8.3.7.17"
        ::= { wmanIf2BsSsRspCapabilitiesEntry 17 }

wmanIf2BsSsOfdmaRspCapNoUlHarqChannel OBJECT-TYPE
        SYNTAX      WmanIf2OfdmaNoHarqChan
        MAX-ACCESS  read-only
        STATUS      current
        DESCRIPTION
            "This field specifies the number of uplink H-ARQ channels
            (n) the SS supports, where n = 1..16. The value of this
            object should be 0..15."
        ::= { wmanIf2BsSsRspCapabilitiesEntry 18 }

wmanIf2BsSsOfdmaRspCapNoDlHarqChannel OBJECT-TYPE
        SYNTAX      WmanIf2OfdmaNoHarqChan
        MAX-ACCESS  read-only
        STATUS      current
        DESCRIPTION
            "This field specifies the number of downlink H-ARQ channels
            (n) the SS supports, where n = 1..16. The value of this
            object should be 0..15."
        ::= { wmanIf2BsSsRspCapabilitiesEntry 19 }

wmanIf2BsSsRspCapOptionsBasic OBJECT-TYPE
        SYNTAX      WmanIf2BasicCapOptions
        MAX-ACCESS  read-only
        STATUS      current
        DESCRIPTION
            "Combined BITS encoded general capability options as granted
             by BS for SS."
        ::= { wmanIf2BsSsRspCapabilitiesEntry 20 }

wmanIf2BsSsRspCapOptionsOfdm OBJECT-TYPE
        SYNTAX      WmanIf2OfdmCapOptions
        MAX-ACCESS  read-only
        STATUS      current
        DESCRIPTION
            "Combined BITS encoded OFDM specific capability options as
             granted by BS for SS."
        ::= { wmanIf2BsSsRspCapabilitiesEntry 21 }

wmanIf2BsSsRspCapOptionsOfdma OBJECT-TYPE
        SYNTAX      WmanIf2OfdmaCapOptions
        MAX-ACCESS  read-only
        STATUS      current
        DESCRIPTION
            "Combined BITS encoded OFDMA specific capability options as
             granted by BS for SS."
        ::= { wmanIf2BsSsRspCapabilitiesEntry 22 }
                                        
wmanIf2BsBasicCapabilitiesTable OBJECT-TYPE
        SYNTAX      SEQUENCE OF WmanIf2BsBasicCapabilitiesEntry
        MAX-ACCESS  not-accessible
        STATUS      current
        DESCRIPTION
            "This table contains the basic capabilities of the BS as
             implemented in BS hardware and software. These capabilities
             along with the configuration for them
             (wmanIf2BsCapabilitiesConfigTable) are used for negotiation
             of basic capabilities with SS using RNG-RSP, SBC-RSP and
             REG-RSP messages. The negotiated capabilities are obtained
             by interSubclause of SS raw reported capabilities, BS raw
             capabilities and BS configured capabilities. The objects in
             the table have read-only access. The table is maintained
             by BS."
        ::= { wmanIf2BsCm 5 }

wmanIf2BsBasicCapabilitiesEntry OBJECT-TYPE
        SYNTAX      WmanIf2BsBasicCapabilitiesEntry
        MAX-ACCESS  not-accessible
        STATUS      current
        DESCRIPTION
            "This table provides one row for each BS sector."
        INDEX     { ifIndex }
        ::= { wmanIf2BsBasicCapabilitiesTable 1 }

WmanIf2BsBasicCapabilitiesEntry ::= SEQUENCE {
        wmanIf2BsCapUplinkCidSupport            WmanIf2NumOfCid,
        wmanIf2BsCapDsxFlowControl              WmanIf2MaxDsxFlowType,
        wmanIf2BsCapMcaFlowControl              WmanIf2MaxMcaFlowType,
        wmanIf2BsCapMcpGroupCidSupport          WmanIf2MaxMcpGroupCid,
        wmanIf2BsCapPkmFlowControl              WmanIf2MaxPkmFlowType,
        wmanIf2BsCapMaxNumOfSupportedSA         WmanIf2MaxNumOfSaType,
        wmanIf2BsCapMaxNumOfClassifier          WmanIf2MaxClassifiers,
        wmanIf2BsCapTtgTransitionGap            WmanIf2SsTransitionGap,
        wmanIf2BsCapRtgTransitionGap            WmanIf2SsTransitionGap,
        wmanIf2BsCapDownlinkCidSupport          WmanIf2NumOfCid,
        wmanIf2BsCapMaxNumBurstToMs             INTEGER,
        wmanIf2BsCapMaxMacLevelDlFrame          WmanIf2MaxMacLevel,
        wmanIf2BsCapMaxMacLevelUlFrame          WmanIf2MaxMacLevel,
        wmanIf2BsCapNumOfProvisionedSf          Unsigned32,
        wmanIf2BsCapPnWindowSize                INTEGER,
        wmanIf2BsOfdmCapLoopPwrControlSw        Unsigned32,
        wmanIf2BsOfdmaCapSdmaPilot              WmanIf2SdmaPilotCap,
        wmanIf2BsOfdmaCapNoUlHarqChannel        WmanIf2OfdmaNoHarqChan,
        wmanIf2BsOfdmaCapNoDlHarqChannel        WmanIf2OfdmaNoHarqChan,
        wmanIf2BsCapOptionsBasic                WmanIf2BasicCapOptions,
        wmanIf2BsCapOptionsOfdm                 WmanIf2OfdmCapOptions,
        wmanIf2BsCapOptionsOfdma                WmanIf2OfdmaCapOptions}

wmanIf2BsCapUplinkCidSupport OBJECT-TYPE
        SYNTAX      WmanIf2NumOfCid
        MAX-ACCESS  read-only
        STATUS      current
        DESCRIPTION 
            "This object shows the number of Uplink transport CIDs the
             BS can support per SS."
        REFERENCE
           "Subclause 11.7.6.1"
        ::= { wmanIf2BsBasicCapabilitiesEntry 1 }
        
wmanIf2BsCapDsxFlowControl OBJECT-TYPE
        SYNTAX      WmanIf2MaxDsxFlowType
        MAX-ACCESS  read-only
        STATUS      current
        DESCRIPTION
            "This object specifies the maximum number of concurrent
             DSA, DSC, or DSD transactions that BS allows each SS to
             have outstanding."
        DEFVAL      { 0 }
        ::= { wmanIf2BsBasicCapabilitiesEntry 2 }
        
wmanIf2BsCapMcaFlowControl OBJECT-TYPE
        SYNTAX      WmanIf2MaxMcaFlowType
        MAX-ACCESS  read-only
        STATUS      current
        DESCRIPTION
            "This object specifies the maximum number of concurrent
             MCA transactions that BS allows each SS to have."
        DEFVAL      { 0 }
        ::= { wmanIf2BsBasicCapabilitiesEntry 3 }
        
wmanIf2BsCapMcpGroupCidSupport OBJECT-TYPE
        SYNTAX      WmanIf2MaxMcpGroupCid
        MAX-ACCESS  read-only
        STATUS      current
        DESCRIPTION
            "This object indicates the maximum number of simultaneous
             Multicast Polling Groups the BS allows each SS to belong
             to."
        DEFVAL      { 0 }    
        ::= { wmanIf2BsBasicCapabilitiesEntry 4 }
        
wmanIf2BsCapPkmFlowControl OBJECT-TYPE
        SYNTAX      WmanIf2MaxPkmFlowType
        MAX-ACCESS  read-only
        STATUS      current
        DESCRIPTION
            "This object specifies the maximum number of concurrent
             PKM transactions that BS allows each SS to have."
        DEFVAL      { 0 }
        ::= { wmanIf2BsBasicCapabilitiesEntry 5 }
                
wmanIf2BsCapMaxNumOfSupportedSA OBJECT-TYPE
        SYNTAX      WmanIf2MaxNumOfSaType
        MAX-ACCESS  read-only
        STATUS      current
        DESCRIPTION
            "This field specifies maximum number of supported security
             associations per SS that the BS allows."
        DEFVAL      { 1 }
        ::= { wmanIf2BsBasicCapabilitiesEntry 6 }
                                                                                
wmanIf2BsCapMaxNumOfClassifier OBJECT-TYPE
        SYNTAX      WmanIf2MaxClassifiers
        MAX-ACCESS  read-only
        STATUS      current
        DESCRIPTION
            "This object indicates the maximum number of admitted
             Classifiers per SS that the BS allows."
        DEFVAL      { 0 }
        ::= { wmanIf2BsBasicCapabilitiesEntry 7 }

wmanIf2BsCapTtgTransitionGap OBJECT-TYPE
        SYNTAX      WmanIf2SsTransitionGap
        UNITS       "microsecond"
        MAX-ACCESS  read-only
        STATUS      current
        DESCRIPTION
            "This field indicates the transition speed SSTTG for TDD
             and H-FDD SSs allowed by the BS. The usage is defined by
             WmanIf2SsTransitionGap."
        ::= { wmanIf2BsBasicCapabilitiesEntry 8 }

wmanIf2BsCapRtgTransitionGap OBJECT-TYPE
        SYNTAX      WmanIf2SsTransitionGap
        UNITS       "microsecond"
        MAX-ACCESS  read-only
        STATUS      current
        DESCRIPTION
            "This field indicates the transition speed SSRTG for TDD
             and H-FDD SSs allowed by the BS. The usage is defined
             by WmanIf2SsTransitionGap."
        ::= { wmanIf2BsBasicCapabilitiesEntry 9 }

wmanIf2BsCapDownlinkCidSupport OBJECT-TYPE
        SYNTAX      WmanIf2NumOfCid
        MAX-ACCESS  read-only
        STATUS      current
        DESCRIPTION 
            "This object shows the number of Downlink transport CIDs the
             SS can support."
        REFERENCE
           "Subclause 11.7.6.1"
        ::= { wmanIf2BsBasicCapabilitiesEntry 10 }

wmanIf2BsCapMaxNumBurstToMs OBJECT-TYPE
        SYNTAX      INTEGER (1..16) 
        MAX-ACCESS  read-only
        STATUS      current
        DESCRIPTION 
            "Maximum number of bursts transmitted concurrently to the MS
             , including all bursts without CID or with CIDs matching
             the MS CIDs."
        REFERENCE
            "Subclause 11.7.8.9"
        ::= { wmanIf2BsBasicCapabilitiesEntry 11 }

wmanIf2BsCapMaxMacLevelDlFrame OBJECT-TYPE
        SYNTAX      WmanIf2MaxMacLevel
        MAX-ACCESS  read-only
        STATUS      current
        DESCRIPTION 
           "Maximum amount of MAC level data the MS is capable of
            processing per DL frame. A value of 0 indicates such
            limitation does not exist, except the limitation of
            the physical medium"
        REFERENCE
            "Subclause 11.7.8.6"
        DEFVAL      { 0 }
        ::= { wmanIf2BsBasicCapabilitiesEntry 12 }

wmanIf2BsCapMaxMacLevelUlFrame OBJECT-TYPE
        SYNTAX      WmanIf2MaxMacLevel
        MAX-ACCESS  read-only
        STATUS      current
        DESCRIPTION 
           "Maximum amount of MAC level data the MS is capable of
            processing per UL frame. A value of 0 indicates such
            limitation does not exist, except the limitation of
            the physical medium"
        REFERENCE
            "Subclause 11.7.8.6"
        DEFVAL      { 0 }
        ::= { wmanIf2BsBasicCapabilitiesEntry 13 }

wmanIf2BsCapNumOfProvisionedSf OBJECT-TYPE
        SYNTAX      Unsigned32 (0 .. 255) 
        MAX-ACCESS  read-only
        STATUS      current
        DESCRIPTION 
            "When a BS is to transmit multiple DSA transactions for
             provisioned service flows, this object indicates how many
             DSA transactions with provisioned service flows will be
             transmitted."
        REFERENCE
            "Subclause 11.7.19 in IEEE Std 802.16e-2005"
        ::= { wmanIf2BsBasicCapabilitiesEntry 14 }                             
        
wmanIf2BsCapPnWindowSize OBJECT-TYPE
        SYNTAX      INTEGER (0 .. 65535)
        MAX-ACCESS  read-only
        STATUS      current
        DESCRIPTION 
           "Specifies the size capability of the receiver PN window for
            SAs and management connections. The receiver shall track
            PNs within this window to prevent replay attacks (see
            7.5.1.2.4)."
        REFERENCE
            "Subclause 11.8.4.4 in IEEE Std 802.16e-2005"
        ::= { wmanIf2BsBasicCapabilitiesEntry 15 }

wmanIf2BsOfdmCapLoopPwrControlSw OBJECT-TYPE
        SYNTAX      Unsigned32
        MAX-ACCESS  read-only
        STATUS      current
        DESCRIPTION
            "This field indicates he minimum number of frames that SS
             takes to switch from the open loop power control scheme to
             the closed loop power control scheme or vice versa."
        ::= { wmanIf2BsBasicCapabilitiesEntry 16 }

wmanIf2BsOfdmaCapSdmaPilot OBJECT-TYPE
        SYNTAX      WmanIf2SdmaPilotCap
        MAX-ACCESS  read-only
        STATUS      current
        DESCRIPTION
            "This field indicates the SDMA pilot pattern support for AMC
             zone."
        REFERENCE
            "Subclause 11.8.3.7.17"
        ::= { wmanIf2BsBasicCapabilitiesEntry 17 }

wmanIf2BsOfdmaCapNoUlHarqChannel OBJECT-TYPE
        SYNTAX      WmanIf2OfdmaNoHarqChan
        MAX-ACCESS  read-only
        STATUS      current
        DESCRIPTION
            "This field specifies the number of uplink H-ARQ channels
            (n) the SS supports, where n = 1..16. The value of this
            object should be 0..15."
        ::= { wmanIf2BsBasicCapabilitiesEntry 18 }

wmanIf2BsOfdmaCapNoDlHarqChannel OBJECT-TYPE
        SYNTAX      WmanIf2OfdmaNoHarqChan
        MAX-ACCESS  read-only
        STATUS      current
        DESCRIPTION
            "This field specifies the number of downlink H-ARQ channels
            (n) the SS supports, where n = 1..16. The value of this
            object should be 0..15."
        ::= { wmanIf2BsBasicCapabilitiesEntry 19 }

wmanIf2BsCapOptionsBasic OBJECT-TYPE
        SYNTAX      WmanIf2BasicCapOptions
        MAX-ACCESS  read-only
        STATUS      current
        DESCRIPTION
            "Combined BITS encoded general BS capability options."
        ::= { wmanIf2BsBasicCapabilitiesEntry 20 }

wmanIf2BsCapOptionsOfdm OBJECT-TYPE
        SYNTAX      WmanIf2OfdmCapOptions
        MAX-ACCESS  read-only
        STATUS      current
        DESCRIPTION
            "Combined BITS encoded OFDM specific BS capability options."
        ::= { wmanIf2BsBasicCapabilitiesEntry 21 }

wmanIf2BsCapOptionsOfdma OBJECT-TYPE
        SYNTAX      WmanIf2OfdmaCapOptions
        MAX-ACCESS  read-only
        STATUS      current
        DESCRIPTION
            "Combined BITS encoded OFDMA specific BS capability options.
            "
        ::= { wmanIf2BsBasicCapabilitiesEntry 22 }
                                
wmanIf2BsCapabilitiesConfigTable OBJECT-TYPE
        SYNTAX      SEQUENCE OF WmanIf2BsCapabilitiesConfigEntry
        MAX-ACCESS  not-accessible
        STATUS      current
        DESCRIPTION                                                     
            "This table contains the configuration for basic
             capabilities of BS. The table is intended to be used to
             restrict the Capabilities implemented by BS, for example in
             order to comply with local regulatory requirements. The BS
             should use the configuration along with the implemented
             Capabilities (wmanIf2BsBasicCapabilitiesTable) for
             negotiation of basic capabilities with SS using RNG-RSP,
             SBC-RSP and REG-RSP messages. The negotiated capabilities
             are obtained by interSubclause of SS reported capabilities,
             BS raw capabilities and BS configured capabilities. The
             objects in the table have read-write access. The rows are
             created by BS as a copy of wmanIf2BsBasicCapabilitiesTable
             and can be modified by NMS."
        ::= { wmanIf2BsCm 6 }

wmanIf2BsCapabilitiesConfigEntry OBJECT-TYPE
        SYNTAX      WmanIf2BsCapabilitiesConfigEntry
        MAX-ACCESS  not-accessible
        STATUS      current
        DESCRIPTION
            "This table provides one row for each BS sector."
        INDEX     { ifIndex }
        ::= { wmanIf2BsCapabilitiesConfigTable 1 }

WmanIf2BsCapabilitiesConfigEntry ::= SEQUENCE {
        wmanIf2BsCapCfgUplinkCidSupport         WmanIf2NumOfCid,
        wmanIf2BsCapCfgDsxFlowControl           WmanIf2MaxDsxFlowType,
        wmanIf2BsCapCfgMcaFlowControl           WmanIf2MaxMcaFlowType,
        wmanIf2BsCapCfgMcpGroupCidSupport       WmanIf2MaxMcpGroupCid,
        wmanIf2BsCapCfgPkmFlowControl           WmanIf2MaxPkmFlowType,
        wmanIf2BsCapCfgMaxNumOfSupportedSA      WmanIf2MaxNumOfSaType,
        wmanIf2BsCapCfgMaxNumOfClassifier       WmanIf2MaxClassifiers,
        wmanIf2BsCapCfgTtgTransitionGap         WmanIf2SsTransitionGap,
        wmanIf2BsCapCfgRtgTransitionGap         WmanIf2SsTransitionGap,
        wmanIf2BsCapCfgDownlinkCidSupport       WmanIf2NumOfCid,
        wmanIf2BsCapCfgMaxNumBurstToMs          INTEGER,
        wmanIf2BsCapCfgMaxMacLevelDlFrame       WmanIf2MaxMacLevel,
        wmanIf2BsCapCfgMaxMacLevelUlFrame       WmanIf2MaxMacLevel,
        wmanIf2BsCapCfgNumOfProvisionedSf       Unsigned32,
        wmanIf2BsCapCfgPnWindowSize             INTEGER,
        wmanIf2BsOfdmCapCfgLoopPwrControlSw     Unsigned32,
        wmanIf2BsOfdmaCapCfgSdmaPilot           WmanIf2SdmaPilotCap,
        wmanIf2BsOfdmaCapCfgNoUlHarqChannel     WmanIf2OfdmaNoHarqChan,
        wmanIf2BsOfdmaCapCfgNoDlHarqChannel     WmanIf2OfdmaNoHarqChan,
        wmanIf2BsCapCfgOptionsBasic             WmanIf2BasicCapOptions,
        wmanIf2BsCapCfgOptionsOfdm              WmanIf2OfdmCapOptions,
        wmanIf2BsCapCfgOptionsOfdma             WmanIf2OfdmaCapOptions}

wmanIf2BsCapCfgUplinkCidSupport OBJECT-TYPE
        SYNTAX      WmanIf2NumOfCid
        MAX-ACCESS  read-write
        STATUS      current
        DESCRIPTION 
            "This object shows the configured number of Uplink transport
             CIDs the BS can support per SS."
        REFERENCE
           "Subclause 11.7.6.1"
        ::= { wmanIf2BsCapabilitiesConfigEntry 1 }
        
wmanIf2BsCapCfgDsxFlowControl OBJECT-TYPE
        SYNTAX      WmanIf2MaxDsxFlowType
        MAX-ACCESS  read-write
        STATUS      current
        DESCRIPTION
            "This object specifies the configured maximum number of
             concurrent DSA, DSC, or DSD transactions that BS allows
             each SS to have outstanding."
        DEFVAL      { 0 }
        ::= { wmanIf2BsCapabilitiesConfigEntry 2 }
        
wmanIf2BsCapCfgMcaFlowControl OBJECT-TYPE
        SYNTAX      WmanIf2MaxMcaFlowType
        MAX-ACCESS  read-write
        STATUS      current
        DESCRIPTION
            "This object specifies the maximum number of concurrent
             MCA transactions that BS is configured to allow each SS to
             have."
        DEFVAL      { 0 }
        ::= { wmanIf2BsCapabilitiesConfigEntry 3 }
        
wmanIf2BsCapCfgMcpGroupCidSupport OBJECT-TYPE
        SYNTAX      WmanIf2MaxMcpGroupCid
        MAX-ACCESS  read-write
        STATUS      current
        DESCRIPTION
            "This object indicates the maximum number of simultaneous 
             Multicast Polling Groups the BS is configured to allow
             each SS to belong to."
        DEFVAL      { 0 }    
        ::= { wmanIf2BsCapabilitiesConfigEntry 4 }
        
wmanIf2BsCapCfgPkmFlowControl OBJECT-TYPE
        SYNTAX      WmanIf2MaxPkmFlowType
        MAX-ACCESS  read-write
        STATUS      current
        DESCRIPTION
            "This object specifies the maximum number of concurrent
             PKM transactions that BS is configured to allow each SS
             to have."
        DEFVAL      { 0 }
        ::= { wmanIf2BsCapabilitiesConfigEntry 5 }
                
wmanIf2BsCapCfgMaxNumOfSupportedSA OBJECT-TYPE
        SYNTAX      WmanIf2MaxNumOfSaType
        MAX-ACCESS  read-write
        STATUS      current
        DESCRIPTION
            "This field specifies configured maximum number of supported
             security association per SS."
        DEFVAL      { 1 }
        ::= { wmanIf2BsCapabilitiesConfigEntry 6 }
                                                                                
wmanIf2BsCapCfgMaxNumOfClassifier OBJECT-TYPE
        SYNTAX      WmanIf2MaxClassifiers
        MAX-ACCESS  read-write
        STATUS      current
        DESCRIPTION
            "This object indicates the configured maximum number of
             admitted Classifiers per SS that the BS can support."
        DEFVAL      { 0 }
        ::= { wmanIf2BsCapabilitiesConfigEntry 7 }

wmanIf2BsCapCfgTtgTransitionGap OBJECT-TYPE
        SYNTAX      WmanIf2SsTransitionGap
        UNITS       "microsecond"
        MAX-ACCESS  read-write
        STATUS      current
        DESCRIPTION
            "This field indicates the configured transition speed
             SSTTG for TDD and H-FDD SSs. The usage is defined by
             WmanIf2SsTransitionGap."
        ::= { wmanIf2BsCapabilitiesConfigEntry 8 }

wmanIf2BsCapCfgRtgTransitionGap OBJECT-TYPE
        SYNTAX      WmanIf2SsTransitionGap
        UNITS       "microsecond"
        MAX-ACCESS  read-write
        STATUS      current
        DESCRIPTION
            "This field indicates the configured transition speed
             SSRTG for TDD and H-FDD SSs. The usage is defined by
             WmanIf2SsTransitionGap."
        ::= { wmanIf2BsCapabilitiesConfigEntry 9 }

wmanIf2BsCapCfgDownlinkCidSupport OBJECT-TYPE
        SYNTAX      WmanIf2NumOfCid
        MAX-ACCESS  read-write
        STATUS      current
        DESCRIPTION 
            "This object shows the number of Downlink transport CIDs
             the SS can support."
        REFERENCE
           "Subclause 11.7.6.1"
        ::= { wmanIf2BsCapabilitiesConfigEntry 10 }

wmanIf2BsCapCfgMaxNumBurstToMs OBJECT-TYPE
        SYNTAX      INTEGER (1..16) 
        MAX-ACCESS  read-write
        STATUS      current
        DESCRIPTION 
            "Maximum number of bursts transmitted concurrently to the MS
             , including all bursts without CID or with CIDs matching
             the MS CIDs."
        REFERENCE
            "Subclause 11.7.8.9"
        ::= { wmanIf2BsCapabilitiesConfigEntry 11 }
       
wmanIf2BsCapCfgMaxMacLevelDlFrame OBJECT-TYPE
        SYNTAX      WmanIf2MaxMacLevel
        MAX-ACCESS  read-write
        STATUS      current
        DESCRIPTION 
           "Maximum amount of MAC level data the MS is capable of
            processing per DL frame. A value of 0 indicates such
            limitation does not exist, except the limitation of
            the physical medium"
        REFERENCE
            "Subclause 11.7.8.6"
        DEFVAL      { 0 }
        ::= { wmanIf2BsCapabilitiesConfigEntry 12 }

wmanIf2BsCapCfgMaxMacLevelUlFrame OBJECT-TYPE
        SYNTAX      WmanIf2MaxMacLevel
        MAX-ACCESS  read-write
        STATUS      current
        DESCRIPTION 
           "Maximum amount of MAC level data the MS is capable of
            processing per UL frame. A value of 0 indicates such
            limitation does not exist, except the limitation of
            the physical medium"
        REFERENCE
            "Subclause 11.7.8.6"
        DEFVAL      { 0 }
        ::= { wmanIf2BsCapabilitiesConfigEntry 13 }
        
wmanIf2BsCapCfgNumOfProvisionedSf OBJECT-TYPE
        SYNTAX      Unsigned32 (0 .. 255) 
        MAX-ACCESS  read-write
        STATUS      current
        DESCRIPTION 
            "When a BS is to transmit multiple DSA transactions for
             provisioned service flows, this object indicates how many
             DSA transactions with provisioned service flows will be
             transmitted."
        REFERENCE
            "Subclause 11.7.19 in IEEE Std 802.16e-2005"
        ::= { wmanIf2BsCapabilitiesConfigEntry 14 }                                     
        
wmanIf2BsCapCfgPnWindowSize OBJECT-TYPE
        SYNTAX      INTEGER (0 .. 65535)
        MAX-ACCESS  read-only
        STATUS      current
        DESCRIPTION 
           "Specifies the size capability of the receiver PN window for
            SAs and management connections. The receiver shall track
            PNs within this window to prevent replay attacks (see
            7.5.1.2.4)."
        REFERENCE
            "Subclause 11.8.4.4 in IEEE Std 802.16e-2005"
        ::= { wmanIf2BsCapabilitiesConfigEntry 15 }

wmanIf2BsOfdmCapCfgLoopPwrControlSw OBJECT-TYPE
        SYNTAX      Unsigned32
        MAX-ACCESS  read-only
        STATUS      current
        DESCRIPTION
            "This field indicates he minimum number of frames that SS
             takes to switch from the open loop power control scheme to
             the closed loop power control scheme or vice versa."
        ::= { wmanIf2BsCapabilitiesConfigEntry 16 }

wmanIf2BsOfdmaCapCfgSdmaPilot OBJECT-TYPE
        SYNTAX      WmanIf2SdmaPilotCap
        MAX-ACCESS  read-only
        STATUS      current
        DESCRIPTION
            "This field indicates the SDMA pilot pattern support for AMC
             zone."
        REFERENCE
            "Subclause 11.8.3.7.17"
        ::= { wmanIf2BsCapabilitiesConfigEntry 17 }

wmanIf2BsOfdmaCapCfgNoUlHarqChannel OBJECT-TYPE
        SYNTAX      WmanIf2OfdmaNoHarqChan
        MAX-ACCESS  read-only
        STATUS      current
        DESCRIPTION
            "This field specifies the number of uplink H-ARQ channels
            (n) the SS supports, where n = 1..16. The value of this
            object should be 0..15."
        ::= { wmanIf2BsCapabilitiesConfigEntry 18 }

wmanIf2BsOfdmaCapCfgNoDlHarqChannel OBJECT-TYPE
        SYNTAX      WmanIf2OfdmaNoHarqChan
        MAX-ACCESS  read-only
        STATUS      current
        DESCRIPTION
            "This field specifies the number of downlink H-ARQ channels
            (n) the SS supports, where n = 1..16. The value of this
            object should be 0..15."
        ::= { wmanIf2BsCapabilitiesConfigEntry 19 }

wmanIf2BsCapCfgOptionsBasic OBJECT-TYPE
        SYNTAX      WmanIf2BasicCapOptions
        MAX-ACCESS  read-only
        STATUS      current
        DESCRIPTION
            "Combined BITS encoded general capability options cofigured
             on BS. These object typically restricts availability of BS
             supported features."
        ::= { wmanIf2BsCapabilitiesConfigEntry 20 }

wmanIf2BsCapCfgOptionsOfdm OBJECT-TYPE
        SYNTAX      WmanIf2OfdmCapOptions
        MAX-ACCESS  read-only
        STATUS      current
        DESCRIPTION
            "Combined BITS encoded OFDM specific capability options
             cofigured on BS. These object typically restricts
             availability of BS supported OFDM specific features."
        ::= { wmanIf2BsCapabilitiesConfigEntry 21 }

wmanIf2BsCapCfgOptionsOfdma OBJECT-TYPE
        SYNTAX      WmanIf2OfdmaCapOptions
        MAX-ACCESS  read-only
        STATUS      current
        DESCRIPTION
            "Combined BITS encoded OFDMA specific capability options
             cofigured on BS. These object typically restricts
             availability of BS supported OFDMA specific features."
        ::= { wmanIf2BsCapabilitiesConfigEntry 22 }
                                                                                
wmanIf2BsSsActionsTable OBJECT-TYPE
        SYNTAX      SEQUENCE OF WmanIf2BsSsActionsEntry
        MAX-ACCESS  not-accessible
        STATUS      current
        DESCRIPTION
            "This table contains all the actions specified for SSs in
             the standard. The actions are routed down to SS using
             unsolicited MAC messages: REG-RSP, DREG-REQ and RES-CMD.
             The table also contains the parameters of the actions in
             cases where they are specified by the standard."
        ::= { wmanIf2BsCm 7 }

wmanIf2BsSsActionsEntry OBJECT-TYPE
        SYNTAX      WmanIf2BsSsActionsEntry
        MAX-ACCESS  not-accessible
        STATUS      current
        DESCRIPTION
            "The action can be requested for SS in any state not only
             those registered. However BS will decide whether the action
             is applicable to the SS based on its current state and
             execute it or skip it as defined in each action definition.
             "
        INDEX     { wmanIf2BsSsActionsMacAddress }
        ::= { wmanIf2BsSsActionsTable 1 }

WmanIf2BsSsActionsEntry ::= SEQUENCE {
        wmanIf2BsSsActionsMacAddress            MacAddress,
        wmanIf2BsSsActionsResetSs               INTEGER,
        wmanIf2BsSsActionsAbortSs               INTEGER,
        wmanIf2BsSsActionsOverrideDnFreq        Unsigned32,
        wmanIf2BsSsActionsOverrideChannelId     INTEGER,
        wmanIf2BsSsActionsDeReRegSs             INTEGER,
        wmanIf2BsSsActionsDeReRegSsCode         INTEGER,
        wmanIf2BsSsActionsRowStatus             RowStatus}

wmanIf2BsSsActionsMacAddress OBJECT-TYPE
        SYNTAX      MacAddress
        MAX-ACCESS  not-accessible
        STATUS      current
        DESCRIPTION
            "This object uniquely identifies the SS as an action
             target."
        ::= { wmanIf2BsSsActionsEntry 1 }

wmanIf2BsSsActionsResetSs OBJECT-TYPE
        SYNTAX      INTEGER {actionsResetSsNoAction(0),
                             actionsResetSs(1)}
        MAX-ACCESS  read-create
        STATUS      current
        DESCRIPTION
            "This object should be implemented as follows:
             - When set to actionsResetSs value, instructs BS to send
               RES-CMD to SS
             - When set to value different than actionsResetSs it
               should be ignored
             - When read it should return actionsResetSsNoAction
             The RES-CMD message shall be transmitted by the BS on an
             SS Basic CID to force the SS to reset itself,
             reinitialize its MAC, and repeat initial system access."
        REFERENCE
            "Subclause 6.3.2.3.22 in IEEE Std 802.16-2004"
        ::= { wmanIf2BsSsActionsEntry 2 }

wmanIf2BsSsActionsAbortSs OBJECT-TYPE
        SYNTAX      INTEGER {actionsAbortSsNoAction(0),
                             actionsAbortSs(1),
                             actionAbortSsParams(2)}

        MAX-ACCESS  read-create
        STATUS      current
        DESCRIPTION
            "This object should be implemented as follows:
             - When set to actionsAbortSs value, it instructs BS to send
               unsolicited RNG-RSP with Ranging Status equal to 'abort'
               without override parameters
             - When set to actionAbortSsParams value, it instructs BS to
               send unsolicited RNG-RSP with Ranging Status equal to
               'abort' and with 'Downlink Frequency Override' and
               'Uplink Channel ID Override' parameters.
             - When set to any other value it should be ignored
             - When read it should returned actionsAbortSsNoAction"
        REFERENCE
            "Subclause 11.6, Table 365 in IEEE Std 802.16-2004"
        ::= { wmanIf2BsSsActionsEntry 3 }

wmanIf2BsSsActionsOverrideDnFreq OBJECT-TYPE
        SYNTAX      Unsigned32
        UNITS       "kHz"
        MAX-ACCESS  read-create
        STATUS      current
        DESCRIPTION
            "This object is used as a parmeter of the AbortSs action
             with the code actionAbortSsParams. It is used for licensed
             bands only. It defines the Center frequency, in kHz, of
             new downlink channel where the SS should redo initial
             ranging."
        REFERENCE
            "Subclause 11.6, Table 365 in IEEE Std 802.16-2004"
        ::= { wmanIf2BsSsActionsEntry 4 }

wmanIf2BsSsActionsOverrideChannelId OBJECT-TYPE
        SYNTAX      INTEGER (0..199)
        MAX-ACCESS  read-create
        STATUS      current
        DESCRIPTION
            "This object is used as a parmeter of the AbortSs action
             with the code actionAbortSsParams. It is coded as follows:
             - Licensed bands: The identifier of the uplink channel
               with which the SS is to redo initial ranging (not used
               with PHYs without channelized uplinks).
             - License-exempt bands: The Channel Nr (see 8.5.1) where
               the SS should redo initial ranging."
        REFERENCE
            "Subclause 11.6, Table 365 in IEEE Std 802.16-2004"
        ::= { wmanIf2BsSsActionsEntry 5 }

wmanIf2BsSsActionsDeReRegSs OBJECT-TYPE
        SYNTAX      INTEGER {actionsDeReRegSsNoAction(0),
                             actionsDeReRegSs(1)}
        MAX-ACCESS  read-create
        STATUS      current
        DESCRIPTION
            "This object should be implemented as follows:
             - When set to actionsDeReRegSs value, instructs BS to
               send DREG-CMD to SS with specified action code
             - When set to value different than actionsDeReRegSs it
               should be ignored
             - When read it should return actionsDeReRegSsNoAction
             The DREG-CMD message shall be transmitted by the BS on an
             SS Basic CID to force the SS to change its access state.
             Upon receiving a DREG-CMD, the SS shall take the action
             indicated by the action code defined by
             wmanIf2BsSsActionsDeReRegSsCode."
        REFERENCE
            "Subclause 6.3.2.3.26 in IEEE Std 802.16-2004"
        ::= { wmanIf2BsSsActionsEntry 6 }

wmanIf2BsSsActionsDeReRegSsCode OBJECT-TYPE
        SYNTAX      INTEGER {actionsDeReRegSsCodeChangeChan(0),
                             actionsDeReRegSsCodeNoTransmit(1),
                             actionsDeReRegSsCodeLtdTransmit(2),
                             actionsDeReRegSsCodeResume(3)}
        MAX-ACCESS  read-create
        STATUS      current
        DESCRIPTION
            "This object defines the action code for
             wmanIf2BsSsActionsDeReRegSs action. The codes are defined
             as follows:
             actionsDeReRegSsCodeChangeChan - SS shall leave the
                 current channel and attempt to access another channel.
             actionsDeReRegSsCodeNoTransmit - SS shall listen to the
                 current channel but shall not transmit until an
                 RES-CMD message or DREG_CMD with an Action Code that
                 allows transmission is received.
             actionsDeReRegSsCodeLtdTransmit - SS shall listen to the
                 current channel but only transmit on the Basic,
                 Primary Management and 2nd Management Connections.
             actionsDeReRegSsCodeResume - SS shall return to normal
                 operation and may transmit on any of its active
                 connections."
        REFERENCE
            "Subclause 6.3.2.3.26, Table 55 in IEEE Std 802.16-2004"
        ::= { wmanIf2BsSsActionsEntry 7 }

wmanIf2BsSsActionsRowStatus OBJECT-TYPE
        SYNTAX      RowStatus
        MAX-ACCESS  read-create
        STATUS      current
        DESCRIPTION
            "This object is used to ensure that the write operation to
             multiple columns is guaranteed to be treated as atomic
             operation by agent."
        ::= { wmanIf2BsSsActionsEntry 8 }

wmanIf2BsMulticastPollingTable OBJECT-TYPE
        SYNTAX      SEQUENCE OF WmanIf2BsMulticastPollingEntry
        MAX-ACCESS  not-accessible
        STATUS      current
        DESCRIPTION
            "This table contains the multicast polling group information
             . BS can send MCA-REQ message to assign/remove a SS to/from
             a multicast polling group. An entry is created when a SS is
             assigned to a multicast polling group; and deleted when a
             SS is removed from a multicast polling group."
        REFERENCE
             "Subclause 6.3.2.3.18 in IEEE Std 802.16-2004"
        ::= { wmanIf2BsCm 8 }
        
wmanIf2BsMulticastPollingEntry OBJECT-TYPE
        SYNTAX      WmanIf2BsMulticastPollingEntry
        MAX-ACCESS  not-accessible
        STATUS      current
        DESCRIPTION
            ""
        INDEX     { wmanIf2BsMulticastPollingCid,
                    wmanIf2BsSsMacAddress }
        ::= { wmanIf2BsMulticastPollingTable 1 }

WmanIf2BsMulticastPollingEntry ::= SEQUENCE {
        wmanIf2BsMulticastPollingCid            WmanIf2CidType,
        wmanIf2BsMulticastGroupType             INTEGER,        
        wmanIf2BsPeriodAllocationParameterM     INTEGER,
        wmanIf2BsPeriodAllocationParameterK     INTEGER,
        wmanIf2BsPeriodAllocationParameterN     INTEGER,        
        wmanIf2BsPeriodicAllocationType         INTEGER}

wmanIf2BsMulticastPollingCid OBJECT-TYPE
        SYNTAX      WmanIf2CidType
        MAX-ACCESS  read-only
        STATUS      current
        DESCRIPTION
            "A 16 bit channel identifier points to the connection being
             created by DSA for this service flow. When '0' is returned
             from reading this object, it means no CID has been assigned
             to this service flow yet."
        ::= { wmanIf2BsMulticastPollingEntry 1 }
        
wmanIf2BsMulticastGroupType OBJECT-TYPE
        SYNTAX      INTEGER {regular(0),
                             aas(1)}
        MAX-ACCESS  read-only
        STATUS      current
        DESCRIPTION
            "Multicast group type."
        REFERENCE
             "Subclause 11.10, Table 382 in IEEE Std 802.16-2004"
        DEFVAL         { 0 }
        ::= { wmanIf2BsMulticastPollingEntry 2 }

wmanIf2BsPeriodAllocationParameterM OBJECT-TYPE
        SYNTAX      INTEGER ( 0 .. 255 )
        MAX-ACCESS  read-only
        STATUS      current
        DESCRIPTION
            "Periodic allocation parameter = 'm'
             Parameters m, k have the following meaning: multicast group
             gets a multicast polling allocation at the end of the frame
             #N if N mod k = m; size of the allocation is n."
        REFERENCE
             "Subclause 11.10, Table 382 in IEEE Std 802.16-2004"
        ::= { wmanIf2BsMulticastPollingEntry 3 }

wmanIf2BsPeriodAllocationParameterK OBJECT-TYPE
        SYNTAX      INTEGER ( 0 .. 255 )
        MAX-ACCESS  read-only
        STATUS      current
        DESCRIPTION
            "Periodic allocation parameter = 'k'
             Parameters m, k have the following meaning: multicast group
             gets a multicast polling allocation at the end of the frame
             #N if N mod k = m; size of the allocation is n."
        REFERENCE
             "Subclause 11.10, Table 382 in IEEE Std 802.16-2004"
        ::= { wmanIf2BsMulticastPollingEntry 4 }
        
wmanIf2BsPeriodAllocationParameterN OBJECT-TYPE
        SYNTAX      INTEGER ( 0 .. 255 )
        MAX-ACCESS  read-only
        STATUS      current
        DESCRIPTION
            "Periodic allocation parameter = 'n'
             Parameters m, k have the following meaning: multicast group
             gets a multicast polling allocation at the end of the frame
             #N if N mod k = m; size of the allocation is n."
        REFERENCE
             "Subclause 11.10, Table 382 in IEEE Std 802.16-2004"
        ::= { wmanIf2BsMulticastPollingEntry 5 }

wmanIf2BsPeriodicAllocationType OBJECT-TYPE
        SYNTAX      INTEGER {reqRegionFull(0),
                             regRegionFocused(1)}
        MAX-ACCESS  read-only
        STATUS      current
        DESCRIPTION
            "Periodic allocation type. Applicable for OFDM PHY only."
        REFERENCE
             "Subclause 11.10, Table 382 in IEEE Std 802.16-2004"
        ::= { wmanIf2BsMulticastPollingEntry 6 }
                                
--
-- Base station PHY Group 
--
wmanIf2BsPhy OBJECT IDENTIFIER ::= { wmanIf2BsCm 9 }

--
-- BS Common PHY objects    
--
wmanIf2BsCmnPhy OBJECT IDENTIFIER ::= { wmanIf2BsPhy 1 }

wmanIf2BsCmnPhyUplinkChannelTable OBJECT-TYPE
        SYNTAX      SEQUENCE OF WmanIf2BsCmnPhyUplinkChannelEntry
        MAX-ACCESS  not-accessible
        STATUS      current
        DESCRIPTION
            "This table contains common channel attributes that
             characterize the uplink channels"
        REFERENCE
            "Table 349 and Table 352, in IEEE Std 802.16-2004"
        ::= { wmanIf2BsCmnPhy 1 }

wmanIf2BsCmnPhyUplinkChannelEntry OBJECT-TYPE
        SYNTAX      WmanIf2BsCmnPhyUplinkChannelEntry
        MAX-ACCESS  not-accessible
        STATUS      current
        DESCRIPTION
             "This table provides one row for each uplink channel of
              multi-sector BS. An entry in this table exists for each
              ifEntry of BS with an ifType of ieee80216WMAN."
        INDEX     { ifIndex }
        ::= { wmanIf2BsCmnPhyUplinkChannelTable 1 }

WmanIf2BsCmnPhyUplinkChannelEntry ::= SEQUENCE {
        wmanIf2BsCmnPhyCtBasedResvTimeout       INTEGER,
        wmanIf2BsCmnPhyUplinkCenterFreq         Unsigned32}

wmanIf2BsCmnPhyCtBasedResvTimeout OBJECT-TYPE
        SYNTAX      INTEGER (1..255)
        MAX-ACCESS  read-write
        STATUS      current
        DESCRIPTION
            "The number of UL-MAPs to receive before contention-based
             reservation is attempted again for the same connection."
        REFERENCE
            "Table 349, in IEEE Std 802.16-2004"
        ::= { wmanIf2BsCmnPhyUplinkChannelEntry 1 }

wmanIf2BsCmnPhyUplinkCenterFreq OBJECT-TYPE
        SYNTAX      Unsigned32
        UNITS       "kHz"
        MAX-ACCESS  read-write
        STATUS      current
        DESCRIPTION
            " Uplink center frequency (kHz)"
        REFERENCE
            "Table 349, in IEEE Std 802.16-2004"
        ::= { wmanIf2BsCmnPhyUplinkChannelEntry 2 }
        
wmanIf2BsCmnPhyDownlinkChannelTable OBJECT-TYPE
        SYNTAX      SEQUENCE OF WmanIf2BsCmnPhyDownlinkChannelEntry
        MAX-ACCESS  not-accessible
        STATUS      current
        DESCRIPTION
            "This table contains common channel attributes that
             charaterize the downlink channels"
        REFERENCE
            "Table 358, in IEEE Std 802.16-2004"
        ::= { wmanIf2BsCmnPhy 2 }

wmanIf2BsCmnPhyDownlinkChannelEntry OBJECT-TYPE
        SYNTAX      WmanIf2BsCmnPhyDownlinkChannelEntry
        MAX-ACCESS  not-accessible
        STATUS      current
        DESCRIPTION
            "This table provides one row for each downlink channel of
             multi-sector BS. An entry in this table exists for each
             ifEntry of BS with an ifType of ieee80216WMAN."
        INDEX     { ifIndex }
        ::= { wmanIf2BsCmnPhyDownlinkChannelTable 1 }

WmanIf2BsCmnPhyDownlinkChannelEntry ::= SEQUENCE {   
        wmanIf2BsCmnPhyBsEIRP                   INTEGER,
        wmanIf2BsCmnPhyChannelNumber            WmanIf2ChannelNumber,
        wmanIf2BsCmnPhyTTG                      INTEGER,
        wmanIf2BsCmnPhyRTG                      INTEGER,
        wmanIf2BsCmnPhyInitRngMaxRSS            INTEGER,
        wmanIf2BsCmnPhyDownlinkCenterFreq       Unsigned32,
        wmanIf2BsCmnPhyBsId                     WmanIf2BsIdType,
        wmanIf2BsCmnPhyMacVersion               WmanIf2MacVersion,
        wmanIf2BsCmnPhyCyclicPrefix             INTEGER}

wmanIf2BsCmnPhyBsEIRP OBJECT-TYPE
        SYNTAX      INTEGER (-32768..32767)
        UNITS       "dBm"
        MAX-ACCESS  read-write
        STATUS      current
        DESCRIPTION
            "The EIRP is the equivalent isotropic radiated power of
             the base station, which is computed for a simple
             single-antenna transmitter."
        REFERENCE
            "Table 358, in IEEE Std 802.16-2004"
        ::= { wmanIf2BsCmnPhyDownlinkChannelEntry 1 }

wmanIf2BsCmnPhyChannelNumber OBJECT-TYPE
        SYNTAX      WmanIf2ChannelNumber
        MAX-ACCESS  read-write
        STATUS      current
        DESCRIPTION
            "Downlink channel number as defined in 8.5.
             Used for license-exempt operation only."
        REFERENCE
            "Table 358, in IEEE Std 802.16-2004"
        ::= { wmanIf2BsCmnPhyDownlinkChannelEntry 2 }

wmanIf2BsCmnPhyTTG OBJECT-TYPE
        SYNTAX      INTEGER (0..255)
        MAX-ACCESS  read-write
        STATUS      current
        DESCRIPTION
            "Transmit / Receive Transition Gap."
        REFERENCE
            "Table 358, in IEEE Std 802.16-2004"
        ::= { wmanIf2BsCmnPhyDownlinkChannelEntry 3 }

wmanIf2BsCmnPhyRTG OBJECT-TYPE
        SYNTAX      INTEGER (0..255)
        MAX-ACCESS  read-write
        STATUS      current
        DESCRIPTION
            "Receive / Transmit Transition Gap."
        REFERENCE
            "Table 358, in IEEE Std 802.16-2004"
        ::= { wmanIf2BsCmnPhyDownlinkChannelEntry 4 }

wmanIf2BsCmnPhyInitRngMaxRSS OBJECT-TYPE
        SYNTAX      INTEGER (-32768..32767)
        UNITS       "dBm"
        MAX-ACCESS  read-write
        STATUS      current
        DESCRIPTION
            "Initial Ranging Max. equivalent isotropic received power
             at BS Signed in units of 1 dBm."
        REFERENCE
            "Table 358, in IEEE Std 802.16-2004"
        ::= { wmanIf2BsCmnPhyDownlinkChannelEntry 5 }

wmanIf2BsCmnPhyDownlinkCenterFreq OBJECT-TYPE
        SYNTAX      Unsigned32
        UNITS       "kHz"
        MAX-ACCESS  read-write
        STATUS      current
        DESCRIPTION
            "Downlink center frequency (kHz)."
        REFERENCE
            "Table 358, in IEEE Std 802.16-2004"
        ::= { wmanIf2BsCmnPhyDownlinkChannelEntry 6 }

wmanIf2BsCmnPhyBsId OBJECT-TYPE
        SYNTAX      WmanIf2BsIdType
        MAX-ACCESS  read-write
        STATUS      current
        DESCRIPTION
            "Base station ID."
        REFERENCE
            "Table 358, in IEEE Std 802.16-2004"
        ::= { wmanIf2BsCmnPhyDownlinkChannelEntry 7 }
        
wmanIf2BsCmnPhyMacVersion OBJECT-TYPE
        SYNTAX      WmanIf2MacVersion
        MAX-ACCESS  read-write
        STATUS      current
        DESCRIPTION
            "This parameter specifies the version of 802.16 to which
             the message originator conforms."
        REFERENCE
            "Table 358, in IEEE Std 802.16-2004"
        ::= { wmanIf2BsCmnPhyDownlinkChannelEntry 8 }

wmanIf2BsCmnPhyCyclicPrefix OBJECT-TYPE
        SYNTAX INTEGER {ratio1To4(0),
                        ratio1To8(1),
                        ratio1To16(2),
                        ratio1To32(3)}
        MAX-ACCESS  read-write
        STATUS      current
        DESCRIPTION
            "The ratio of CP time to 'useful' time.Values
             are 1/4, 1/8, 1/16 or 1/32."
        REFERENCE
            "Subclause 8.3.1.1.1 in IEEE Std 802.16-2004"
        DEFVAL      { ratio1To4 }
        ::= { wmanIf2BsCmnPhyDownlinkChannelEntry 9 }
                
--
-- BS OFDM PHY objects    
--
wmanIf2BsOfdmPhy OBJECT IDENTIFIER ::= { wmanIf2BsPhy 2 }

wmanIf2BsOfdmUplinkChannelTable OBJECT-TYPE
        SYNTAX      SEQUENCE OF WmanIf2BsOfdmUplinkChannelEntry
        MAX-ACCESS  not-accessible
        STATUS      current
        DESCRIPTION
            "This table contains UCD channel attributes, defining the
             transmission characteristics of uplink channels"
        REFERENCE
            "Table 349 and Table 352, in IEEE Std 802.16-2004"
        ::= { wmanIf2BsOfdmPhy 1 }

wmanIf2BsOfdmUplinkChannelEntry OBJECT-TYPE
        SYNTAX      WmanIf2BsOfdmUplinkChannelEntry
        MAX-ACCESS  not-accessible
        STATUS      current
        DESCRIPTION
             "This table provides one row for each uplink channel of
              multi-sector BS. An entry in this table exists for each
              ifEntry of BS with an ifType of ieee80216WMAN."
        INDEX     { ifIndex }
        ::= { wmanIf2BsOfdmUplinkChannelTable 1 }

WmanIf2BsOfdmUplinkChannelEntry ::= SEQUENCE {
        wmanIf2BsOfdmBwReqOppSize               INTEGER,
        wmanIf2BsOfdmRangReqOppSize             INTEGER,
        wmanIf2BsOfdmNumSubChReqRegionFull      INTEGER,
        wmanIf2BsOfdmNumSymbolsReqRegionFull    INTEGER,
        wmanIf2BsOfdmSubChFocusCtCode           INTEGER}

wmanIf2BsOfdmBwReqOppSize OBJECT-TYPE
        SYNTAX      INTEGER (1..65535)
        UNITS       "PS"
        MAX-ACCESS  read-write
        STATUS      current
        DESCRIPTION
            "Size (in units of PS) of PHY payload that SS may use to
             format and transmit a bandwidth request message in a
             contention request opportunity. The value includes all
             PHY overhead as well as allowance for the MAC data the
             message may hold."
        REFERENCE
            "Table 349, in IEEE Std 802.16-2004"
        ::= { wmanIf2BsOfdmUplinkChannelEntry 1 }

wmanIf2BsOfdmRangReqOppSize OBJECT-TYPE
        SYNTAX      INTEGER (1..65535)
        UNITS       "PS"
        MAX-ACCESS  read-write
        STATUS      current
        DESCRIPTION
            "Size (in units of PS) of PHY payload that SS may use to
             format and transmit a RNG-REQ message in a contention
             request opportunity. The value includes all PHY overhead
             as well as allowance for the MAC data the message may
             hold and the maxiumum SS/BS roundtrip propagation delay."
        REFERENCE
            "Table 349, in IEEE Std 802.16-2004"
        ::= { wmanIf2BsOfdmUplinkChannelEntry 2 }
        
wmanIf2BsOfdmNumSubChReqRegionFull OBJECT-TYPE
        SYNTAX      INTEGER {oneSubchannel(0),
                             twoSubchannels(1),
                             fourSubchannels(2),
                             eightSubchannels(3),
                             sixteenSubchannels(4)}
        MAX-ACCESS  read-write
        STATUS      current
        DESCRIPTION
            "Number of subchannels used by each transmit opportunity
             when REQ Region-Full is allocated in subchannelization
             region."
        REFERENCE
             "Table 352, in IEEE Std 802.16-2004"
        ::= { wmanIf2BsOfdmUplinkChannelEntry 3 }

wmanIf2BsOfdmNumSymbolsReqRegionFull OBJECT-TYPE
        SYNTAX      INTEGER (0..31)
        MAX-ACCESS  read-write
        STATUS      current
        DESCRIPTION
            "Number of OFDM symbols used by each transmit
             opportunity when REQ Region-Full is allocated in
             subchannelization region."
        REFERENCE
             "Table 352, in IEEE Std 802.16-2004"
        ::= { wmanIf2BsOfdmUplinkChannelEntry 4 }

wmanIf2BsOfdmSubChFocusCtCode OBJECT-TYPE
        SYNTAX      INTEGER (0..8)
        MAX-ACCESS  read-write
        STATUS      current
        DESCRIPTION
            "Number of contention codes (CSE) that shall only be used to
             request a subchannelized allocation. Default value 0.
             Allowed values 0-8."
        REFERENCE
            "Table 352, in IEEE Std 802.16-2004"
        DEFVAL         { 0 }
        ::= { wmanIf2BsOfdmUplinkChannelEntry 5 }
        
wmanIf2BsOfdmDownlinkChannelTable OBJECT-TYPE
        SYNTAX      SEQUENCE OF WmanIf2BsOfdmDownlinkChannelEntry
        MAX-ACCESS  not-accessible
        STATUS      current
        DESCRIPTION
            "This table contains DCD channel attributes, defining the
             transmission characteristics of downlink channels"
        REFERENCE
            "Table 358, in IEEE Std 802.16-2004"
        ::= { wmanIf2BsOfdmPhy 2 }

wmanIf2BsOfdmDownlinkChannelEntry OBJECT-TYPE
        SYNTAX      WmanIf2BsOfdmDownlinkChannelEntry
        MAX-ACCESS  not-accessible
        STATUS      current
        DESCRIPTION
            "This table provides one row for each downlink channel of
             multi-sector BS. An entry in this table exists for each
             ifEntry of BS with an ifType of ieee80216WMAN."
        INDEX     { ifIndex }
        ::= { wmanIf2BsOfdmDownlinkChannelTable 1 }

WmanIf2BsOfdmDownlinkChannelEntry ::= SEQUENCE {   
        wmanIf2BsOfdmFrameDurationCode          INTEGER,
        wmanIf2BsOfdmFftSize                    WmanIf2OfdmFftSize}

wmanIf2BsOfdmFrameDurationCode OBJECT-TYPE
        SYNTAX      INTEGER {duration2dot5ms(0),
                             duration4ms(1),
                             duration5ms(2),
                             duration8ms(3),
                             duration10ms(4),
                             duration12dot5ms(5),
                             duration20ms(6)}
        MAX-ACCESS  read-write
        STATUS      current
        DESCRIPTION
            "The duration of the frame. The frame duration code
             values are specified in Table 230."
        REFERENCE
            "Subclause 11.4.1, Table 230, in IEEE Std 802.16-2004"
        ::= { wmanIf2BsOfdmDownlinkChannelEntry 1 }

wmanIf2BsOfdmFftSize OBJECT-TYPE
        SYNTAX      WmanIf2OfdmFftSize
        MAX-ACCESS  read-write
        STATUS      current
        DESCRIPTION
            "This field indicates the channel BW in units of 125 kHz
             for OFDM PHY."
        REFERENCE
            "Subclause 11.8.3.6.1, IEEE Std 802.16-2004"
        ::= { wmanIf2BsOfdmDownlinkChannelEntry 2 }
        
wmanIf2BsOfdmUcdBurstProfileTable OBJECT-TYPE
        SYNTAX      SEQUENCE OF WmanIf2BsOfdmUcdBurstProfileEntry
        MAX-ACCESS  not-accessible
        STATUS      current
        DESCRIPTION
            "This table contains UCD burst profiles for each uplink
             channel"
        REFERENCE
            "Table 356, in IEEE Std 802.16-2004"
        ::= { wmanIf2BsOfdmPhy 3 }

wmanIf2BsOfdmUcdBurstProfileEntry OBJECT-TYPE
        SYNTAX      WmanIf2BsOfdmUcdBurstProfileEntry
        MAX-ACCESS  not-accessible
        STATUS      current
        DESCRIPTION
            "This table provides one row for each UCD burst profile."
        INDEX     { ifIndex, wmanIf2BsOfdmUiucIndex }
        ::= { wmanIf2BsOfdmUcdBurstProfileTable 1 }

WmanIf2BsOfdmUcdBurstProfileEntry ::= SEQUENCE {
        wmanIf2BsOfdmUiucIndex                  INTEGER,
        wmanIf2BsOfdmUcdFecCodeType             WmanIf2OfdmFecCodeType,
        wmanIf2BsOfdmFocusCtPowerBoost          INTEGER,
        wmanIf2BsOfdmUcdTcsEnable               INTEGER,
        wmanIf2BsOfdmUcdBurstProfileRowStatus   RowStatus}

wmanIf2BsOfdmUiucIndex OBJECT-TYPE
        SYNTAX      INTEGER (5 .. 12)
        MAX-ACCESS  not-accessible
        STATUS      current
        DESCRIPTION
            "The Uplink Interval Usage Code indicates the uplink burst
             profile in the UCD message, and is used along with ifIndex
             to identify an entry in the
             wmanIf2BsOfdmUcdBurstProfileTable."
        REFERENCE
            "Subclause 8.3.6.3.1, in IEEE Std 802.16-2004"
        ::= { wmanIf2BsOfdmUcdBurstProfileEntry 1 }

wmanIf2BsOfdmUcdFecCodeType OBJECT-TYPE
        SYNTAX      WmanIf2OfdmFecCodeType
        MAX-ACCESS  read-create
        STATUS      current
        DESCRIPTION
            "Uplink FEC code type and modulation type"
        REFERENCE
            "Table 542 and 548"
        ::= { wmanIf2BsOfdmUcdBurstProfileEntry 2 }

wmanIf2BsOfdmFocusCtPowerBoost OBJECT-TYPE
        SYNTAX      INTEGER (0 .. 255)
        MAX-ACCESS  read-create
        STATUS      current
        DESCRIPTION
            "The power boost in dB of focused contention carriers, as
             described in 8.3.6.3.3."
        REFERENCE
            "Table 356, in IEEE Std 802.16-2004"
        ::= { wmanIf2BsOfdmUcdBurstProfileEntry 3 }

wmanIf2BsOfdmUcdTcsEnable OBJECT-TYPE
        SYNTAX      INTEGER {tcsDisabled(0),
                             tcsEnabled(1)}
        MAX-ACCESS  read-create
        STATUS      current
        DESCRIPTION
            "This parameter determines the transmission convergence
             sublayer, as described in 8.1.4.3, can be enabled on a
             per-burst basis for both uplink and downlink. through
             DIUC/UIUC messages."
        REFERENCE
            "Table 356, in IEEE Std 802.16-2004"
        ::= { wmanIf2BsOfdmUcdBurstProfileEntry 4 }
        
wmanIf2BsOfdmUcdBurstProfileRowStatus OBJECT-TYPE
        SYNTAX      RowStatus
        MAX-ACCESS  read-create
        STATUS      current
        DESCRIPTION
            "This object is used to create a new row or modify or
             delete an existing row in this table.

             If the implementator of this MIB has choosen not
             to implement 'dynamic assignment' of profiles, this
             object is not useful and should return noSuchName
             upon SNMP request."
        ::= { wmanIf2BsOfdmUcdBurstProfileEntry 5 }
        
wmanIf2BsOfdmDcdBurstProfileTable OBJECT-TYPE
        SYNTAX      SEQUENCE OF WmanIf2BsOfdmDcdBurstProfileEntry
        MAX-ACCESS  not-accessible
        STATUS      current
        DESCRIPTION
            "This table provides one row for each DCD burst profile."
        REFERENCE
            "Table 362, in IEEE Std 802.16-2004"
        ::= { wmanIf2BsOfdmPhy 4 }

wmanIf2BsOfdmDcdBurstProfileEntry OBJECT-TYPE
        SYNTAX      WmanIf2BsOfdmDcdBurstProfileEntry
        MAX-ACCESS  not-accessible
        STATUS      current
        DESCRIPTION
            "This table provides one row for each DCD burst profile."
        INDEX     { ifIndex, wmanIf2BsOfdmDiucIndex }
        ::= { wmanIf2BsOfdmDcdBurstProfileTable 1 }

WmanIf2BsOfdmDcdBurstProfileEntry ::= SEQUENCE {
        wmanIf2BsOfdmDiucIndex                  INTEGER,
        wmanIf2BsOfdmDcdFecCodeType             WmanIf2OfdmFecCodeType,
        wmanIf2BsOfdmTcsEnable                  INTEGER,
        wmanIf2BsOfdmDcdBurstProfileRowStatus   RowStatus}

wmanIf2BsOfdmDiucIndex OBJECT-TYPE
        SYNTAX      INTEGER (1..11)
        MAX-ACCESS  not-accessible
        STATUS      current
        DESCRIPTION
            "The Downlink Interval Usage Code indicates the downlink
             burst profile in the DCD message, and is used along with
             ifIndex to identify an entry in the
             wmanIf2BsOfdmDcdBurstProfileTable."
        REFERENCE
            "Subclause 8.3.6.3.1, in IEEE Std 802.16-2004"
        ::= { wmanIf2BsOfdmDcdBurstProfileEntry 1 }

wmanIf2BsOfdmDcdFecCodeType OBJECT-TYPE
        SYNTAX      WmanIf2OfdmFecCodeType
        MAX-ACCESS  read-create
        STATUS      current
        DESCRIPTION
            "Downlink FEC code type and modulation type"
        REFERENCE
            "Table 542 and 548"
        ::= { wmanIf2BsOfdmDcdBurstProfileEntry 2 }

wmanIf2BsOfdmTcsEnable OBJECT-TYPE
        SYNTAX      INTEGER {tcsDisabled (0),
                             tcsEnabled (1)}
        MAX-ACCESS  read-create
        STATUS      current
        DESCRIPTION
            "Indicates whether Transmission COnvergence Sublayer
             is enabled or disabled."
        REFERENCE
            "Table 362, in IEEE Std 802.16-2004"
        ::= { wmanIf2BsOfdmDcdBurstProfileEntry 3 }
        
wmanIf2BsOfdmDcdBurstProfileRowStatus OBJECT-TYPE
        SYNTAX      RowStatus
        MAX-ACCESS  read-create
        STATUS      current
        DESCRIPTION
            "This object is used to create a new row or modify or
             delete an existing row in this table.

             If the implementator of this MIB has choosen not
             to implement 'dynamic assignment' of profiles, this
             object is not useful and should return noSuchName
             upon SNMP request."
        ::= { wmanIf2BsOfdmDcdBurstProfileEntry 4 }

wmanIf2BsOfdmConfigurationTable OBJECT-TYPE
        SYNTAX      SEQUENCE OF WmanIf2BsOfdmConfigurationEntry
        MAX-ACCESS  not-accessible
        STATUS      current
        DESCRIPTION
            "This table contains BS configuration objects, specific to
             OFDM PHY."
        ::= { wmanIf2BsOfdmPhy 5 }

wmanIf2BsOfdmConfigurationEntry OBJECT-TYPE
        SYNTAX      WmanIf2BsOfdmConfigurationEntry
        MAX-ACCESS  not-accessible
        STATUS      current
        DESCRIPTION
            ""
        INDEX     { ifIndex }
        ::= { wmanIf2BsOfdmConfigurationTable 1 }

WmanIf2BsOfdmConfigurationEntry ::= SEQUENCE {
        wmanIf2BsOfdmMinReqRegionFullTxOpp      INTEGER,
        wmanIf2BsOfdmMinFocusedCtTxOpp          INTEGER,
        wmanIf2BsOfdmMaxRoundTripDelay          INTEGER,
        wmanIf2BsOfdmRangeAbortTimingThold      INTEGER,
        wmanIf2BsOfdmRangeAbortPowerThold       INTEGER,
        wmanIf2BsOfdmRangeAbortFreqThold        INTEGER,
        wmanIf2BsOfdmDnlkRateId                 INTEGER}

wmanIf2BsOfdmMinReqRegionFullTxOpp OBJECT-TYPE
        SYNTAX      INTEGER (1..65535)
        UNITS       "n per second"
        MAX-ACCESS  read-write
        STATUS      current
        DESCRIPTION
            "The minimum number of Full bandwidth Req-Region Full
             Transmit opportunities scheduled in the UL per second."
        REFERENCE
            "Subclause 6.3.7.4.3 in IEEE Std 802.16-2004"
        ::= { wmanIf2BsOfdmConfigurationEntry 1 }

wmanIf2BsOfdmMinFocusedCtTxOpp OBJECT-TYPE
        SYNTAX      INTEGER (0..65535)
        UNITS       "1/sec"
        MAX-ACCESS  read-write
        STATUS      current
        DESCRIPTION
            "The minimum number of focused contention Transmit
             opportunities scheduled in the UL per second. The value may
             be 0 if the focused contention is not implemented."
        REFERENCE
            "Subclauses 6.3.6.4 and 8.3.7.3.3 in IEEE Std 802.16-2004"
        ::= { wmanIf2BsOfdmConfigurationEntry 2 }

wmanIf2BsOfdmMaxRoundTripDelay OBJECT-TYPE
        SYNTAX      INTEGER (1..65535)
        UNITS       "microsecond"
        MAX-ACCESS  read-write
        STATUS      current
        DESCRIPTION
            "Maximum supported round trip delay.
             It is required to limit the cell size."
        REFERENCE
            "Subclause 8.3.5.1 in IEEE Std 802.16-2004"
        ::= { wmanIf2BsOfdmConfigurationEntry 3 }

wmanIf2BsOfdmRangeAbortTimingThold OBJECT-TYPE
        SYNTAX      INTEGER (0..255)
        UNITS       "1/Fs"
        MAX-ACCESS  read-write
        STATUS      current
        DESCRIPTION
            "This object defines Tolerable Timing Offset. BS performs
             Initial Ranging until the SS transmissions are within 
             limits that are deemed tolerable by the BS. If the SS does
             not transmit within these limits after a number of
             correction attempts then the BS aborts Initial Ranging."
        REFERENCE
            "Figure 63 and Table 365 in IEEE Std 802.16-2004"
        ::= { wmanIf2BsOfdmConfigurationEntry 4 }
        
wmanIf2BsOfdmRangeAbortPowerThold OBJECT-TYPE
        SYNTAX      INTEGER (0..255)
        UNITS       "0.25dB"
        MAX-ACCESS  read-write
        STATUS      current
        DESCRIPTION
            "This object defines Tolerable Power Offset. BS performs
             Initial Ranging until the SS transmissions are within 
             limits that are deemed tolerable by the BS. If the SS does
             not transmit within these limits after a number of
             correction attempts then the BS aborts Initial Ranging."
        REFERENCE
            "Figure 63 and Table 365 in IEEE Std 802.16-2004"
        ::= { wmanIf2BsOfdmConfigurationEntry 5 }
        
wmanIf2BsOfdmRangeAbortFreqThold OBJECT-TYPE
        SYNTAX      INTEGER (0..255)
        UNITS       "Hz"
        MAX-ACCESS  read-write
        STATUS      current
        DESCRIPTION
            "This object defines Tolerable Frequency Offset. BS performs
             Initial Ranging until the SS transmissions are within
             limits that are deemed tolerable by the BS. If the SS does
             not transmit within these limits after a number of
             correction attempts then the BS aborts Initial Ranging."
        REFERENCE
            "Figure 63 and Table 365 in IEEE Std 802.16-2004"
        ::= { wmanIf2BsOfdmConfigurationEntry 6 }
        
wmanIf2BsOfdmDnlkRateId OBJECT-TYPE
        SYNTAX      INTEGER {dnlkRateIdBpsk1Over2(0),
                             dnlkRateIdQpsk1Over2(1),
                             dnlkRateIdQpsk3Over4(2),
                             dnlkRateId16Qam1Over2(3),
                             dnlkRateId16Qam3Over4(4),
                             dnlkRateId64Qam2Over3(5),
                             dnlkRateId64Qam3Over4(6)}
        MAX-ACCESS  read-write
        STATUS      current
        DESCRIPTION
            "The Rate ID to be used in the first downlink burst
             immediately following the FCH. The Rate ID encoding is
             static and cannot be changed during system operation. The
             change of the Rate ID should be applied on system
             re-intialisation (e.g. following sector or BS reset)."
        REFERENCE
            "Subclause 8.3.3.4.3 in IEEE Std 802.16-2004"
        DEFVAL      { dnlkRateIdBpsk1Over2 }
        ::= { wmanIf2BsOfdmConfigurationEntry 7 }

--
-- BS OFDMA PHY objects    
--
wmanIf2BsOfdmaPhy OBJECT IDENTIFIER ::= { wmanIf2BsPhy 3 }

wmanIf2BsOfdmaUplinkChannelTable OBJECT-TYPE
        SYNTAX      SEQUENCE OF WmanIf2BsOfdmaUplinkChannelEntry
        MAX-ACCESS  not-accessible
        STATUS      current
        DESCRIPTION
            "This table contains UCD channel attributes, defining the
             transmission characteristics of uplink channels"
        REFERENCE
            "Table 349 and Table 353, in IEEE Std 802.16-2004"
        ::= { wmanIf2BsOfdmaPhy 1 }

wmanIf2BsOfdmaUplinkChannelEntry OBJECT-TYPE
        SYNTAX      WmanIf2BsOfdmaUplinkChannelEntry
        MAX-ACCESS  not-accessible
        STATUS      current
        DESCRIPTION
            "This table provides one row for each uplink channel of
             multi-sector BS. An entry in this table exists for each
             ifEntry of BS with an ifType of ieee80216WMAN."
        INDEX     { ifIndex }
        ::= { wmanIf2BsOfdmaUplinkChannelTable 1 }

WmanIf2BsOfdmaUplinkChannelEntry ::= SEQUENCE {
        wmanIf2BsOfdmaStartOfRngCodes           INTEGER,
        wmanIf2BsOfdmaPermutationBase           INTEGER,
        wmanIf2BsOfdmaULAllocSubchBitmap        OCTET STRING,
        wmanIf2BsOfdmaOptPermULAllocSubchBitmap OCTET STRING,
        wmanIf2BsOfdmaBandAMCAllocThreshold     INTEGER,
        wmanIf2BsOfdmaBandAMCReleaseThreshold   INTEGER,
        wmanIf2BsOfdmaBandAMCAllocTimer         INTEGER,
        wmanIf2BsOfdmaBandAMCReleaseTimer       INTEGER,
        wmanIf2BsOfdmaBandStatRepMAXPeriod      INTEGER,
        wmanIf2BsOfdmaBandAMCRetryTimer         INTEGER,
        wmanIf2BsOfdmaPerRngBackoffStart        INTEGER,
        wmanIf2BsOfdmaPerRngBackoffEnd          INTEGER,
        wmanIf2BsOfdmaInitRngCodes              INTEGER,
        wmanIf2BsOfdmaPeriodicRngCodes          INTEGER,
        wmanIf2BsOfdmaBWReqCodes                INTEGER,
        wmanIf2BsOfdmaHandoverRangingStart      INTEGER,
        wmanIf2BsOfdmaHandoverRangingEnd        INTEGER,
        wmanIf2BsOfdmaHARQAckDelayDLBurst       WmanIf2HarqAckDelay,
        wmanIf2BsOfdmaUlAmcAlloPhyBandsBitmap   OCTET STRING,
        wmanIf2BsOfdmaMaxRetransmission         INTEGER,
        wmanIf2BsOfdmaNormalizedCnOverride      OCTET STRING,
        wmanIf2BsOfdmaSizeOfCqichId             INTEGER,
        wmanIf2BsOfdmaNormalizedCnValue         INTEGER,
        wmanIf2BsOfdmaNormalizedCnOverride2     OCTET STRING,
        wmanIf2BsOfdmaBandAmcEntryAvgCinr       INTEGER,
        wmanIf2BsOfdmaAasPreambleUpperBond      INTEGER,
        wmanIf2BsOfdmaAasPreambleLowerBond      INTEGER,
        wmanIf2BsOfdmaAasBeamSelectAllowed      WmanIf2AasBeamSel,
        wmanIf2BsOfdmaCqichIndicationFlag       OCTET STRING,
        wmanIf2BsOfdmaUpPowerAdjStep            Unsigned32,
        wmanIf2BsOfdmaDownPowerAdjStep          Unsigned32,
        wmanIf2BsOfdmaMinPowerOffsetAdj         INTEGER,
        wmanIf2BsOfdmaMaxPowerOffsetAdj         INTEGER,
        wmanIf2BsOfdmaHandoverRngCodes          INTEGER,
        wmanIf2BsOfdmaInitialRngInterval        INTEGER,
        wmanIf2BsOfdmaTxPwrRepThreshold         INTEGER,
        wmanIf2BsOfdmaTprPower                  INTEGER,
        wmanIf2BsOfdmaAlphaPavg                 INTEGER,
        wmanIf2BsOfdmaCqichTxPwrRepThreshold    INTEGER,
        wmanIf2BsOfdmaCqichTprPower             INTEGER,
        wmanIf2BsOfdmaCqichAlphaPavg            INTEGER,
        wmanIf2BsOfdmaNormalizedCnChSounding    INTEGER,
        wmanIf2BsOfdmaInitialRngBackoffStart    INTEGER,
        wmanIf2BsOfdmaInitialRngBackoffEnd      INTEGER,
        wmanIf2BsOfdmaBwRequestBackoffStart     INTEGER,
        wmanIf2BsOfdmaBwRequestBackoffEnd       INTEGER}

wmanIf2BsOfdmaStartOfRngCodes OBJECT-TYPE
        SYNTAX      INTEGER (0..255)
        MAX-ACCESS  read-write
        STATUS      current
        DESCRIPTION
            "Indicates the starting number, S, of the group of codes
             used for this uplink.All the ranging codes used on this
             uplink will be between S and ((S+N+M+L) mod 256). Where,
               N: the number of initial-ranging codes
               M: the number of periodic-ranging codes
               L: the number of bandwidth-request codes
               O: the number of handover-ranging codes"
        REFERENCE
            "Subclause 11.3.1, Table 353, in IEEE Std 802.16e-2005"
        DEFVAL 	    { 0 }
        ::= { wmanIf2BsOfdmaUplinkChannelEntry 1 }

wmanIf2BsOfdmaPermutationBase OBJECT-TYPE
        SYNTAX      INTEGER (0..255)
        MAX-ACCESS  read-write
        STATUS      current
        DESCRIPTION
            "Determines the UL_PermBase parameter for the subcarrier
             permutation to be used on this uplink channel.
                 UL_PermBase = 7 LSBs of Permutation base."
        REFERENCE
            "Subclause 11.3.1, Table 353, in IEEE Std 802.16-2004"
        DEFVAL 	    { 0 }
        ::= { wmanIf2BsOfdmaUplinkChannelEntry 2 }

wmanIf2BsOfdmaULAllocSubchBitmap OBJECT-TYPE
        SYNTAX      OCTET STRING (SIZE (9))
        MAX-ACCESS  read-write
        STATUS      current
        DESCRIPTION
            "This is a bitmap describing the physical sub-channels
             allocated to the segment in the UL, when using the uplink
             PUSC permutation. The LSB of the first byte shall corrspond
             to subchannel 0. For any bit that is not set, the
             corresponding subchannel shall not be used by the SS on
             that segment"
        REFERENCE
            "Subclause 11.3.1, Table 353, in IEEE Std 802.16e-2005"
        ::= { wmanIf2BsOfdmaUplinkChannelEntry 3 }

wmanIf2BsOfdmaOptPermULAllocSubchBitmap OBJECT-TYPE
        SYNTAX      OCTET STRING (SIZE (13))
        MAX-ACCESS  read-write
        STATUS      current
        DESCRIPTION
            "This is a bitmap describing the sub-channels allocated to
             the segment in the UL, when using the uplink optional PUSC
             permutation (see 8.4.6.2.5 in IEEE Std 802.16-2004). The
             LSB of the first byte shall correspond to subchannel 0.
             For any bit that is not set, the corresponding subchannel
             shall not be used by the SS on that segment. When this TLV
             is not present, BS may allocate any subchannels to an SS."
        REFERENCE
            "Subclause 11.3.1, Table 353, in IEEE Std 802.16-2004"
        ::= { wmanIf2BsOfdmaUplinkChannelEntry 4 }

wmanIf2BsOfdmaBandAMCAllocThreshold OBJECT-TYPE
        SYNTAX      INTEGER (0 .. 255)
        UNITS       "dB"
        MAX-ACCESS  read-write
        STATUS      current
        DESCRIPTION
            "Threshold of the maximum of the standard deviations of the
             individual bands CINR measurements over time to trigger
             mode transition from normal subchannel to Band AMC"
        REFERENCE
            "Subclause 11.3.1, Table 353, in IEEE Std 802.16e-2005"
        ::= { wmanIf2BsOfdmaUplinkChannelEntry 5 }

wmanIf2BsOfdmaBandAMCReleaseThreshold OBJECT-TYPE
        SYNTAX      INTEGER (0 .. 255)
        UNITS       "dB"
        MAX-ACCESS  read-write
        STATUS      current
        DESCRIPTION
            "Threshold of the maximum of the standard deviations of the
             individual bands CINR measurements over time to trigger
             mode transition from Band AMC to normal subchannel"
        REFERENCE
            "Subclause 11.3.1, Table 353, in IEEE Std 802.16e-2005"
        ::= { wmanIf2BsOfdmaUplinkChannelEntry 6 }

wmanIf2BsOfdmaBandAMCAllocTimer OBJECT-TYPE
        SYNTAX      INTEGER (0 .. 255)
        UNITS       "Frame"
        MAX-ACCESS  read-write
        STATUS      current
        DESCRIPTION
            "Minimum required number of frames to measure the average
             and standard deviation for the event of Band AMC triggering"
        REFERENCE
            "Subclause 11.3.1, Table 353, in IEEE Std 802.16e-2005"
        ::= { wmanIf2BsOfdmaUplinkChannelEntry 7 }

wmanIf2BsOfdmaBandAMCReleaseTimer OBJECT-TYPE
        SYNTAX      INTEGER (0 .. 255)
        UNITS       "Frame"
        MAX-ACCESS  read-write
        STATUS      current
        DESCRIPTION
            "Minimum required number of frames to measure the average
             and standard deviation for the event triggering from Band
             AMC to normal subchannel"
        REFERENCE
            "Subclause 11.3.1, Table 353, in IEEE Std 802.16e-2005"
        ::= { wmanIf2BsOfdmaUplinkChannelEntry 8 }

wmanIf2BsOfdmaBandStatRepMAXPeriod OBJECT-TYPE
        SYNTAX      INTEGER (0 .. 255)
        UNITS       "Frame"
        MAX-ACCESS  read-write
        STATUS      current
        DESCRIPTION
            "Maximum period between refreshing the Band CINR
             measurement by the unsolicited REP-RSP"
        REFERENCE
            "Subclause 11.3.1, Table 353, in IEEE Std 802.16e-2005"
        ::= { wmanIf2BsOfdmaUplinkChannelEntry 9 }

wmanIf2BsOfdmaPerRngBackoffStart OBJECT-TYPE
        SYNTAX      INTEGER (0..15)
        MAX-ACCESS 	read-write
        STATUS      current
        DESCRIPTION
            "Initial backoff window size for periodic ranging
             contention, expressed as a power of 2."
        REFERENCE
            "Subclause 11.3.1, Table 353, in IEEE Std 802.16-2004"
        DEFVAL 	    { 0 }
        ::= { wmanIf2BsOfdmaUplinkChannelEntry 10 }

wmanIf2BsOfdmaPerRngBackoffEnd OBJECT-TYPE
        SYNTAX      INTEGER (0 .. 15)
        MAX-ACCESS  read-write
        STATUS      current
        DESCRIPTION
            "Final backoff window size for periodic ranging contention,
             expressed as a power of 2."
        REFERENCE
            "Subclause 11.3.1, Table 353, in IEEE Std 802.16-2004"
        DEFVAL 	    { 15 }
        ::= { wmanIf2BsOfdmaUplinkChannelEntry 11 }
        
wmanIf2BsOfdmaBandAMCRetryTimer OBJECT-TYPE
        SYNTAX      INTEGER (0 .. 255)
        UNITS       "Frame"
        MAX-ACCESS  read-write
        STATUS      current
        DESCRIPTION
            "Backoff timer between consecutive mode transitions from
             normal subchannel to Band AMC when the previous request
             is failed"
        REFERENCE
            "Subclause 11.3.1, Table 353, in IEEE Std 802.16e-2005"
        ::= { wmanIf2BsOfdmaUplinkChannelEntry 12 }
        
wmanIf2BsOfdmaInitRngCodes OBJECT-TYPE
        SYNTAX      INTEGER (0..255)
        MAX-ACCESS  read-write
        STATUS      current
        DESCRIPTION
            "Number of initial ranging CDMA codes. Possible values are
             0..255. The total number of wmanIf2SsOfdmaInitRngCodes,
             wmanIf2SsOfdmaPeriodicRngCodes and wmanIf2SsOfdmaBWReqCodes
             shall be equal or less than 256."
        REFERENCE
            "Subclause 11.3.1, Table 353, in IEEE Std 802.16-2004"
        DEFVAL      { 30 }
        ::= { wmanIf2BsOfdmaUplinkChannelEntry 13 }
        
wmanIf2BsOfdmaPeriodicRngCodes OBJECT-TYPE
        SYNTAX      INTEGER (0..255)
        MAX-ACCESS  read-write
        STATUS      current
        DESCRIPTION
            "Number of periodic ranging CDMA codes. Possible values are
             0..255. The total number of wmanIf2SsOfdmaInitRngCodes,
             wmanIf2SsOfdmaPeriodicRngCodes and wmanIf2SsOfdmaBWReqCodes
             shall be equal or less than 256."
        REFERENCE
            "Subclause 11.3.1, Table 353, in IEEE Std 802.16-2004"
        DEFVAL 	    { 30 }
        ::= { wmanIf2BsOfdmaUplinkChannelEntry 14 }

wmanIf2BsOfdmaBWReqCodes OBJECT-TYPE
        SYNTAX      INTEGER (0..255)
        MAX-ACCESS  read-write
        STATUS      current
        DESCRIPTION
            "Number of bandwidth request codes. Possible values are
             0..255. The total number of wmanIf2SsOfdmaInitRngCodes,
             wmanIf2SsOfdmaPeriodicRngCodes and wmanIf2SsOfdmaBWReqCodes
             shall be equal or less than 256."
        REFERENCE
            "Subclause 11.3.1, Table 353, in IEEE Std 802.16-2004"
        DEFVAL 	    { 30 }
        ::= { wmanIf2BsOfdmaUplinkChannelEntry 15 }

wmanIf2BsOfdmaHandoverRangingStart OBJECT-TYPE
        SYNTAX      INTEGER (0..15)
        MAX-ACCESS  read-write
        STATUS      current
        DESCRIPTION
            "Initial backoff window size for MS performing initial
             ranging during handover process, expressed as a power
             of 2."
        REFERENCE
            "Table 349, in IEEE Std 802.16e-2005"
        ::= { wmanIf2BsOfdmaUplinkChannelEntry 16 }

wmanIf2BsOfdmaHandoverRangingEnd OBJECT-TYPE
        SYNTAX      INTEGER (0..15)
        MAX-ACCESS  read-write
        STATUS      current
        DESCRIPTION
            "Final backoff window size for MS performing initial
             ranging during handover process, expressed as a power
             of 2."
        REFERENCE
            "Table 349, in IEEE Std 802.16e-2005"
        ::= { wmanIf2BsOfdmaUplinkChannelEntry 17 }
        
wmanIf2BsOfdmaHARQAckDelayDLBurst OBJECT-TYPE
        SYNTAX      WmanIf2HarqAckDelay
        MAX-ACCESS  read-write
        STATUS      current
        DESCRIPTION
            "This object defines the OFDMA H-ARQ ACK delay for DL
             burst."
        REFERENCE 
            "Subclause 11.3.1, Table 540, 544"
        ::= { wmanIf2BsOfdmaUplinkChannelEntry 18 }        

wmanIf2BsOfdmaUlAmcAlloPhyBandsBitmap OBJECT-TYPE
        SYNTAX      OCTET STRING (SIZE (6))
        MAX-ACCESS  read-write
        STATUS      current
        DESCRIPTION
            "A bitmap describing the physical bands allocated to the
             segment in the UL, when using the optional AMC permutation
             with regular MAPs (see 8.4.6.3). The LSB of the first byte
             shall correspond to the physical band 0. For any bit that
             is not set, the corresponding physical bands shall not be
             used by the SS on that segment. When this TLV is not
             present, BS may allocate any physical bands to an SS."
        REFERENCE
            "Subclause 11.3.1, Table 353, in IEEE Std 802.16e-2005"
        ::= { wmanIf2BsOfdmaUplinkChannelEntry 19 }

wmanIf2BsOfdmaMaxRetransmission OBJECT-TYPE
        SYNTAX      INTEGER (1..255)
        MAX-ACCESS  read-write
        STATUS      current
        DESCRIPTION
            "Maximum number of retransmission in UL HARQ."
        REFERENCE
            "Table 353, in IEEE Std 802.16e-2005"
        DEFVAL      { 4 }
        ::= { wmanIf2BsOfdmaUplinkChannelEntry 20 }
        
wmanIf2BsOfdmaNormalizedCnOverride OBJECT-TYPE
        SYNTAX      OCTET STRING (SIZE (8))
        MAX-ACCESS  read-write
        STATUS      current
        DESCRIPTION
            "This is a list of numbers, where each number is encoded by
             one nibble, and interpreted as a signed integer. The
             nibbles correspond in order to the list define by Table
             334, starting from the second line, such that the LS
             nibble of the first byte corresponds to the second line in
             the table. The number encoded by each nibble represents
             the difference in normalized C/N relative to the previous
             line in the table."
        REFERENCE
            "Subclause 11.3.1, Table 353, in IEEE Std 802.16e-2005"
        ::= { wmanIf2BsOfdmaUplinkChannelEntry 21 }        

wmanIf2BsOfdmaSizeOfCqichId OBJECT-TYPE
        SYNTAX      INTEGER (0..7)
        MAX-ACCESS  read-write
        STATUS      current
        DESCRIPTION
            "Size of CQICH ID field.
                 0 = 0 bits
                 1 = 3 bits
                 2 = 4 bits
                 3 = 5 bits
                 4 = 6 bits
                 5 = 7 bits
                 6 = 8 bits
                 7 = 9 bits"
        REFERENCE 
            "Subclause 11.3.1, Table 353, in IEEE Std 802.16e-2005"
        DEFVAL      { 0 }
        ::= { wmanIf2BsOfdmaUplinkChannelEntry 22 }
        
wmanIf2BsOfdmaNormalizedCnValue OBJECT-TYPE
        SYNTAX      INTEGER (-128..128)
        UNITS       "dB"
        MAX-ACCESS  read-write
        STATUS      current
        DESCRIPTION
            "It shall be interpreted as signed integer in dB. It
             corresponds to the normalized C/N value in the first line
             (counting except for header cell of table)"
        REFERENCE
            "Subclause 11.3.1, Table 353, in IEEE Std 802.16e-2005"
        ::= { wmanIf2BsOfdmaUplinkChannelEntry 23 }

wmanIf2BsOfdmaNormalizedCnOverride2 OBJECT-TYPE
        SYNTAX      OCTET STRING (SIZE (7))
        MAX-ACCESS  read-write
        STATUS      current
        DESCRIPTION
            "This is a list of numbers, where each number is encoded
             by one nibble, and interpreted as a signed integer. The
             nibbles correspond in order to the list define by Table
             334, starting from the second line (counting except for
             the header cell of table), such that the LS nibble of
             the first byte corresponds to the second line in the
             table. The number encoded by each nibble represents the
             difference in normalized C/N relative to the previous
             line in the table."
        REFERENCE
            "Subclause 11.3.1, Table 353, in IEEE Std 802.16e-2005"
        ::= { wmanIf2BsOfdmaUplinkChannelEntry 24 }

wmanIf2BsOfdmaBandAmcEntryAvgCinr OBJECT-TYPE
        SYNTAX      INTEGER (-128..128)
        UNITS       "dB"
        MAX-ACCESS  read-write
        STATUS      current
        DESCRIPTION
            "Threshold of the average CINR of the whole bandwidth to
             trigger mode transition from normal subchannel to AMC"
        REFERENCE
            "Subclause 11.3.1, Table 353, in IEEE Std 802.16e-2005"
        ::= { wmanIf2BsOfdmaUplinkChannelEntry 25 }

wmanIf2BsOfdmaAasPreambleUpperBond OBJECT-TYPE
        SYNTAX      INTEGER (-128..128)
        UNITS       "0.25 dB"
        MAX-ACCESS  read-write
        STATUS      current
        DESCRIPTION
            "Upper bound of AAS preamble."
        REFERENCE
            "Subclause 11.3.1, Table 353, in IEEE Std 802.16e-2005"
        ::= { wmanIf2BsOfdmaUplinkChannelEntry 26 }

wmanIf2BsOfdmaAasPreambleLowerBond OBJECT-TYPE
        SYNTAX      INTEGER (-128..128)
        UNITS       "0.25 dB"
        MAX-ACCESS  read-write
        STATUS      current
        DESCRIPTION
            "Lower bound of AAS preamble."
        REFERENCE
            "Subclause 11.3.1, Table 353, in IEEE Std 802.16e-2005"
        ::= { wmanIf2BsOfdmaUplinkChannelEntry 27 }

wmanIf2BsOfdmaAasBeamSelectAllowed OBJECT-TYPE
        SYNTAX      WmanIf2AasBeamSel
        UNITS       "0.25 dB"
        MAX-ACCESS  read-write
        STATUS      current
        DESCRIPTION
            "Indicate whether unsolicited AAS Beam Select messages
            (see 6.3.2.3.41 in IEEE 802.16e-2005) should be sent by
            the MS."
        REFERENCE
            "Subclause 11.3.1, Table 540"
        DEFVAL      { allowed }
        ::= { wmanIf2BsOfdmaUplinkChannelEntry 28 }

wmanIf2BsOfdmaCqichIndicationFlag OBJECT-TYPE
        SYNTAX      OCTET STRING (SIZE (1))
        MAX-ACCESS  read-write
        STATUS      current
        DESCRIPTION
            "The N MSB values of this field represents the N-bit
             payload value on the Fast-Feedback channel reserved as
             indication flag for MS to initiate feedback on the
             Feedback header, where N is the number of payload bits
             used for S/N measurement feedback on the Fast-Feedback
             channel. The value shall not be set to all zeros."
        REFERENCE
            "Subclause 11.3.1, Table 353, in IEEE Std 802.16e-2005"
        ::= { wmanIf2BsOfdmaUplinkChannelEntry 29 }

wmanIf2BsOfdmaUpPowerAdjStep OBJECT-TYPE
        SYNTAX      Unsigned32
        UNITS       "0.01 dB"
        MAX-ACCESS  read-write
        STATUS      current
        DESCRIPTION
            "MS-specific up power offset adjustment step"
        REFERENCE
            "Subclause 11.3.1, Table 353, in IEEE Std 802.16e-2005"   
        ::= { wmanIf2BsOfdmaUplinkChannelEntry 30 }

wmanIf2BsOfdmaDownPowerAdjStep OBJECT-TYPE
        SYNTAX      Unsigned32
        UNITS       "0.01 dB"
        MAX-ACCESS  read-write
        STATUS      current
        DESCRIPTION
            "MS-specific down power offset adjustment step"
        REFERENCE
            "Subclause 11.3.1, Table 353, in IEEE Std 802.16e-2005"   
        ::= { wmanIf2BsOfdmaUplinkChannelEntry 31 }        

wmanIf2BsOfdmaMinPowerOffsetAdj OBJECT-TYPE
        SYNTAX      INTEGER
        UNITS       "0.1 dB"
        MAX-ACCESS  read-write
        STATUS      current
        DESCRIPTION
            "Minimum level of power offset adjustment"
        REFERENCE
            "Subclause 11.3.1, Table 353, in IEEE Std 802.16e-2005"   
        ::= { wmanIf2BsOfdmaUplinkChannelEntry 32 }

wmanIf2BsOfdmaMaxPowerOffsetAdj OBJECT-TYPE
        SYNTAX      INTEGER
        UNITS       "0.1 dB"
        MAX-ACCESS  read-write
        STATUS      current
        DESCRIPTION
            "Maximum level of power offset adjustment"
        REFERENCE
            "Subclause 11.3.1, Table 353, in IEEE Std 802.16e-2005"   
        ::= { wmanIf2BsOfdmaUplinkChannelEntry 33 }

wmanIf2BsOfdmaHandoverRngCodes OBJECT-TYPE
        SYNTAX      INTEGER (0..255)
        MAX-ACCESS  read-write
        STATUS      current
        DESCRIPTION
            "Number of handover ranging CDMA codes"
        REFERENCE
            "Subclause 11.3.1, Table 353, in IEEE Std 802.16e-2005"   
        ::= { wmanIf2BsOfdmaUplinkChannelEntry 34 }

wmanIf2BsOfdmaInitialRngInterval OBJECT-TYPE
        SYNTAX      INTEGER
        MAX-ACCESS  read-write
        STATUS      current
        DESCRIPTION
            "Number of frames between initial ranging interval
             allocation."
        REFERENCE
            "Subclause 11.3.1, Table 353, in IEEE Std 802.16e-2005"   
        ::= { wmanIf2BsOfdmaUplinkChannelEntry 35 }

wmanIf2BsOfdmaTxPwrRepThreshold OBJECT-TYPE
        SYNTAX      INTEGER (0..15)
        UNITS       "dB"
        MAX-ACCESS  read-write
        STATUS      current
        DESCRIPTION
            "Tx power report threshold.
             wmanIf2BsOfdmaTxPwrRepThreshold = 0b1111 means infinite."
        REFERENCE
            "Subclause 11.3.1, Table 353, and 8.4.10.3.2.1 in IEEE
             Std 802.16e-2005"   
        ::= { wmanIf2BsOfdmaUplinkChannelEntry 36 }

wmanIf2BsOfdmaTprPower OBJECT-TYPE
        SYNTAX      INTEGER (0..15)
        UNITS       "dB"
        MAX-ACCESS  read-write
        STATUS      current
        DESCRIPTION
            "Tx power report interval = 2 ^ wmanIf2BsOfdmaTprPower.
             The unit of Tx power report interval is frame. 
             wmanIf2BsOfdmaTprPower = 0b1111 means infinite."
        REFERENCE
            "Subclause 11.3.1, Table 353, and 8.4.10.3.2.1 in IEEE
             Std 802.16e-2005"   
        ::= { wmanIf2BsOfdmaUplinkChannelEntry 37 }
        
wmanIf2BsOfdmaAlphaPavg OBJECT-TYPE
        SYNTAX      INTEGER (0..15)
        UNITS       "dB"
        MAX-ACCESS  read-write
        STATUS      current
        DESCRIPTION
            "Aplha p_avg parameter as shown in equation 138d in
             IEEE 802.16e-2005 indicates the multiple of 1/16. For
             example '0' means 1/16, 15 means 16/16. "
        REFERENCE
            "Subclause 11.3.1, Table 353, and 8.4.10.3.2.1 in IEEE
             Std 802.16e-2005"   
        ::= { wmanIf2BsOfdmaUplinkChannelEntry 38 }

wmanIf2BsOfdmaCqichTxPwrRepThreshold OBJECT-TYPE
        SYNTAX      INTEGER (0..15)
        UNITS       "dB"
        MAX-ACCESS  read-write
        STATUS      current
        DESCRIPTION
            "Tx power report threshold.
             wmanIf2BsOfdmaTxPwrRepThreshold = 0b1111 means infinite.
             It shall be used when CQICH is allocated to the SS."
        REFERENCE
            "Subclause 11.3.1, Table 353, and 8.4.10.3.2.1 in IEEE
             Std 802.16e-2005"   
        ::= { wmanIf2BsOfdmaUplinkChannelEntry 39 }

wmanIf2BsOfdmaCqichTprPower OBJECT-TYPE
        SYNTAX      INTEGER (0..15)
        UNITS       "dB"
        MAX-ACCESS  read-write
        STATUS      current
        DESCRIPTION
            "Tx power report interval = 2 ^ wmanIf2BsOfdmaTprPower.
             The unit of Tx power report interval is frame. 
             wmanIf2BsOfdmaTprPower = 0b1111 means infinite.
             It shall be used when CQICH is allocated to the SS."
        REFERENCE
            "Subclause 11.3.1, Table 353, and 8.4.10.3.2.1 in IEEE
             Std 802.16e-2005"   
        ::= { wmanIf2BsOfdmaUplinkChannelEntry 40 }
        
wmanIf2BsOfdmaCqichAlphaPavg OBJECT-TYPE
        SYNTAX      INTEGER (0..15)
        UNITS       "dB"
        MAX-ACCESS  read-write
        STATUS      current
        DESCRIPTION
            "Aplha p_avg parameter as shown in equation 138d in
             IEEE 802.16e-2005 indicates the multiple of 1/16. For
             example '0' means 1/16, 15 means 16/16. It shall be
             used when CQICH is allocated to the SS."
        REFERENCE
            "Subclause 11.3.1, Table 353, and 8.4.10.3.2.1 in IEEE
             Std 802.16e-2005"   
        ::= { wmanIf2BsOfdmaUplinkChannelEntry 41 }
        
wmanIf2BsOfdmaNormalizedCnChSounding OBJECT-TYPE
        SYNTAX      INTEGER
        MAX-ACCESS  read-write
        STATUS      current
        DESCRIPTION
            "Signed integer for the required C/N (dB) for Channel
             Sounding."
        REFERENCE
            "Subclause 11.3.1, Table 353, in IEEE Std 802.16e-2005"   
        ::= { wmanIf2BsOfdmaUplinkChannelEntry 42 }

wmanIf2BsOfdmaInitialRngBackoffStart OBJECT-TYPE
        SYNTAX      INTEGER (0..15)
        MAX-ACCESS  read-write
        STATUS      current
        DESCRIPTION
            "Initial backoff window size for initial ranging
             contention, expressed as a power of 2."
        REFERENCE
            "Subclause 11.3.1, Table 353, in IEEE Std 802.16e-2005"   
        ::= { wmanIf2BsOfdmaUplinkChannelEntry 43 }
                
wmanIf2BsOfdmaInitialRngBackoffEnd OBJECT-TYPE
        SYNTAX      INTEGER (0..15)
        MAX-ACCESS  read-write
        STATUS      current
        DESCRIPTION
            "Final backoff window size for initial ranging
             contention, expressed as a power of 2."
        REFERENCE
            "Subclause 11.3.1, Table 353, in IEEE Std 802.16e-2005"   
        ::= { wmanIf2BsOfdmaUplinkChannelEntry 44 }
        
wmanIf2BsOfdmaBwRequestBackoffStart OBJECT-TYPE
        SYNTAX      INTEGER (0..15)
        MAX-ACCESS  read-write
        STATUS      current
        DESCRIPTION
            "Initial backoff window size for contention BW requests,
             expressed as a power of 2."
        REFERENCE
            "Subclause 11.3.1, Table 353, in IEEE Std 802.16e-2005"   
        ::= { wmanIf2BsOfdmaUplinkChannelEntry 45 }

wmanIf2BsOfdmaBwRequestBackoffEnd OBJECT-TYPE
        SYNTAX      INTEGER (0..15)
        MAX-ACCESS  read-write
        STATUS      current
        DESCRIPTION
            "Final backoff window size for contention BW requests,
             expressed as a power of 2."
        REFERENCE
            "Subclause 11.3.1, Table 353, in IEEE Std 802.16e-2005"   
        ::= { wmanIf2BsOfdmaUplinkChannelEntry 46 }
        
wmanIf2BsOfdmaDownlinkChannelTable OBJECT-TYPE
        SYNTAX      SEQUENCE OF WmanIf2BsOfdmaDownlinkChannelEntry
        MAX-ACCESS  not-accessible
        STATUS      current
        DESCRIPTION
            "This table contains DCD channel attributes, defining the
             transmission characteristics of downlink channels"
        REFERENCE
            "Subclause 11.4.1, Table 358, in IEEE Std 802.16-2004"
        ::= { wmanIf2BsOfdmaPhy 2 }

wmanIf2BsOfdmaDownlinkChannelEntry OBJECT-TYPE
        SYNTAX      WmanIf2BsOfdmaDownlinkChannelEntry
        MAX-ACCESS  not-accessible
        STATUS      current
        DESCRIPTION
            "This table provides one row for each downlink channel of
             multi-sector BS. An entry in this table exists for each
             ifEntry of BS with an ifType of ieee80216WMAN."
        INDEX     { ifIndex }
        ::= { wmanIf2BsOfdmaDownlinkChannelTable 1 }

WmanIf2BsOfdmaDownlinkChannelEntry ::= SEQUENCE {
        wmanIf2BsOfdmaFrameDurationCode         INTEGER,
        wmanIf2BsOfdmaFftSize                   WmanIf2OfdmaFftSize,
        wmanIf2BsOfdmaHARQAckDelayULBurst       WmanIf2HarqAckDelay,
        wmanIf2BsOfdmaHarqZonePermutation       WmanIfPermutationType,
        wmanIf2BsOfdmaHMaxRetransmission        INTEGER,
        wmanIf2BsOfdmaCinrAlphaAvg              INTEGER,
        wmanIf2BsOfdmaRssiAlphaAvg              INTEGER,
        wmanIf2BsOfdmaDlAmcAlloPhyBandsBitmap   OCTET STRING,
        wmanIf2BsOfdmaHandoverSupported         WmanIf2HoSupportType,
        wmanIf2BsOfdmaThresholdAddBsDivSet      INTEGER,
        wmanIf2BsOfdmaThresholdDelBsDivSet      INTEGER,
        wmanIf2BsOfdmaAsrSlotLength             INTEGER,
        wmanIf2BsOfdmaAsrSwitchingPeriod        INTEGER,
        wmanIf2BsOfdmaHysteresisMargin          INTEGER,
        wmanIf2BsOfdmaTimeToTrigger             INTEGER,
        wmanIf2BsOfdmaRestartCount              INTEGER}

wmanIf2BsOfdmaFrameDurationCode OBJECT-TYPE
        SYNTAX      INTEGER {aASGap(0),
                             duration2ms(1),
                             duration2dot5ms(2),
                             duration4ms(3),
                             duration5ms(4),
                             duration8ms(5),
                             duration10ms(6),
                             duration12dot5ms(7),
                             duration20ms(8)}
        MAX-ACCESS  read-write
        STATUS      current
        DESCRIPTION
            "The duration of the frame. The frame duration code values
             are specified in Table 274."
        REFERENCE
            "Table 273, in IEEE Std 802.16-2004"
        ::= { wmanIf2BsOfdmaDownlinkChannelEntry 1 }

wmanIf2BsOfdmaFftSize OBJECT-TYPE
        SYNTAX      WmanIf2OfdmaFftSize
        MAX-ACCESS  read-write
        STATUS      current
        DESCRIPTION
            "This field indicates the channel BW in units of 125 kHz
             for OFDMA PHY."
        REFERENCE
            "Subclause 11.18.1, Table 384b in IEEE Std 802.16e-2005"
        ::= { wmanIf2BsOfdmaDownlinkChannelEntry 2 }

wmanIf2BsOfdmaHARQAckDelayULBurst OBJECT-TYPE
        SYNTAX      WmanIf2HarqAckDelay
        MAX-ACCESS  read-write
        STATUS      current
        DESCRIPTION
            "This object defines the OFDMA H-ARQ ACK delay for UL
             burst."
        REFERENCE 
            "Table 540, 544"
        ::= { wmanIf2BsOfdmaDownlinkChannelEntry 3 }
	    
wmanIf2BsOfdmaHarqZonePermutation OBJECT-TYPE
        SYNTAX      WmanIfPermutationType
        MAX-ACCESS  read-write
        STATUS      current
        DESCRIPTION
            "Permutation type for broadcast region in HARQ zone"
        REFERENCE
            "Table 544"
        ::= { wmanIf2BsOfdmaDownlinkChannelEntry 4 }

wmanIf2BsOfdmaHMaxRetransmission OBJECT-TYPE
        SYNTAX      INTEGER (0..255)
        MAX-ACCESS  read-write
        STATUS      current
        DESCRIPTION
            "Maximum number of retransmission in DL HARQ."
        REFERENCE
            "Table 358, in IEEE Std 802.16e-2005"
        DEFVAL      { 4 }
        ::= { wmanIf2BsOfdmaDownlinkChannelEntry 5 }
        
wmanIf2BsOfdmaCinrAlphaAvg OBJECT-TYPE
        SYNTAX      INTEGER (0..15)
        MAX-ACCESS  read-write
        STATUS      current
        DESCRIPTION
            "Bit 0..3 of Default RSSI and CINR averaging parameter
             TLV.
             
             Default averaging parameter Alpha Avg for physical
             CINR measurements, in multiples of 1/16. For example
             '0' means 1/16, 15 means 16/16."
        REFERENCE
            "Table 358, in IEEE Std 802.16e-2005"   
        DEFVAL      { 3 }
        ::= { wmanIf2BsOfdmaDownlinkChannelEntry 6 }
       
wmanIf2BsOfdmaRssiAlphaAvg OBJECT-TYPE
        SYNTAX      INTEGER (0..15)
        MAX-ACCESS  read-write
        STATUS      current
        DESCRIPTION
            "Bit 0..3 of Default RSSI and CINR averaging parameter
             TLV.
             
             Default averaging parameter Alpha Avg for physical
             RSSI measurements, in multiples of 1/16. For example
             '0' means 1/16, 15 means 16/16."
        REFERENCE
            "Table 358, in IEEE Std 802.16e-2005"   
        DEFVAL      { 3 }
        ::= { wmanIf2BsOfdmaDownlinkChannelEntry 7 }        

wmanIf2BsOfdmaDlAmcAlloPhyBandsBitmap OBJECT-TYPE
        SYNTAX      OCTET STRING (SIZE (6))
        MAX-ACCESS  read-write
        STATUS      current
        DESCRIPTION
            "A bitmap describing the physical bands allocated to the
             segment in the DL, when allocating AMC subchannels
             through the HARQ MAP, or through the Normal MAP, or for
             Band-AMC CINR reports, or using the optional AMC
             permutation (see 8.4.6.3). The LSB of the first byte
             shall correspond to band 0. For any bit that is not set,
             the corresponding band shall not be used by the SS on
             that segment. When this TLV is not present, BS may
             allocate any physical bands to an SS."
        REFERENCE
            "Table 358, in IEEE Std 802.16e-2005"
        ::= { wmanIf2BsOfdmaDownlinkChannelEntry 8 }

wmanIf2BsOfdmaHandoverSupported OBJECT-TYPE
        SYNTAX      WmanIf2HoSupportType
        MAX-ACCESS  read-write
        STATUS      current
        DESCRIPTION
            "Indicates the types of handover supported.
             Bit #0 = HO
             Bit #1 = MDHO
             Bit #2 = FBSS HO."
        REFERENCE
            "Table 544"   
        ::= { wmanIf2BsOfdmaDownlinkChannelEntry 9 }
       
wmanIf2BsOfdmaThresholdAddBsDivSet OBJECT-TYPE
        SYNTAX      INTEGER (0..255)
        UNITS       "dB"
        MAX-ACCESS  read-write
        STATUS      current
        DESCRIPTION
            "Threshold used by the MS to add a neighbor BS to the
             diversity set. When the CINR of a neighbor BS is higher
             than H_Add_Threshold, the MS should send MOB_MSHO-REQ to
             request adding this neighbor BS to the diversity set.
             This threshold is used for the MS that is performing 
             MDHO/FBSS HO. If the BS does not support FBSS HO/MDHO,
             this value is not set."
        REFERENCE
            "Table 358, in IEEE Std 802.16e-2005"   
        ::= { wmanIf2BsOfdmaDownlinkChannelEntry 10 }
       
wmanIf2BsOfdmaThresholdDelBsDivSet OBJECT-TYPE
        SYNTAX      INTEGER (0..255)
        UNITS       "dB"
        MAX-ACCESS  read-write
        STATUS      current
        DESCRIPTION
            "Threshold used by the MS to delete a neighbor BS to the
             diversity set. When the CINR of a neighbor BS is lower
             than H_Add_Threshold, the MS should send MOB_MSHO-REQ to
             request dropping this neighbor BS to the diversity set.
             This threshold is used for the MS that is performing 
             MDHO/FBSS HO. If the BS does not support FBSS HO/MDHO,
             this value is not set."
        REFERENCE
            "Table 358, in IEEE Std 802.16e-2005"   
        ::= { wmanIf2BsOfdmaDownlinkChannelEntry 12 }
       
wmanIf2BsOfdmaAsrSlotLength OBJECT-TYPE
        SYNTAX      INTEGER (0..15)
        UNITS       "Frames"
        MAX-ACCESS  read-write
        STATUS      current
        DESCRIPTION
            "Bit 0..3 of ASR Slot Length and Switching Period.
             For FBSS operation, the time axis is slotted by an ASR
             (Anchor Switch Reporting) slot that is
             wmanIf2BsOfdmaAsrSlotLength frame long."
        REFERENCE
            "Table 358, in IEEE Std 802.16e-2005"   
        ::= { wmanIf2BsOfdmaDownlinkChannelEntry 13 }	                            
       
wmanIf2BsOfdmaAsrSwitchingPeriod OBJECT-TYPE
        SYNTAX      INTEGER (0..15)
        UNITS       "ASR slots"
        MAX-ACCESS  read-write
        STATUS      current
        DESCRIPTION
            "Bit 0..3 of ASR Slot Length and Switching Period.
             A switching period is introduced whose duration is equals
             to wmanIf2BsOfdmaAsrSwitchingPeriod ASR slots that
             should be long enough such that certain process (e.g., 
             HARQ transmission, backhaul context transfer) can be
             completed at the current anchor BS before the MS switches
             to the new anchor BS."
        REFERENCE
            "Table 358, in IEEE Std 802.16e-2005"   
        ::= { wmanIf2BsOfdmaDownlinkChannelEntry 14 }

wmanIf2BsOfdmaHysteresisMargin OBJECT-TYPE
        SYNTAX      INTEGER (0..57)
        UNITS       "dB"
        MAX-ACCESS  read-write
        STATUS      current
        DESCRIPTION
            "When the CINR of a neighbor BS is larger than the sum of
             the CINR of the current serving BS and 
             wmanIf2BsOfdmaHysteresisMargin for the time-to-trigger
             duration, then the neighbor BS is included in the list
             of possible target BSs in MOB_MSHO-REQ."
        REFERENCE
            "Table 358, in IEEE Std 802.16e-2005"   
        ::= { wmanIf2BsOfdmaDownlinkChannelEntry 15 }

wmanIf2BsOfdmaTimeToTrigger OBJECT-TYPE
        SYNTAX      INTEGER
        UNITS       "milliseconds"
        MAX-ACCESS  read-write
        STATUS      current
        DESCRIPTION
            "Indicates the time duration for MS decides to select a
             neighbor BS as a possible target BS. It is  applicable
             only for HHO."
        REFERENCE
            "Table 358, in IEEE Std 802.16e-2005"   
        ::= { wmanIf2BsOfdmaDownlinkChannelEntry 16 }

wmanIf2BsOfdmaRestartCount OBJECT-TYPE
        SYNTAX      INTEGER (0..255)
        MAX-ACCESS  read-only
        STATUS      current
        DESCRIPTION
            "The value is incremented by one whenever BS restarts
             (see 6.3.9.11). The value rolls over from 0 to 255."
        REFERENCE
            "Table 358, in IEEE Std 802.16e-2005"   
        ::= { wmanIf2BsOfdmaDownlinkChannelEntry 17 }
                
wmanIf2BsOfdmaUcdBurstProfileTable OBJECT-TYPE
        SYNTAX      SEQUENCE OF WmanIf2BsOfdmaUcdBurstProfileEntry
        MAX-ACCESS  not-accessible
        STATUS      current
        DESCRIPTION
            "This table contains UCD burst profiles for each uplink
             channel"
        REFERENCE
            "Table 356, in IEEE Std 802.16-2004"
        ::= { wmanIf2BsOfdmaPhy 3 }

wmanIf2BsOfdmaUcdBurstProfileEntry OBJECT-TYPE
        SYNTAX      WmanIf2BsOfdmaUcdBurstProfileEntry
        MAX-ACCESS  not-accessible
        STATUS      current
        DESCRIPTION
            "This table provides one row for each UCD burst profile."
        INDEX     { ifIndex, wmanIf2BsOfdmaUiucIndex }
        ::= { wmanIf2BsOfdmaUcdBurstProfileTable 1 }

WmanIf2BsOfdmaUcdBurstProfileEntry ::= SEQUENCE {
        wmanIf2BsOfdmaUiucIndex                 INTEGER,
        wmanIf2BsOfdmaUcdFecCodeType            WmanIf2OfdmaUcdFecCode,
        wmanIf2BsOfdmaRangingDataRatio          INTEGER,
        wmanIf2BsOfdmaUcdBurstProfileRowStatus  RowStatus}

wmanIf2BsOfdmaUiucIndex OBJECT-TYPE
        SYNTAX      INTEGER (1 .. 10)
        MAX-ACCESS 	not-accessible
        STATUS      current
        DESCRIPTION
            "The Uplink Interval Usage Code indicates the uplink burst
             profile in the UCD message, and is used along with ifIndex
             to identify an entry in the
             wmanIf2BsOfdmaUcdBurstProfileTable."
        REFERENCE
            "Subclause 8.4.5.4.1, in IEEE Std 802.16-2004"
        ::= { wmanIf2BsOfdmaUcdBurstProfileEntry 1 }

wmanIf2BsOfdmaUcdFecCodeType OBJECT-TYPE
        SYNTAX      WmanIf2OfdmaUcdFecCode
        MAX-ACCESS  read-create
        STATUS      current
        DESCRIPTION
            "Uplink FEC code type and modulation type"
        REFERENCE
            "Table 543"
        ::= { wmanIf2BsOfdmaUcdBurstProfileEntry 2 }

wmanIf2BsOfdmaRangingDataRatio OBJECT-TYPE
        SYNTAX      INTEGER (-128 .. 127)
        UNITS       "dB"
        MAX-ACCESS  read-create
        STATUS      current
        DESCRIPTION
            "Reducing factor in units of 1 dB, between the power used
             for this burst and power should be used for CDMA Ranging."
        REFERENCE
        "Subclause 11.3.1.1, Table 357, in IEEE Std 802.16-2004"
        ::= { wmanIf2BsOfdmaUcdBurstProfileEntry 3 }

wmanIf2BsOfdmaUcdBurstProfileRowStatus OBJECT-TYPE
        SYNTAX      RowStatus
        MAX-ACCESS  read-create
        STATUS      current
        DESCRIPTION
            "This object is used to create a new row or modify or delete
             an existing row in this table. If the implementator of this
             MIB has choosen not to implement 'dynamic assignment' of
             profiles, this object is not useful and should return
             noSuchName upon SNMP request."
        ::= { wmanIf2BsOfdmaUcdBurstProfileEntry 5 }

wmanIf2BsOfdmaDcdBurstProfileTable OBJECT-TYPE
        SYNTAX      SEQUENCE OF WmanIf2BsOfdmaDcdBurstProfileEntry
        MAX-ACCESS  not-accessible
        STATUS      current
        DESCRIPTION
            "This table provides one row for each DCD burst profile."
        ::= { wmanIf2BsOfdmaPhy 4 }

wmanIf2BsOfdmaDcdBurstProfileEntry OBJECT-TYPE
        SYNTAX      WmanIf2BsOfdmaDcdBurstProfileEntry
        MAX-ACCESS  not-accessible
        STATUS      current
        DESCRIPTION
            "This table provides one row for each DCD burst profile."
        INDEX     { ifIndex, wmanIf2BsOfdmaDiucIndex }
        ::= { wmanIf2BsOfdmaDcdBurstProfileTable 1 }

WmanIf2BsOfdmaDcdBurstProfileEntry ::= SEQUENCE {
        wmanIf2BsOfdmaDiucIndex                 INTEGER,
        wmanIf2BsOfdmaDcdFecCodeType            WmanIf2OfdmaDcdFecCode,
        wmanIf2BsOfdmaDcdBurstProfileRowStatus  RowStatus}
                                                
wmanIf2BsOfdmaDiucIndex OBJECT-TYPE
        SYNTAX      INTEGER (0 .. 12)
        MAX-ACCESS  not-accessible
        STATUS      current
        DESCRIPTION
            "The Downlink Interval Usage Code indicates the downlink
             burst profile in the DCD message, and is used along with
             ifIndex to identify an entry in the
             wmanIf2BsOfdmaDcdBurstProfileTable."
        REFERENCE
            "Subclause 8.4.5.3.1, in IEEE Std 802.16-2004"
        ::= { wmanIf2BsOfdmaDcdBurstProfileEntry 1 }

wmanIf2BsOfdmaDcdFecCodeType OBJECT-TYPE
        SYNTAX      WmanIf2OfdmaDcdFecCode
        MAX-ACCESS  read-create
        STATUS      current
        DESCRIPTION
            "Downlink FEC code type and modulation type"
        REFERENCE
            "Table 549"
        ::= { wmanIf2BsOfdmaDcdBurstProfileEntry 2 }
        
wmanIf2BsOfdmaDcdBurstProfileRowStatus OBJECT-TYPE
        SYNTAX      RowStatus
        MAX-ACCESS  read-create
        STATUS      current
        DESCRIPTION
            "This object is used to create a new row or modify or delete
             an existing row in this table. If the implementator of this
             MIB has choosen not to implement 'dynamic assignment' of
             profiles, this object is not useful and should return
             noSuchName upon SNMP request."
        ::= { wmanIf2BsOfdmaDcdBurstProfileEntry 3 }

--
-- wmanIf2BsAm group – containing tables and objects related to Account
--                     Management
--
wmanIf2BsOtaUsageDataRecordTable OBJECT-TYPE
        SYNTAX      SEQUENCE OF WmanIf2BsOtaUsageDataRecordEntry
        MAX-ACCESS  not-accessible
        STATUS      current
        DESCRIPTION
            "This table contains counters to keep track of the number
             of packets and octets that have been received or 
             transmitted over the air interface. BS may delete some
             OTA UDR in wmanIf2BsOtaUsageDataRecordTable after they
             have been transferred to the AAA server."        
        ::= { wmanIf2BsAm 1 }

wmanIf2BsOtaUsageDataRecordEntry OBJECT-TYPE
        SYNTAX      WmanIf2BsOtaUsageDataRecordEntry
        MAX-ACCESS  not-accessible
        STATUS      current
        DESCRIPTION 
           "This table provides one row for each session, and Since MAC
            management CID (i.e. basic , primary, and 2nd management)
            share the same CID for both UL and DL, it should use the QoS
            parameter set to distinguish which entry is DL or UL."
        INDEX     { ifIndex,
                    wmanIf2BsSsMacAddress,
                    wmanIf2BsCid,
                    wmanIf2BsSessionId }
        ::= { wmanIf2BsOtaUsageDataRecordTable 1 }

WmanIf2BsOtaUsageDataRecordEntry::= SEQUENCE {
        wmanIf2BsSessionId                      Unsigned32,
        wmanIf2BsCid                            INTEGER,
        wmanIf2BsServiceFlowId                  Unsigned32,
        wmanIf2BsMacSduCount                    Counter64,
        wmanIf2BsOctetCount                     Counter64,
        wmanIf2BsSessionEstablishTime           TimeStamp,
        wmanIf2BsSessionTerminateTime           TimeStamp,
        wmanIf2BsGlobalServiceClass             WmanIf2GlobalSrvClass,
        wmanIf2BsQoSProfileIndex                INTEGER}

wmanIf2BsSessionId OBJECT-TYPE
        SYNTAX      Unsigned32 (1 .. 4294967295)
        MAX-ACCESS  not-accessible
        STATUS      current
        DESCRIPTION
            "An index identifies the accounting seesion within a CID.
             An accounting session may be created or ended, based on
             certain events, for example
                 - QoS parameter set change in a CID
                 - wmanIf2BsServiceFlowState is changed
                 - an SS registers at the BS
                 - an MS handoffs to another BS"
        ::= { wmanIf2BsOtaUsageDataRecordEntry 1 }

wmanIf2BsCid OBJECT-TYPE
        SYNTAX      INTEGER (0 .. 65535)
        MAX-ACCESS  not-accessible
        STATUS      current
        DESCRIPTION
            "A 16 bit channel identifier points to the connection being
             created by DSA for this service flow."
        ::= { wmanIf2BsOtaUsageDataRecordEntry 2 }
                
wmanIf2BsServiceFlowId OBJECT-TYPE
        SYNTAX      Unsigned32 (1 .. 4294967295)
        MAX-ACCESS  read-only
        STATUS      current
        DESCRIPTION
            "A 32 bit quantity that uniquely identifies a service flow.
             wmanIf2BsServiceFlowId should return '0' for MAC
             management (i.e. basic, primary, and 2nd management CID)."
        ::= { wmanIf2BsOtaUsageDataRecordEntry 3 }
        
wmanIf2BsMacSduCount OBJECT-TYPE
        SYNTAX      Counter64
        UNITS       "SDU"
        MAX-ACCESS  read-only
        STATUS      current
        DESCRIPTION
            "This object counts the number of MAC SDUs or MAC messages
             that have been transmitted or received over the air
             interface. For MAC management CID, wmanIf2BsMacSduCount
             tracks SDU count on DL and UL."
        ::= { wmanIf2BsOtaUsageDataRecordEntry 4 }

wmanIf2BsOctetCount OBJECT-TYPE
        SYNTAX      Counter64
        UNITS       "Octet"
        MAX-ACCESS  read-only
        STATUS      current
        DESCRIPTION
            "This object counts the number of octets of MAC SDUs or MAC
             messages that have been transmitted or received over the
             air interface."
        ::= { wmanIf2BsOtaUsageDataRecordEntry 5 }
        
wmanIf2BsSessionEstablishTime OBJECT-TYPE
        SYNTAX      TimeStamp
        MAX-ACCESS  read-only
        STATUS      current
        DESCRIPTION
            "Indicates the date and time when the session is established
             ."
        ::= { wmanIf2BsOtaUsageDataRecordEntry 6 }

wmanIf2BsSessionTerminateTime OBJECT-TYPE
        SYNTAX      TimeStamp
        MAX-ACCESS  read-only
        STATUS      current
        DESCRIPTION
            "Indicates the date and time when the session is terminated
             ."
        ::= { wmanIf2BsOtaUsageDataRecordEntry 7 }
        
wmanIf2BsGlobalServiceClass OBJECT-TYPE
        SYNTAX      WmanIf2GlobalSrvClass
        MAX-ACCESS  read-only
        STATUS      current
        DESCRIPTION
            "This object defines the QoS parameter set used in this
             session. When '0' is returned from reading this object, it
             means either no global service class is available for this
             session, or its Qos profile may be defined in the entry
             pointed by wmanIf2BsQoSProfileIndex."
        REFERENCE
            "Subclause 6.3.14.4.1 Table 124a in IEEE Std 802.16e-2005"
        ::= { wmanIf2BsOtaUsageDataRecordEntry 8 }

wmanIf2BsQoSProfileIndex OBJECT-TYPE
        SYNTAX      INTEGER (1 .. 65535)
        MAX-ACCESS  read-only
        STATUS      current
        DESCRIPTION
            "This index points to an entry in wmanIf2mCmnQoSProfileTable
             that defines the the QoS parameter set used in this
             session. When '0' is returned from reading this object, it
             means the QoS profile either is not available for this
             session."
        REFERENCE            
            "Subclause 6.3.13 and 6.3.14 in IEEE Std 802.16-2004"
        ::= { wmanIf2BsOtaUsageDataRecordEntry 9 }
        
--
-- wmanIf2BsPm group – containing tables and objects related to
--                     Performance Management
--        
wmanIf2BsChannelMeasurementTable OBJECT-TYPE
        SYNTAX      SEQUENCE OF   WmanIf2BsChannelMeasurementEntry
        MAX-ACCESS  not-accessible
        STATUS      current
        DESCRIPTION
            "This table contains channel measurement information as
             derived from BS measurement of uplink signal from SS,
             and the downlink signal as reported from SS using
             REP-REQ/RSP messages. The table shall be maintained as
             FIFO to store measurement samples that can be used to
             create RSSI and CINR histogram report. When the
             measurement entry for a SS reaches the limit, the oldest
             entry shall be deleted as the new entry is added to the
             table."
        REFERENCE
            "6.3.2.3.33 in IEEE Std 802.16-2004"
        ::= { wmanIf2BsPm 1 }

wmanIf2BsChannelMeasurementEntry OBJECT-TYPE
        SYNTAX      WmanIf2BsChannelMeasurementEntry
        MAX-ACCESS  not-accessible
        STATUS      current
        DESCRIPTION
            "Each entry in the table contains RSSI and CINR
             signal quality measurement on signal received from the SS.
             The primary index is the ifIndex with ifType of
             ieee80216WMAN identifing the BS sector.
             wmanIf2BsSsMacAddress identifies the SS from which the
             signal was received. wmanIf2BsChannelDirection is the
             index to the direction of the channel. 
             wmanIf2BsHistogramIndex is the index to histogram samples.
             Since there is no time stamp in the table, 
             wmanIf2BsHistogramIndex should be increased monotonically,
             and wraps around when it reaches the implementation
             specific limit."
        INDEX     { ifIndex,
                    wmanIf2BsSsMacAddress,
                    wmanIf2BsChannelDirection,
                    wmanIf2BsHistogramIndex }
        ::= { wmanIf2BsChannelMeasurementTable  1 }

WmanIf2BsChannelMeasurementEntry ::= SEQUENCE {
        wmanIf2BsChannelDirection               WmanIf2LinkDirection, 
        wmanIf2BsHistogramIndex                 Unsigned32,
        wmanIf2BsChannelNumber                  WmanIf2ChannelNumber,
        wmanIf2BsStartFrame                     INTEGER,
        wmanIf2BsDuration                       INTEGER,
        wmanIf2BsBasicReport                    BITS,
        wmanIf2BsMeanCinrReport                 INTEGER,
        wmanIf2BsMeanRssiReport                 INTEGER,
        wmanIf2BsStdDeviationCinrReport         INTEGER,
        wmanIf2BsStdDeviationRssiReport         INTEGER}

wmanIf2BsChannelDirection OBJECT-TYPE
        SYNTAX      WmanIf2LinkDirection 
        MAX-ACCESS  not-accessible
        STATUS      current
        DESCRIPTION
            "wmanIf2BsChannelDirection identifies the direction of a
             a channel where the measurement takes place."
        ::= { wmanIf2BsChannelMeasurementEntry 1 }

wmanIf2BsHistogramIndex OBJECT-TYPE
        SYNTAX      Unsigned32 (1 .. 4294967295) 
        MAX-ACCESS  read-only
        STATUS      current
        DESCRIPTION
            "wmanIf2BsHistogramIndex identifies the histogram samples
             in the table for each subscriber station."
        ::= { wmanIf2BsChannelMeasurementEntry 2 }
                 
wmanIf2BsChannelNumber OBJECT-TYPE
        SYNTAX      WmanIf2ChannelNumber 
        MAX-ACCESS  read-only
        STATUS      current
        DESCRIPTION
            "Physical channel number to be reported on is only
             applicable to license exempt band. For licensed band,
             this parameter should be null."
        REFERENCE
            "Subclause 11.12 in IEEE Std 802.16-2004"
        ::= { wmanIf2BsChannelMeasurementEntry 3 }
               
wmanIf2BsStartFrame OBJECT-TYPE
        SYNTAX      INTEGER (0..65535) 
        MAX-ACCESS  read-only
        STATUS      current
        DESCRIPTION
            "Frame number in which measurement for this channel
             started."
        REFERENCE
            "Subclause 11.12 in IEEE Std 802.16-2004"
        ::= { wmanIf2BsChannelMeasurementEntry 4 }
                
wmanIf2BsDuration OBJECT-TYPE
        SYNTAX      INTEGER (0 .. 16777215) 
        MAX-ACCESS  read-only
        STATUS      current
        DESCRIPTION
            "Cumulative measurement duration on the channel in
             multiples of Ts. For any value exceeding 0xFFFFFF,
             report 0xFFFFFF."
        REFERENCE
            "Subclause 11.12 in IEEE Std 802.16-2004"
        ::= { wmanIf2BsChannelMeasurementEntry 5 }
                        
wmanIf2BsBasicReport OBJECT-TYPE
        SYNTAX      BITS {wirelessHuman(0),
                          unknownTransmission(1),
                          primaryUser(2),
                          channelNotMeasured(3)}                          
        MAX-ACCESS  read-only
        STATUS      current
        DESCRIPTION
            "Bit #0: WirelessHUMAN detected on the channel
             Bit #1: Unknown transmissions detected on the channel
             Bit #2: Primary User detected on the channel
             Bit #3: Unmeasured. Channel not measured"
        REFERENCE
            "Subclause 11.12 in IEEE Std 802.16-2004"
        ::= { wmanIf2BsChannelMeasurementEntry 6 }                        
                                          
wmanIf2BsMeanCinrReport OBJECT-TYPE
        SYNTAX      INTEGER (-20 .. 37) 
        UNITS       "dB"
        MAX-ACCESS  read-only
        STATUS      current
        DESCRIPTION
            "Mean CINR report."
        REFERENCE
            "Subclause 8.2.2, 8.3.9 in IEEE Std 802.16-2004"
        ::= { wmanIf2BsChannelMeasurementEntry 7 }
                                          
wmanIf2BsMeanRssiReport OBJECT-TYPE
        SYNTAX      INTEGER (-123 .. -40)
        UNITS       "dBm" 
        MAX-ACCESS  read-only
        STATUS      current
        DESCRIPTION
            "Mean RSSI report."
        REFERENCE
            "Subclause 8.2.2, 8.3.9 in IEEE Std 802.16-2004"
        ::= { wmanIf2BsChannelMeasurementEntry 8 }
        
wmanIf2BsStdDeviationCinrReport OBJECT-TYPE
        SYNTAX      INTEGER (0 .. 29) 
        UNITS       "dB"
        MAX-ACCESS  read-only
        STATUS      current
        DESCRIPTION
             "Standard deviation CINR report."
        REFERENCE
            "Subclause 8.2.2, 8.3.9 in IEEE Std 802.16-2004"
        ::= { wmanIf2BsChannelMeasurementEntry 9 }
                                          
wmanIf2BsStdDeviationRssiReport OBJECT-TYPE
        SYNTAX      INTEGER (0 .. 42)
        UNITS       "dB"
        MAX-ACCESS  read-only
        STATUS      current
        DESCRIPTION
             "Standard deviation RSSI report."
        REFERENCE
            "Subclause 8.2.2, 8.3.9 in IEEE Std 802.16-2004"
        ::= { wmanIf2BsChannelMeasurementEntry 10 }

-- 
-- Statistics Configuration Table
--         
wmanIf2BsStatisticsConfigTable OBJECT-TYPE
        SYNTAX      SEQUENCE OF WmanIf2BsStatisticsConfigEntry
        MAX-ACCESS  not-accessible
        STATUS      current
        DESCRIPTION
            "This table contains the configuration of statistics
             information capture."
        ::= { wmanIf2BsPm 2 }

wmanIf2BsStatisticsConfigEntry OBJECT-TYPE
        SYNTAX      WmanIf2BsStatisticsConfigEntry
        MAX-ACCESS  not-accessible
        STATUS      current
        DESCRIPTION
            "This table provides one row for each BS sector."
        INDEX     { ifIndex }
        ::= { wmanIf2BsStatisticsConfigTable  1 }

WmanIf2BsStatisticsConfigEntry ::= SEQUENCE {
        wmanIf2BsDataSampleInterval           INTEGER,
        wmanIf2BsCountersReportInterval       INTEGER}

wmanIf2BsDataSampleInterval OBJECT-TYPE
        SYNTAX      INTEGER
        UNITS       "Seconds"
        MAX-ACCESS  read-write
        STATUS      current
        DESCRIPTION
            "This object determines the interval that the BS uses to
             measure the peak and average data rate statistics to be
             stored in wmanIf2BsDataRateStatisticsTable."
        DEFVAL      { 1 }
        ::= { wmanIf2BsStatisticsConfigEntry 1 }

wmanIf2BsCountersReportInterval OBJECT-TYPE
        SYNTAX      INTEGER
        UNITS       "Minutes"
        MAX-ACCESS  read-write
        STATUS      current
        DESCRIPTION
            "This object determines the interval that the BS shall
             generate an event trap to report the performance counters
             to EMS. BS should reset all counters after they have been
             reported to EMS via wmanIf2BsPerformanceCountersTrap."
        DEFVAL      { 15 }
        ::= { wmanIf2BsStatisticsConfigEntry 2 }
                        
-- 
-- Mobile Station startup statistics Table
--         
wmanIf2BsSsStartupStatisticsTable OBJECT-TYPE
        SYNTAX      SEQUENCE OF WmanIf2BsSsStartupStatisticsEntry
        MAX-ACCESS  not-accessible
        STATUS      current
        DESCRIPTION
            "This table contains statistical information that can be
             used to characterize SS' performance during the startup.
             BS should reset all counters after they have been reported
             to EMS via wmanIf2BsPerformanceCountersTrap."
        ::= { wmanIf2BsPm 3 }

wmanIf2BsSsStartupStatisticsEntry OBJECT-TYPE
        SYNTAX      WmanIf2BsSsStartupStatisticsEntry
        MAX-ACCESS  not-accessible
        STATUS      current
        DESCRIPTION
            "This table provides one row for each BS sector."
        INDEX     { ifIndex }
        ::= { wmanIf2BsSsStartupStatisticsTable  1 }

WmanIf2BsSsStartupStatisticsEntry ::= SEQUENCE {
        wmanIf2BsSsAuthenAttempt                Counter64, 
        wmanIf2BsSsAuthenSuccess                Counter64,
        wmanIf2BsSsAuthenSuccessRate            INTEGER,
        wmanIf2BsSsRangingAttempt               Counter64, 
        wmanIf2BsSsRangingSuccess               Counter64,
        wmanIf2BsSsRangingSuccessRate           INTEGER}

wmanIf2BsSsAuthenAttempt OBJECT-TYPE
        SYNTAX      Counter64 
        MAX-ACCESS  read-only
        STATUS      current
        DESCRIPTION
            "This object counts the number of SS authentication
             attempt. The BS increments the counter by one each time
             the BS receives:
               1) PKMv1 Auth Request,
               2) PKMv2 RSA-Request,
               3) PKMv2 EAP start message."
        ::= { wmanIf2BsSsStartupStatisticsEntry 1 }
        
wmanIf2BsSsAuthenSuccess OBJECT-TYPE
        SYNTAX      Counter64 
        MAX-ACCESS  read-only
        STATUS      current
        DESCRIPTION
            "This object counts the number of successful SS
             authentication. The BS increments the counter by one each
             time the BS sends:
               1) PKMv1 Auth Reply,
               2) PKMv2 RSA-Reply,
               3) PKMv2 EAP complete with EAP-success payload message."
        ::= { wmanIf2BsSsStartupStatisticsEntry 2 }

wmanIf2BsSsAuthenSuccessRate OBJECT-TYPE
        SYNTAX      INTEGER 
        MAX-ACCESS  read-only
        STATUS      current
        DESCRIPTION
            "wmanIf2BsSsAuthenSuccessRate % =
             wmanIf2BsSsAuthenSuccess  / wmanIf2BsSsAuthenAttempt * 100"
        ::= { wmanIf2BsSsStartupStatisticsEntry 3 }
        
wmanIf2BsSsRangingAttempt OBJECT-TYPE
        SYNTAX      Counter64
        MAX-ACCESS  read-only
        STATUS      current
        DESCRIPTION
            "This object counts the number of SS Ranging attempt. The BS
             increments the counter by one each time the BS receives the
             RNG-REQ message."
        ::= { wmanIf2BsSsStartupStatisticsEntry 4 }
        
wmanIf2BsSsRangingSuccess OBJECT-TYPE
        SYNTAX      Counter64 
        MAX-ACCESS  read-only
        STATUS      current
        DESCRIPTION
            "This object counts the number of successful SS Ranging.
             The increments the counter by one each time the BS sends
             the RNG-RSP message."
        ::= { wmanIf2BsSsStartupStatisticsEntry 5 }

wmanIf2BsSsRangingSuccessRate OBJECT-TYPE
        SYNTAX      INTEGER
        MAX-ACCESS  read-only
        STATUS      current
        DESCRIPTION
            "wmanIf2BsSsRangingSuccessRate % =
             wmanIf2BsSsNetwkEntrySuccess / wmanIf2BsSsNetwkEntryAttempt 
             * 100."
        ::= { wmanIf2BsSsStartupStatisticsEntry 6 }

--  
-- Base Station Data Rate Statistics Table
--         
wmanIf2BsDataRateStatisticsTable OBJECT-TYPE
        SYNTAX      SEQUENCE OF WmanIf2BsDataRateStatisticsEntry
        MAX-ACCESS  not-accessible
        STATUS      current
        DESCRIPTION
            "This table contains the average and peak data rate
             statistics at the BS sector level. The BS measures the
             number of bytes that are sent or received withing each
             interval set by the wmanIf2BsDataSampleInterval object.
             
             For example:
             S = the number of bytes measured in an interval
             N = the number of measurements

             Avg(N) = the average data rate after N measurements
             Avg(0) = S, the 1st measurement
             Avg(N) = (Avg(N-1)*(N-1) + S) / N

             Peak(N) = the peak data rate after N measurement
             Peak(0) = S, the 1st measurement
             Peak(N) = S if S > Peak(N-1)
                     = Peak(N -1) if S <= Peak(N-1)
             BS should reset all counters after they have been reported
             to EMS via wmanIf2BsPerformanceCountersTrap."
        ::= { wmanIf2BsPm 4 }

wmanIf2BsDataRateStatisticsEntry OBJECT-TYPE
        SYNTAX      WmanIf2BsDataRateStatisticsEntry
        MAX-ACCESS  not-accessible
        STATUS      current
        DESCRIPTION
            "This table provides one row for each BS sector."
        INDEX     { ifIndex }
        ::= { wmanIf2BsDataRateStatisticsTable 1 }

WmanIf2BsDataRateStatisticsEntry ::= SEQUENCE { 
        wmanIf2BsAvgDlUserThroughput            Counter32,
        wmanIf2BsAvgUlUserThroughput            Counter32,
        wmanIf2BsAvgDlMacThroughput             Counter32,
        wmanIf2BsAvgUlMacThroughput             Counter32,
        wmanIf2BsAvgDlPhyThroughput             Counter32,
        wmanIf2BsAvgUlPhyThroughput             Counter32,        
        wmanIf2BsPeakDlUserThroughput           Counter32,
        wmanIf2BsPeakUlUserThroughput           Counter32,
        wmanIf2BsPeakDlMacThroughput            Counter32,
        wmanIf2BsPeakUlMacThroughput            Counter32,
        wmanIf2BsPeakDlPhyThroughput            Counter32,
        wmanIf2BsPeakUlPhyThroughput            Counter32,
        wmanIf2BsAvgDlCellEdgeThroughput        Counter32,
        wmanIf2BsAvgUlCellEdgeThroughput        Counter32,
        wmanIf2BsDataRateMeasurements           Counter64}

wmanIf2BsAvgDlUserThroughput OBJECT-TYPE
        SYNTAX      Counter32
        UNITS       "Octet"        
        MAX-ACCESS  read-only
        STATUS      current
        DESCRIPTION
            "This object records the average downlink user throughput
             Avg(N). Each measurement indicates the number of octets of
             MAC SDUs that are sent within the
             wmanIf2BsDataSampleInterval interval."
        ::= { wmanIf2BsDataRateStatisticsEntry 1 }   

wmanIf2BsAvgUlUserThroughput OBJECT-TYPE
        SYNTAX      Counter32
        UNITS       "Octet"        
        MAX-ACCESS  read-only
        STATUS      current
        DESCRIPTION
            "This object records the average uplink user throughput
             Avg(N). Each measurement indicates the number of octets of
             MAC SDUs that are received within the
             wmanIf2BsDataSampleInterval interval."
        ::= { wmanIf2BsDataRateStatisticsEntry 2 }

wmanIf2BsAvgDlMacThroughput OBJECT-TYPE
        SYNTAX      Counter32
        UNITS       "Octet"        
        MAX-ACCESS  read-only
        STATUS      current
        DESCRIPTION
            "This object records the average downlink MAC throughput
             Avg(N). Each measurement indicates the number of octets of
             MAC PDUs (i.e. user data, MAC headers, and MAC management
             messages) that are sent within the
             wmanIf2BsDataSampleInterval interval."
        ::= { wmanIf2BsDataRateStatisticsEntry 3 }   

wmanIf2BsAvgUlMacThroughput OBJECT-TYPE
        SYNTAX      Counter32
        UNITS       "Octet"        
        MAX-ACCESS  read-only
        STATUS      current
        DESCRIPTION
            "This object records the average uplink MAC throughput
             Avg(N). Each measurement indicates the number of octets of
             MAC PDUs (i.e. user data, MAC headers, and MAC management
             messages) that are received within the
             wmanIf2BsDataSampleInterval interval."
        ::= { wmanIf2BsDataRateStatisticsEntry 4 }

wmanIf2BsAvgDlPhyThroughput OBJECT-TYPE
        SYNTAX      Counter32
        UNITS       "Octet"        
        MAX-ACCESS  read-only
        STATUS      current
        DESCRIPTION
            "This object records the average downlink PHY throughput
             Avg(N). Each measurement indicates the number of octets of
             bursts (i.e. MAC PDU + PHY overheads) that are sent within
             the wmanIf2BsDataSampleInterval interval."
        ::= { wmanIf2BsDataRateStatisticsEntry 5 }   

wmanIf2BsAvgUlPhyThroughput OBJECT-TYPE
        SYNTAX      Counter32
        UNITS       "Octet"        
        MAX-ACCESS  read-only
        STATUS      current
        DESCRIPTION
            "This object records the average uplink PHY throughput
             Avg(N). Each measurement indicates the number of octets of
             bursts (i.e. MAC PDU + PHY overheads) that are received
             within the wmanIf2BsDataSampleInterval interval."
        ::= { wmanIf2BsDataRateStatisticsEntry 6 }

wmanIf2BsPeakDlUserThroughput OBJECT-TYPE
        SYNTAX      Counter32
        UNITS       "Octet"        
        MAX-ACCESS  read-only
        STATUS      current
        DESCRIPTION
            "This object records the peak downlink user throughput
             Peak(N). Each measurement indicates the number of octets of
             MAC SDUs that are sent within the
             wmanIf2BsDataSampleInterval interval."
        ::= { wmanIf2BsDataRateStatisticsEntry 7 }   

wmanIf2BsPeakUlUserThroughput OBJECT-TYPE
        SYNTAX      Counter32
        UNITS       "Octet"        
        MAX-ACCESS  read-only
        STATUS      current
        DESCRIPTION
            "This object records the peak uplink user throughput Peak(N)
             . Each measurement indicates the number of octets of MAC
             SDUs that are received within the
             wmanIf2BsDataSampleInterval interval."
        ::= { wmanIf2BsDataRateStatisticsEntry 8 }

wmanIf2BsPeakDlMacThroughput OBJECT-TYPE
        SYNTAX      Counter32
        UNITS       "Octet"        
        MAX-ACCESS  read-only
        STATUS      current
        DESCRIPTION
            "This object records the peak downlink MAC throughput
             Peak(N). Each measurement indicates the number of octets of
             MAC PDUs (i.e. user data, MAC headers, and MAC management
             messages) that are sent within the
             wmanIf2BsDataSampleInterval interval."
        ::= { wmanIf2BsDataRateStatisticsEntry 9 }   

wmanIf2BsPeakUlMacThroughput OBJECT-TYPE
        SYNTAX      Counter32
        UNITS       "Octet"        
        MAX-ACCESS  read-only
        STATUS      current
        DESCRIPTION
            "This object records the peak uplink MAC throughput Peak(N).
             Each measurement indicates the number of octets of MAC PDUs
             (i.e. user data, MAC headers, and MAC management messages)
             that are received within the wmanIf2BsDataSampleInterval
             interval."
        ::= { wmanIf2BsDataRateStatisticsEntry 10 }

wmanIf2BsPeakDlPhyThroughput OBJECT-TYPE
        SYNTAX      Counter32
        UNITS       "Octet"        
        MAX-ACCESS  read-only
        STATUS      current
        DESCRIPTION
            "This object records the peak downlink PHY throughput
             Peak(N). Each measurement indicates the number of octets of
             bursts (i.e. MAC PDU + PHY overheads) that are sent within
             the wmanIf2BsDataSampleInterval interval."
        ::= { wmanIf2BsDataRateStatisticsEntry 11 }   

wmanIf2BsPeakUlPhyThroughput OBJECT-TYPE
        SYNTAX      Counter32
        UNITS       "Octet"        
        MAX-ACCESS  read-only
        STATUS      current
        DESCRIPTION
            "This object records the peak uplink PHY throughput Peak(N).
             Each measurement indicates the number of octets of bursts
             (i.e. MAC PDU + PHY overheads) that are received within the
             wmanIf2BsDataSampleInterval interval."
        ::= { wmanIf2BsDataRateStatisticsEntry 12 }

wmanIf2BsAvgDlCellEdgeThroughput OBJECT-TYPE
        SYNTAX      Counter32
        UNITS       "Octet"        
        MAX-ACCESS  read-only
        STATUS      current
        DESCRIPTION
            "This object records the Average downlink MAC throughput
             Avg(N). Each measurement indicates the number of octets of
             MAC PDU that are sent within the
             wmanIf2BsDataSampleInterval interval using the most robust
             coding (i.e. QPSK)."
        ::= { wmanIf2BsDataRateStatisticsEntry 13 }   

wmanIf2BsAvgUlCellEdgeThroughput OBJECT-TYPE
        SYNTAX      Counter32
        UNITS       "Octet"        
        MAX-ACCESS  read-only
        STATUS      current
        DESCRIPTION
            "This object records the peak uplink PHY throughput Peak(N).
             Each measurement indicates the number of octets of MAC PDU
             that are received within the wmanIf2BsDataSampleInterval
             interval using the most robust coding (i.e. QPSK)."
        ::= { wmanIf2BsDataRateStatisticsEntry 14 }
                
wmanIf2BsDataRateMeasurements OBJECT-TYPE
        SYNTAX      Counter64        
        MAX-ACCESS  read-only
        STATUS      current
        DESCRIPTION
            "This object tracks the number of measurements 'N'."
        ::= { wmanIf2BsDataRateStatisticsEntry 15 }

-- 
-- Base Station Network Entry Statistics Table
--         
wmanIf2BsNetworkEntryStatisticsTable OBJECT-TYPE
        SYNTAX      SEQUENCE OF WmanIf2BsNetworkEntryStatisticsEntry
        MAX-ACCESS  not-accessible
        STATUS      current
        DESCRIPTION
            "This table contains the average and maximum amount of time
             for network entry and network re-entry.
             
             For example:
             T = a) Network entry time is the amount of time between:
                    1. BS received the 1st RNG-REQ from a SS
                    2. BS sends the DSA-RSP to such SS
                 b) Network re-entry time is the amount of time between:
                    1. BS received the 1st RNG-REQ from a SS with the
                       Ranging Purpose Indication TLV to indicate that
                       the SS is leaving the idle mode   
                    2. BS sends the DSA-RSP to such SS                                   
             N = the number of network entries

             Avg(N) = the average amount of time after N network entries
             Avg(0) = T, the 1st network entry
             Avg(N) = (Avg(N-1)*(N-1) + T) / N

             Max(N) = the maximum amount of time after N network entries
             Max(0) = T, the 1st network entry
             Max(N) = T if T > Max(N-1)
                     = Max(N-1) if T <= Max(N-1)
             BS should reset all counters after they have been reported
             to EMS via wmanIf2BsPerformanceCountersTrap."
        ::= { wmanIf2BsPm 5 }

wmanIf2BsNetworkEntryStatisticsEntry OBJECT-TYPE
        SYNTAX      WmanIf2BsNetworkEntryStatisticsEntry
        MAX-ACCESS  not-accessible
        STATUS      current
        DESCRIPTION
            "This table provides one row for each BS sector."
        INDEX     { ifIndex }
        ::= { wmanIf2BsNetworkEntryStatisticsTable 1 }

WmanIf2BsNetworkEntryStatisticsEntry ::= SEQUENCE { 
        wmanIf2BsAvgNetworkEntryTime            INTEGER,
        wmanIf2BsMaxNetworkEntryTime            INTEGER,
        wmanIf2BsAvgNetworkReEntryTime          INTEGER,
        wmanIf2BsMaxNetworkReEntryTime          INTEGER,
        wmanIf2BsNumOfNetworkEntries            Counter64,
        wmanIf2BsNumOfNetworkReEntries          Counter64}

wmanIf2BsAvgNetworkEntryTime OBJECT-TYPE
        SYNTAX      INTEGER
        UNITS       "second"        
        MAX-ACCESS  read-only
        STATUS      current
        DESCRIPTION
            "This object records the average network entry time Avg(N)."
        ::= { wmanIf2BsNetworkEntryStatisticsEntry 1 }   

wmanIf2BsMaxNetworkEntryTime OBJECT-TYPE
        SYNTAX      INTEGER
        UNITS       "second"        
        MAX-ACCESS  read-only
        STATUS      current
        DESCRIPTION
            "This object records the maximum network entry time Max(N)."
        ::= { wmanIf2BsNetworkEntryStatisticsEntry 2 }

wmanIf2BsAvgNetworkReEntryTime OBJECT-TYPE
        SYNTAX      INTEGER
        UNITS       "second"        
        MAX-ACCESS  read-only
        STATUS      current
        DESCRIPTION
            "This object records the average network re-entry time
             Avg(N)."
        ::= { wmanIf2BsNetworkEntryStatisticsEntry 3 }   

wmanIf2BsMaxNetworkReEntryTime OBJECT-TYPE
        SYNTAX      INTEGER
        UNITS       "second"        
        MAX-ACCESS  read-only
        STATUS      current
        DESCRIPTION
            "This object records the maximum network re-entry time
             Max(N)."
        ::= { wmanIf2BsNetworkEntryStatisticsEntry 4 }
        
wmanIf2BsNumOfNetworkEntries OBJECT-TYPE
        SYNTAX      Counter64        
        MAX-ACCESS  read-only
        STATUS      current
        DESCRIPTION
            "This object tracks the number of network entries 'N'."
        ::= { wmanIf2BsNetworkEntryStatisticsEntry 5 }
        
wmanIf2BsNumOfNetworkReEntries OBJECT-TYPE
        SYNTAX      Counter64        
        MAX-ACCESS  read-only
        STATUS      current
        DESCRIPTION
            "This object tracks the number of network re-entries 'N'."
        ::= { wmanIf2BsNetworkEntryStatisticsEntry 6 }

-- 
-- Mobile Packet Error Rate Table
--         
wmanIf2BsPacketErrorRateTable OBJECT-TYPE
        SYNTAX      SEQUENCE OF WmanIf2BsPacketErrorRateEntry
        MAX-ACCESS  not-accessible
        STATUS      current
        DESCRIPTION
            "This table contains the packet error rate information.
            BS should reset all counters after they have been reported
            to EMS via wmanIf2BsPerformanceCountersTrap"
        ::= { wmanIf2BsPm 6 }

wmanIf2BsPacketErrorRateEntry OBJECT-TYPE
        SYNTAX      WmanIf2BsPacketErrorRateEntry
        MAX-ACCESS  not-accessible
        STATUS      current
        DESCRIPTION
            "This table provides one row for each BS sector."
        INDEX     { ifIndex }
        ::= { wmanIf2BsPacketErrorRateTable  1 }

WmanIf2BsPacketErrorRateEntry ::= SEQUENCE {
        wmanIf2BsDlPacketsSend                  Counter64, 
        wmanIf2BsDlPacketsErrored               Counter64,
        wmanIf2BsDlPacketErrorRate              Unsigned32}

wmanIf2BsDlPacketsSend OBJECT-TYPE
        SYNTAX      Counter64 
        MAX-ACCESS  read-only
        STATUS      current
        DESCRIPTION
            "This object counts the total number of MAC SDUs that a BS
             has sent."
        ::= { wmanIf2BsPacketErrorRateEntry 1 }
        
wmanIf2BsDlPacketsErrored OBJECT-TYPE
        SYNTAX      Counter64 
        MAX-ACCESS  read-only
        STATUS      current
        DESCRIPTION
            "This object counts the total number of MAC SDUs including
             at least an ARQ block that has not been successful
             acknowledged (i.e. timeout or NAK)."
        ::= { wmanIf2BsPacketErrorRateEntry 2 }

wmanIf2BsDlPacketErrorRate OBJECT-TYPE
        SYNTAX      Unsigned32
        UNITS       "1x10E-7"  
        MAX-ACCESS  read-only
        STATUS      current
        DESCRIPTION
            "wmanIf2BsDlPacketErrorRate = (wmanIf2BsDlPacketsErrored /
             wmanIf2BsDlPacketsSend) * 10000000"
        ::= { wmanIf2BsPacketErrorRateEntry 3 }

-- 
-- Mobile Station handover matrics Table
--         
wmanIf2BsSsHandoverMetricsTable OBJECT-TYPE
        SYNTAX      SEQUENCE OF WmanIf2BsSsHandoverMetricsEntry
        MAX-ACCESS  not-accessible
        STATUS      current
        DESCRIPTION
            "This table contains metrics information that can be
             used to characterize SS' performance during the handover.
             BS should reset all counters after they have been reported
             to EMS via wmanIf2BsPerformanceCountersTrap."
        ::= { wmanIf2BsPm 7 }

wmanIf2BsSsHandoverMetricsEntry OBJECT-TYPE
        SYNTAX      WmanIf2BsSsHandoverMetricsEntry
        MAX-ACCESS  not-accessible
        STATUS      current
        DESCRIPTION
            "This table provides one row for each BS sector."
        INDEX     { ifIndex }
        ::= { wmanIf2BsSsHandoverMetricsTable  1 }

WmanIf2BsSsHandoverMetricsEntry ::= SEQUENCE {
        wmanIf2BsSsHandoverAttempt              Counter64, 
        wmanIf2BsSsHandoverSuccess              Counter64,
        wmanIf2BsSsHandoverSuccessRate          INTEGER,
        wmanIf2BsSsHandoverCancel               Counter64, 
        wmanIf2BsSsHandoverReject               Counter64,
        wmanIf2BsSsHandoverCancelRate           INTEGER,
        wmanIf2BsSsHandoverRejectRate           INTEGER,
        wmanIf2BsSsAvgHandoverTime              INTEGER,
        wmanIf2BsSsUnexpectedHandover           Counter64}

wmanIf2BsSsHandoverAttempt OBJECT-TYPE
        SYNTAX      Counter64 
        MAX-ACCESS  read-only
        STATUS      current
        DESCRIPTION
            "This object counts the number of SS initiated handover
             attempts. The serving BS increments the counter by one each
             time the BS receives MOB_MSHO-REQ from SS."
        ::= { wmanIf2BsSsHandoverMetricsEntry 1 }
        
wmanIf2BsSsHandoverSuccess OBJECT-TYPE
        SYNTAX      Counter64 
        MAX-ACCESS  read-only
        STATUS      current
        DESCRIPTION
            "This object counts the number of successful SS initiated
             handover. The serving BS increments the counter by one each
             time the BS sends MOB_BSHO-RSP to SS."
        ::= { wmanIf2BsSsHandoverMetricsEntry 2 }

wmanIf2BsSsHandoverSuccessRate OBJECT-TYPE
        SYNTAX      INTEGER 
        MAX-ACCESS  read-only
        STATUS      current
        DESCRIPTION
            "wmanIf2BsSsHandoverSuccessRate % =
             wmanIf2BsSsHandoverSuccess / wmanIf2BsSsHandoverAttempt
             * 100"
        ::= { wmanIf2BsSsHandoverMetricsEntry 3 }
        
wmanIf2BsSsHandoverCancel OBJECT-TYPE
        SYNTAX      Counter64
        MAX-ACCESS  read-only
        STATUS      current
        DESCRIPTION
            "This object counts the number of SS initiated handover
             cancellation. The BS serving increments the counter by one
             each time the BS receives MOB_HO-IND with
                 HO_IND_type = 'HO cancel'"
        ::= { wmanIf2BsSsHandoverMetricsEntry 4 }

wmanIf2BsSsHandoverReject OBJECT-TYPE
        SYNTAX      Counter64
        MAX-ACCESS  read-only
        STATUS      current
        DESCRIPTION
            "This object counts the number of SS initiated handover
             rejected by SS. The serving BS increments the counter by
             one each time the BS receives MOB_HO-IND with
                 HO_IND_type = 'HO reject'"
        ::= { wmanIf2BsSsHandoverMetricsEntry 5 }

wmanIf2BsSsHandoverCancelRate OBJECT-TYPE
        SYNTAX      INTEGER 
        MAX-ACCESS  read-only
        STATUS      current
        DESCRIPTION
            "wmanIf2BsSsHandoverCancelRate % =
             wmanIf2BsSsHandoverCancel / wmanIf2BsSsHandoverAttempt
             * 100"
        ::= { wmanIf2BsSsHandoverMetricsEntry 6 }

wmanIf2BsSsHandoverRejectRate OBJECT-TYPE
        SYNTAX      INTEGER 
        MAX-ACCESS  read-only
        STATUS      current
        DESCRIPTION
            "wmanIf2BsSsHandoverRejectRate % =
             wmanIf2BsSsHandoverReject  / wmanIf2BsSsHandoverAttempt
             * 100"
        ::= { wmanIf2BsSsHandoverMetricsEntry 7 }

wmanIf2BsSsAvgHandoverTime OBJECT-TYPE
        SYNTAX      INTEGER
        UNITS       "millisecond"        
        MAX-ACCESS  read-only
        STATUS      current
        DESCRIPTION
            "This object records the average handover time Avg(N)
             measured at target BS. The BS measures the number of
             handovers occured withing each interval set by the
             wmanIf2BsDataSampleInterval object. The formula of the
             measurement is shown below:      
                                        
             T = Handover time is the amount of time between:
                 1. Target BS receives the backbone handover indication
                    message from the serving BS for a give SS 
                 2. The given SS completes the ranging successfully by
                    receiving RNG-RSP from the target BS 
                                   
             N = the number of handover in a reporting interval

             Avg(N) = the average amount of time after N handovers
             Avg(0) = T, the 1st handover
             Avg(N) = (Avg(N-1)*(N-1) + T) / N"
        ::= { wmanIf2BsSsHandoverMetricsEntry 8 }

wmanIf2BsSsUnexpectedHandover OBJECT-TYPE
        SYNTAX      Counter64 
        MAX-ACCESS  read-only
        STATUS      current
        DESCRIPTION
            "This object counts the number of unexpected SS initiated
             handover attempts. The target BS increments the counter by
             one each time the target BS receives RNG-REQ from a SS
             initiated handover without backbone handover indication
             message from the serving BS."
        ::= { wmanIf2BsSsHandoverMetricsEntry 9 }       

-- 
-- Mobile Station user metrics Table
--         
wmanIf2BsSsUserMetricsTable OBJECT-TYPE
        SYNTAX      SEQUENCE OF WmanIf2BsSsUserMetricsEntry
        MAX-ACCESS  not-accessible
        STATUS      current
        DESCRIPTION
            "This table contains counter objects to track user metrics.
             BS should reset all counters after they have been reported
             to EMS via wmanIf2BsPerformanceCountersTrap."
        ::= { wmanIf2BsPm 8 }

wmanIf2BsSsUserMetricsEntry OBJECT-TYPE
        SYNTAX      WmanIf2BsSsUserMetricsEntry
        MAX-ACCESS  not-accessible
        STATUS      current
        DESCRIPTION
            "This table provides one row for each BS sector."
        INDEX     { ifIndex }
        ::= { wmanIf2BsSsUserMetricsTable  1 }

WmanIf2BsSsUserMetricsEntry ::= SEQUENCE {
        wmanIf2BsSsActiveUsers                  Counter64, 
        wmanIf2BsSsPeakNormalModeUsers          Counter64,
        wmanIf2BsSsPeakSleepModeUsers           Counter64,
        wmanIf2BsSsPeakIdleModeUsers            Counter64,
        wmanIf2BsSsAvgNormalModeUsers           INTEGER}

wmanIf2BsSsActiveUsers OBJECT-TYPE
        SYNTAX      Counter64 
        MAX-ACCESS  read-only
        STATUS      current
        DESCRIPTION
            "This object captures the number of active users over a
             reporting period by counting the number of SS's that have
             active CIDs."
        ::= { wmanIf2BsSsUserMetricsEntry 1 }
        
wmanIf2BsSsPeakNormalModeUsers OBJECT-TYPE
        SYNTAX      Counter64 
        MAX-ACCESS  read-only
        STATUS      current
        DESCRIPTION
            "This object counts the number of peak normal mode users.
             The serving BS increments the counter by one each time the
             BS receives REG-REQ from a SS and returns REG-RSP."
        ::= { wmanIf2BsSsUserMetricsEntry 2 }

wmanIf2BsSsPeakSleepModeUsers OBJECT-TYPE
        SYNTAX      Counter64 
        MAX-ACCESS  read-only
        STATUS      current
        DESCRIPTION
            "This object counts the number of peak sleep mode users.
             The serving BS increments the counter by one each time the
             BS successfully puts a SS into sleep mod by doing the
             following.
             1. BS receives MOB_SLP-REQ from a SS and returns
                MOB_SLP-RSP.
             2. BS send MOB_SLP-RSP to a SS autonomously."
        ::= { wmanIf2BsSsUserMetricsEntry 3 }
        
wmanIf2BsSsPeakIdleModeUsers OBJECT-TYPE
        SYNTAX      Counter64 
        MAX-ACCESS  read-only
        STATUS      current
        DESCRIPTION
            "This object counts the number of peak idle mode users.
             The serving BS increments the counter by one each time the
             BS successfully puts a SS into the idle mode by doing the
             following.
             1. SS sends DREG-REQ with a De-Registration_Request_Code =
                0x01; BS returns DREG-CMD message to the SS.
             2. BS sends a DREG-CMD with an Action Code = 0x05 in
                unsolicited manner; SS returns the DREG-REQ message with
                De-Registration_Request_Code = 0x02"
        ::= { wmanIf2BsSsUserMetricsEntry 4 }

wmanIf2BsSsAvgNormalModeUsers OBJECT-TYPE
        SYNTAX      INTEGER        
        MAX-ACCESS  read-only
        STATUS      current
        DESCRIPTION
            "This object records the average normal mode users Avg(N)
             measured at BS. The BS measures the number of normal mode
             users recorded within each interval set by the
             wmanIf2BsDataSampleInterval object. The formula of the
             measurement is shown below:      
                                        
             T = the number of normal mode users recorded in each sample
                 interval  
                                   
             N = the number of samples in a reporting interval

             Avg(N) = the average of normal mode users
             Avg(0) = T, the 1st sample
             Avg(N) = (Avg(N-1)*(N-1) + T) / N"
        ::= { wmanIf2BsSsUserMetricsEntry 5 }

-- 
-- Mobile Station connection ID metrics Table
--         
wmanIf2BsSsCidmetricsTable OBJECT-TYPE
        SYNTAX      SEQUENCE OF WmanIf2BsSsCidmetricsEntry
        MAX-ACCESS  not-accessible
        STATUS      current
        DESCRIPTION
            "This table tracks the number of basic and primary CIDs, and
             the average and maximum number of user CIDs.
             
             For example:
             T = the number of user CIDs measured in a sample interval
                                                 
             N = the number of samples in a reporting interval 

             Avg(N) = the average anumber of user CIDs
             Avg(0) = T, the 1st sample
             Avg(N) = (Avg(N-1)*(N-1) + T) / N

             Max(N) = the maximum number of user CIDs
             Max(0) = T, the 1st sample
             Max(N) = T if T > Max(N-1)
                     = Max(N-1) if T <= Max(N-1)
                     
             BS should reset all counters after they have been reported
             to EMS via wmanIf2BsPerformanceCountersTrap."
        ::= { wmanIf2BsPm 9 }

wmanIf2BsSsCidmetricsEntry OBJECT-TYPE
        SYNTAX      WmanIf2BsSsCidmetricsEntry
        MAX-ACCESS  not-accessible
        STATUS      current
        DESCRIPTION
            "This table provides one row for each BS sector."
        INDEX     { ifIndex }
        ::= { wmanIf2BsSsCidmetricsTable  1 }

WmanIf2BsSsCidmetricsEntry ::= SEQUENCE {
        wmanIf2BsSsBasicAndPrimaryCids          Counter64, 
        wmanIf2BsSsMaximumUserCids              Counter64,
        wmanIf2BsSsAvgUserCids                  Counter64}

wmanIf2BsSsBasicAndPrimaryCids OBJECT-TYPE
        SYNTAX      Counter64 
        MAX-ACCESS  read-only
        STATUS      current
        DESCRIPTION
            "This object captures the number of basic and primary CIDs
             in a reporting period."
        ::= { wmanIf2BsSsCidmetricsEntry 1 }
        
wmanIf2BsSsMaximumUserCids OBJECT-TYPE
        SYNTAX      Counter64 
        MAX-ACCESS  read-only
        STATUS      current
        DESCRIPTION
            "This object records the maximum anumber of user CIDs Avg(N)
             , measured in a reporting interval"
        ::= { wmanIf2BsSsCidmetricsEntry 2 }

wmanIf2BsSsAvgUserCids OBJECT-TYPE
        SYNTAX      Counter64        
        MAX-ACCESS  read-only
        STATUS      current
        DESCRIPTION
            "This object records the average number of user CIDs Avg(N)
             , measured in a reporting interval"
        ::= { wmanIf2BsSsCidmetricsEntry 3 }
                                        
--
-- wmanIf2BsSm group – containing tables and objects related to Security
--                     Management (i.e. Privacy Sublayer objects)
--

wmanIf2BsPkmSecurityCapabilityTable OBJECT-TYPE
        SYNTAX      SEQUENCE OF WmanIf2BsPkmSecurityCapabilityEntry
        MAX-ACCESS  not-accessible
        STATUS      current
        DESCRIPTION
            "This table contains the list of the cryptographic
             suite(s) an BS supports."
        REFERENCE
            "Subclause 11.9.13 in IEEE Std 802.16-2004"
        ::= { wmanIf2BsSm 1 }

wmanIf2BsPkmSecurityCapabilityEntry OBJECT-TYPE
        SYNTAX      WmanIf2BsPkmSecurityCapabilityEntry
        MAX-ACCESS  not-accessible
        STATUS      current
        DESCRIPTION
            ""
        INDEX     { ifIndex,
                    wmanIf2BsPkmSecurityCapIndex }
        ::= { wmanIf2BsPkmSecurityCapabilityTable  1 }

WmanIf2BsPkmSecurityCapabilityEntry ::= SEQUENCE {
        wmanIf2BsPkmSecurityCapIndex            INTEGER,
        wmanIf2BsPkmScDataEncryptAlgorithm      WmanIf2DataEncryptAlgId,
        wmanIf2BsPkmScDataAuthentAlgorithm      WmanIf2DataAuthAlgId,
        wmanIf2BsPkmScEncryptAlgorithm          WmanIf2TekEncryptAlgId}
        
wmanIf2BsPkmSecurityCapIndex OBJECT-TYPE
        SYNTAX      INTEGER (1 .. 65535)
        MAX-ACCESS  not-accessible
        STATUS      current
        DESCRIPTION
            "The index value which uniquely identifies an entry
             in the wmanIf2BsPkmSecurityCapabilityTable"
        ::= { wmanIf2BsPkmSecurityCapabilityEntry 1 }
        
wmanIf2BsPkmScDataEncryptAlgorithm OBJECT-TYPE
        SYNTAX      WmanIf2DataEncryptAlgId
        MAX-ACCESS  read-only
        STATUS      current
        DESCRIPTION
            "The value of this object is the data encryption algorithm
             being utilized."
        REFERENCE
             "Table 562"
        ::= { wmanIf2BsPkmSecurityCapabilityEntry 2 }

wmanIf2BsPkmScDataAuthentAlgorithm OBJECT-TYPE
        SYNTAX      WmanIf2DataAuthAlgId
        MAX-ACCESS  read-only
        STATUS      current
        DESCRIPTION
            "The value of this object is the data authentication
             algorithm being utilized."
        REFERENCE
             "Table 563"
        ::= { wmanIf2BsPkmSecurityCapabilityEntry 3 }

wmanIf2BsPkmScEncryptAlgorithm OBJECT-TYPE
        SYNTAX      WmanIf2TekEncryptAlgId
        MAX-ACCESS  read-only
        STATUS      current
        DESCRIPTION
            "The value of this object is the TEK key encryption
             algorithm being utilized."
        REFERENCE
             "Table 564"
        ::= { wmanIf2BsPkmSecurityCapabilityEntry 4 }
                        
--
-- Table wmanIf2BsSsPkmSecurityCapabilityTable
--
wmanIf2BsSsPkmSecurityCapabilityTable OBJECT-TYPE
        SYNTAX      SEQUENCE OF WmanIf2BsSsPkmSecurityCapabilityEntry
        MAX-ACCESS  not-accessible
        STATUS      current
        DESCRIPTION
            "This table contains the SS's Security Capabilities that are
             conveyed by the Auth Request or PKMv2 SA-TEK-Request
             message. It contains the list of the cryptographic suite(s)
             an SS supports."
        REFERENCE
            "Subclause 11.9.13 in IEEE Std 802.16-2004 and
             Table 37i in IEEE Std 802.16e-2005"
        ::= { wmanIf2BsSm 2 }

wmanIf2BsSsPkmSecurityCapabilityEntry OBJECT-TYPE
        SYNTAX      WmanIf2BsSsPkmSecurityCapabilityEntry
        MAX-ACCESS  not-accessible
        STATUS      current
        DESCRIPTION
            ""
        INDEX     { ifIndex,
                    wmanIf2BsSsMacAddress,
                    wmanIf2BsSsPkmSecurityCapIndex }
        ::= { wmanIf2BsSsPkmSecurityCapabilityTable  1 }

WmanIf2BsSsPkmSecurityCapabilityEntry ::= SEQUENCE {
        wmanIf2BsSsPkmSecurityCapIndex          INTEGER,
        wmanIf2BsSsPkmScDataEncryptAlgorithm    WmanIf2DataEncryptAlgId,
        wmanIf2BsSsPkmScDataAuthentAlgorithm    WmanIf2DataAuthAlgId,
        wmanIf2BsSsPkmScEncryptAlgorithm        WmanIf2TekEncryptAlgId}
        
wmanIf2BsSsPkmSecurityCapIndex OBJECT-TYPE
        SYNTAX      INTEGER (1 .. 65535)
        MAX-ACCESS  not-accessible
        STATUS      current
        DESCRIPTION
            "The index value which uniquely identifies an entry
             in the wmanIf2BsSsPkmSecurityCapabilityTable"
        ::= { wmanIf2BsSsPkmSecurityCapabilityEntry 1 }
        
wmanIf2BsSsPkmScDataEncryptAlgorithm OBJECT-TYPE
        SYNTAX      WmanIf2DataEncryptAlgId
        MAX-ACCESS  read-only
        STATUS      current
        DESCRIPTION
            "The value of this object is the data encryption algorithm
             being utilized."
        REFERENCE
             "Table 375, IEEE Std 802.16-2004"
        ::= { wmanIf2BsSsPkmSecurityCapabilityEntry 2 }

wmanIf2BsSsPkmScDataAuthentAlgorithm OBJECT-TYPE
        SYNTAX      WmanIf2DataAuthAlgId
        MAX-ACCESS  read-only
        STATUS      current
        DESCRIPTION
            "The value of this object is the data authentication
             algorithm being utilized."
        REFERENCE
             "Table 376, IEEE Std 802.16-2004"
        ::= { wmanIf2BsSsPkmSecurityCapabilityEntry 3 }

wmanIf2BsSsPkmScEncryptAlgorithm OBJECT-TYPE
        SYNTAX      WmanIf2TekEncryptAlgId
        MAX-ACCESS  read-only
        STATUS      current
        DESCRIPTION
            "The value of this object is the TEK key encryption
             algorithm being utilized."
        REFERENCE
             "Table 377, IEEE Std 802.16-2004"
        ::= { wmanIf2BsSsPkmSecurityCapabilityEntry 4 }
        
wmanIf2BsPkmV1Objects OBJECT IDENTIFIER ::= { wmanIf2BsSm 3 }

--
-- Table wmanIf2BsPkmV1ConfigTable
--
wmanIf2BsPkmV1ConfigTable OBJECT-TYPE
        SYNTAX      SEQUENCE OF WmanIf2BsPkmV1ConfigEntry
        MAX-ACCESS  not-accessible
        STATUS      current
        DESCRIPTION
            "This table contains the configuration of the PKM
             attributes that are to be used for BS and SS."
        REFERENCE
            "Table 343 in IEEE Std 802.16-2004 and 802.16e-2005"
        ::= { wmanIf2BsPkmV1Objects  1 }

wmanIf2BsPkmV1ConfigEntry OBJECT-TYPE
        SYNTAX      WmanIf2BsPkmV1ConfigEntry
        MAX-ACCESS  not-accessible
        STATUS      current
        DESCRIPTION
            "Each entry contains objects that define the PKM attributes
             of each BS wireless interface, and all SSs that are
             connected with such BS."
        INDEX     { ifIndex }
        ::= { wmanIf2BsPkmV1ConfigTable  1 }

WmanIf2BsPkmV1ConfigEntry ::= SEQUENCE {
        wmanIf2BsPkmV1AkLifetime                Integer32,
        wmanIf2BsPkmV1TekLifetime               Integer32,
        wmanIf2BsPkmV1SelfSigManufCertTrust     INTEGER,
        wmanIf2BsPkmV1AuthWaitTimeout           Integer32,
        wmanIf2BsPkmV1ReauthWaitTimeout         Integer32,
        wmanIf2BsPkmV1AuthGraceTime             Integer32,
        wmanIf2BsPkmV1OpWaitTimeout             Integer32,
        wmanIf2BsPkmV1RekeyWaitTimeout          Integer32,
        wmanIf2BsPkmV1TekGraceTime              Integer32,
        wmanIf2BsPkmV1AuthRejectWaitTimeout     Integer32,
        wmanIf2BsPkmV1CheckCertValidityPeriods  TruthValue}

wmanIf2BsPkmV1AkLifetime OBJECT-TYPE
        SYNTAX      Integer32 (86400 .. 6048000)
        UNITS       "seconds"
        MAX-ACCESS  read-write
        STATUS      current
        DESCRIPTION
            "This object defines the lifetime of a newly assigned
             authorization key."
        REFERENCE
             "Table 343 in IEEE Std 802.16-2004"
        DEFVAL         { 604800 }
        ::= { wmanIf2BsPkmV1ConfigEntry 1 }
                                            
wmanIf2BsPkmV1TekLifetime OBJECT-TYPE
        SYNTAX      Integer32 (1800 .. 604800)
        UNITS       "seconds"
        MAX-ACCESS  read-write
        STATUS      current
        DESCRIPTION
            "This object defines the lifetime of a newly assigned
             Traffic Encryption Key(TEK)."
        REFERENCE
             "Table 343 in IEEE Std 802.16-2004"
        DEFVAL         { 43200 }
        ::= { wmanIf2BsPkmV1ConfigEntry 2 }

wmanIf2BsPkmV1SelfSigManufCertTrust OBJECT-TYPE
        SYNTAX      INTEGER {trusted (1),
                             untrusted (2)}
        MAX-ACCESS  read-write
        STATUS      current
        DESCRIPTION
            "This object determines the default trust of all (new)
             self-signed manufacturer certificates obtained after
             setting the object."
        ::= { wmanIf2BsPkmV1ConfigEntry 3 }

wmanIf2BsPkmV1AuthWaitTimeout OBJECT-TYPE
        SYNTAX      Integer32 (2 .. 30)
        UNITS       "seconds"
        MAX-ACCESS  read-write
        STATUS      current
        DESCRIPTION
            "This object defines the Auth Req retransmission interval
             from Auth Wait state."
        REFERENCE
            "Table 343 and subclause 11.9.19 in IEEE Std 802.16-2004"
        DEFVAL      { 10 }
        ::= { wmanIf2BsPkmV1ConfigEntry 4 }
        
wmanIf2BsPkmV1ReauthWaitTimeout OBJECT-TYPE
        SYNTAX      Integer32 (2 .. 30)
        UNITS       "seconds"
        MAX-ACCESS  read-write
        STATUS      current
        DESCRIPTION
            "This object defines the Auth Req retransmission interval
             from Reauth Wait state."
        REFERENCE
            "Table 343 and subclause 11.9.19 in IEEE Std 802.16-2004"
        DEFVAL      { 10 }
        ::= { wmanIf2BsPkmV1ConfigEntry 5 }
        
wmanIf2BsPkmV1AuthGraceTime OBJECT-TYPE
        SYNTAX      Integer32 (300 .. 3024000)
        UNITS       "seconds"
        MAX-ACCESS  read-write
        STATUS      current
        DESCRIPTION
            "The value of this object is the grace time for an
             authorization key. A SS is expected to start trying to get
             a new authorization key beginning AuthGraceTime seconds
             before the authorization key actually expires."
        REFERENCE
            "Table 343 and subclause 11.9.19 in IEEE Std 802.16-2004"
        DEFVAL      { 600 }
        ::= { wmanIf2BsPkmV1ConfigEntry 6 }

wmanIf2BsPkmV1OpWaitTimeout OBJECT-TYPE
        SYNTAX      Integer32 (1 .. 10)
        UNITS       "seconds"
        MAX-ACCESS  read-write
        STATUS      current
        DESCRIPTION
            "This object defines the Key Req retransmission interval
             from Op Wait state."
        REFERENCE
            "Table 343 and subclause 11.9.19 in IEEE Std 802.16-2004"
        DEFVAL      { 1 }
        ::= { wmanIf2BsPkmV1ConfigEntry 7 }
        
wmanIf2BsPkmV1RekeyWaitTimeout OBJECT-TYPE
        SYNTAX      Integer32 (1 .. 10)
        UNITS       "seconds"
        MAX-ACCESS  read-write
        STATUS      current
        DESCRIPTION
            "This object defines the Key Req retransmission interval
             from Rekey Wait state."
        REFERENCE
            "Table 343 and subclause 11.9.19 in IEEE Std 802.16-2004"
        DEFVAL      { 1 }
        ::= { wmanIf2BsPkmV1ConfigEntry 8 }
        
wmanIf2BsPkmV1TekGraceTime OBJECT-TYPE
        SYNTAX      Integer32 (300 .. 3024000)
        UNITS       "seconds"
        MAX-ACCESS  read-write
        STATUS      current
        DESCRIPTION
            "The value of this object is the grace time for the TEK in
             seconds. The SS is expected to start trying to acquire a
             new TEK beginning TEK GraceTime seconds before the
             expiration of the most recent TEK."
        REFERENCE
            "Table 343 and subclause 11.9.19 in IEEE Std 802.16-2004"
        DEFVAL      { 3600 }
        ::= { wmanIf2BsPkmV1ConfigEntry 9 }
        
wmanIf2BsPkmV1AuthRejectWaitTimeout OBJECT-TYPE
        SYNTAX      Integer32 (10 .. 600)
        UNITS       "seconds"
        MAX-ACCESS  read-write
        STATUS      current
        DESCRIPTION
            "This object defines the Delay before resending Auth Request
             after receiving Auth Reject."
        REFERENCE
            "Table 343 and subclause 11.9.19 in IEEE Std 802.16-2004"
        DEFVAL      { 60 }
        ::= { wmanIf2BsPkmV1ConfigEntry 10 }
        
wmanIf2BsPkmV1CheckCertValidityPeriods OBJECT-TYPE
        SYNTAX      TruthValue 
        MAX-ACCESS  read-write
        STATUS      current
        DESCRIPTION
            "Setting this object to TRUE causes all certificates
             received thereafter to have their validity periods (and
             their chain's validity periods) checked against the current
             time of day. A FALSE setting will cause all certificates
             received Thereafter to not have their validity periods
             (nor their chain's validity periods) checked against the
             current time of day."
        ::= { wmanIf2BsPkmV1ConfigEntry 11 }                        

--
-- Table wmanIf2BsSsPkmV1AuthorizationTable
--
wmanIf2BsSsPkmV1AuthorizationTable OBJECT-TYPE
        SYNTAX      SEQUENCE OF WmanIf2BsSsPkmV1AuthorizationEntry
        MAX-ACCESS  not-accessible
        STATUS      current
        DESCRIPTION
            "This table contains information related to SS's
             authorization process."
        REFERENCE
            "Table 28 and 37 in IEEE Std 802.16-2004"
        ::= { wmanIf2BsPkmV1Objects 2 }

wmanIf2BsSsPkmV1AuthorizationEntry OBJECT-TYPE
        SYNTAX      WmanIf2BsSsPkmV1AuthorizationEntry
        MAX-ACCESS  not-accessible
        STATUS      current
        DESCRIPTION
            "Each entry contains objects that define the SS
             authorization attributes for each SS associated with each
             BS sector."
        INDEX     { ifIndex, wmanIf2BsSsPkmV1AuthMacAddress }
        ::= { wmanIf2BsSsPkmV1AuthorizationTable  1 }

WmanIf2BsSsPkmV1AuthorizationEntry ::= SEQUENCE {
        wmanIf2BsSsPkmV1AuthMacAddress          MacAddress,
        wmanIf2BsSsPkmV1CaCertificate           OCTET STRING,
        wmanIf2BsSsPkmV1SsCertificate           OCTET STRING,
        wmanIf2BsSsPkmV1PrimarySaId             INTEGER,
        wmanIf2BsSsPkmV1AuthKeySequenceNumber   Integer32,
        wmanIf2BsSsPkmV1AuthKeyLifetime         Integer32,
        wmanIf2BsSsPkmV1AuthRejectError         WmanIf2PkmErrorCode,
        wmanIf2BsSsPkmV1AuthInvalidError        WmanIf2PkmErrorCode,
        wmanIf2BsSsPkmV1AkN-1ExpireTime         DateAndTime,
        wmanIf2BsSsPkmV1AkNExpireTime           DateAndTime,
        wmanIf2BsSsPkmV1CertificateStatus       WmanIf2CertificateStat,
        wmanIf2BsSsPkmV1AuthReset               INTEGER}

wmanIf2BsSsPkmV1AuthMacAddress OBJECT-TYPE
        SYNTAX      MacAddress 
        MAX-ACCESS  not-accessible
        STATUS      current
        DESCRIPTION
            "The value of this object is the physical address of the SS
             to which the authorization association applies."
        ::= { wmanIf2BsSsPkmV1AuthorizationEntry 1 }

wmanIf2BsSsPkmV1CaCertificate OBJECT-TYPE
        SYNTAX      OCTET STRING (SIZE(0..65535))  
        MAX-ACCESS  read-only
        STATUS      current
        DESCRIPTION
            "SS sends the CA-Certificate in the Auth Info message. It
             contains an X.509 CA certificate for the manufacturer of
             the SS. The SS's X.509 user certificate shall have been
             issued by the CA identified by the X.509 CA certificate."
        REFERENCE
            "Table 37 in IEEE Std 802.16-2004"
        ::= { wmanIf2BsSsPkmV1AuthorizationEntry 2 }

wmanIf2BsSsPkmV1SsCertificate OBJECT-TYPE
        SYNTAX      OCTET STRING (SIZE(0..65535)) 
        MAX-ACCESS  read-only
        STATUS      current
        DESCRIPTION
            "SS sends the SS-Certificate in the Auth Request message.
             It contains an X.509 SS certificate issued by the SS's
             manufacturer. The SS's X.509 certificate is a public-key
             certificate which binds the SS's identifying information
             to its RSA public key in a verifiable manner. The X.509
             certificate is digitally signed by the SS's manufacturer,
             and that signature can be verified by a BS that knows
             the manufacturer's public key. The manufacturer's public
             key is placed in an X.509 certification authority (CA)
             certificate, which in turn is signed by a higher level CA."
        REFERENCE
            "Table 28 in IEEE Std 802.16-2004"
        ::= { wmanIf2BsSsPkmV1AuthorizationEntry 3 }

wmanIf2BsSsPkmV1PrimarySaId OBJECT-TYPE
        SYNTAX      INTEGER (0..65535) 
        MAX-ACCESS  read-only
        STATUS      current
        DESCRIPTION
            "SS's primary SAID equal to the Basic CID."
        REFERENCE
             "Subclause 6.3.2.3.9.2 in IEEE Std 802.16-2004"
        ::= { wmanIf2BsSsPkmV1AuthorizationEntry 4 }

wmanIf2BsSsPkmV1AuthKeySequenceNumber OBJECT-TYPE
        SYNTAX      Integer32 (0 .. 15)
        MAX-ACCESS  read-only
        STATUS      current
        DESCRIPTION
            "This object provides the most recent authorization key
             sequence number in the Auth Reply message for an SS."
        REFERENCE
             "Table 29 in IEEE Std 802.16-2004"
        ::= { wmanIf2BsSsPkmV1AuthorizationEntry 5 }
        
wmanIf2BsSsPkmV1AuthKeyLifetime OBJECT-TYPE
        SYNTAX      Integer32 (86400..6048000)
        UNITS       "seconds"
        MAX-ACCESS  read-only
        STATUS      current
        DESCRIPTION
            "This object defines the lifetime of an authorization
             key (AK) the BS assigns to a SS."
        REFERENCE
             "Table 343 in IEEE Std 802.16-2004"
        ::= { wmanIf2BsSsPkmV1AuthorizationEntry 6 }

wmanIf2BsSsPkmV1AuthRejectError OBJECT-TYPE
        SYNTAX      WmanIf2PkmErrorCode
        MAX-ACCESS  read-only
        STATUS      current
        DESCRIPTION
            "The Error Code in most recent Authorization Reject message
             transmitted to the SS.
             
             The valid codes are:
               0 - no failure
               1 - unauthorized SS
               2 - unauthorized SAID
               6..11 - permanent authorization failure"
        REFERENCE
             "Table 560 Subclause 11.9.10"
        ::= { wmanIf2BsSsPkmV1AuthorizationEntry 7 }

wmanIf2BsSsPkmV1AuthInvalidError OBJECT-TYPE
        SYNTAX      WmanIf2PkmErrorCode
        MAX-ACCESS  read-only
        STATUS      current
        DESCRIPTION 
            "The Error Code in most recent Authorization Invalid message
             transmitted to the SS.
             
             The valid codes are:
               0 - no failure
               1 - unauthorized SS
               3 - unsolicited
               4 - invalid key sequence
               5 - key request authentication failure"

        REFERENCE
             "Table 560 Subclause 11.9.10"
        ::= { wmanIf2BsSsPkmV1AuthorizationEntry 8 }

wmanIf2BsSsPkmV1AkN-1ExpireTime OBJECT-TYPE
        SYNTAX      DateAndTime
        MAX-ACCESS  read-only
        STATUS      current
        DESCRIPTION
            "This object is the time when AK(N-1) expires.
             wmanIf2BsSsPkmV1AkN-1ExpireTime =
                Auth Reply[AK(N-1)] arrival time +  AK(N-1) lifetime

             If this FSM has only one authorization key, then
             wmanIf2BsSsPkmV1AkN-1ExpireTime = the activation of FSM."
        ::= { wmanIf2BsSsPkmV1AuthorizationEntry 9 }

wmanIf2BsSsPkmV1AkNExpireTime OBJECT-TYPE
        SYNTAX      DateAndTime
        MAX-ACCESS  read-only
        STATUS      current
        DESCRIPTION
            "This object is the time when AK(N) expires.
             wmanIf2BsSsPkmV1AkNExpireTime =
             Auth Reply[AK(N)] arrival time +  AK(N) lifetime

             If this FSM has only one authorization key, then
             wmanIf2BsSsPkmV1AkNExpireTime = the activation of FSM."
        ::= { wmanIf2BsSsPkmV1AuthorizationEntry 10 }
        
wmanIf2BsSsPkmV1CertificateStatus OBJECT-TYPE
        SYNTAX      WmanIf2CertificateStat
        MAX-ACCESS  read-only
        STATUS      current
        DESCRIPTION
            "Indicate the reason why a SS's certificate is deemed valid
             or invalid."
        ::= { wmanIf2BsSsPkmV1AuthorizationEntry 11 }

wmanIf2BsSsPkmV1AuthReset OBJECT-TYPE
        SYNTAX      INTEGER {noResetRequested(1),
                             invalidateAuth(2),
                             sendAuthInvalid(3),
                             invalidateTeks(4)}
        MAX-ACCESS  read-write
        STATUS      current
        DESCRIPTION
            "Setting this object to:
               1 - no reset
               2 - causes the BS to invalidate the current SS
                   authorization key(s), but not to transmit an
                   Authorization Invalid message nor to invalidate 
                   unicast TEKs.
               3 - causes the BS to invalidate the current SS
                   authorization key(s), and to transmit an
                   Authorization Invalid message to the SS, but not
                   to invalidate unicast TEKs.
               4 - causes the BS to invalidate the current SS
                   authorization key(s), to transmit an Authorization
                   Invalid message to the SS, and to invalidate all
                   unicast TEKs associated with this SS authorization.
             Reading this object returns the most-recently-set value
             of this object, or returns noResetRequested(1) if the
             object has not been set since the last BS reboot."
        ::= { wmanIf2BsSsPkmV1AuthorizationEntry 12 }

--
-- Table wmanIf2BsSsPkmV1TekTable
--
wmanIf2BsSsPkmV1TekTable OBJECT-TYPE
        SYNTAX      SEQUENCE OF WmanIf2BsSsPkmV1TekEntry
        MAX-ACCESS  not-accessible
        STATUS      current
        DESCRIPTION
            "This table contains the TEK attributes that are associated
             with each SAID."
        ::= { wmanIf2BsPkmV1Objects 3 }

wmanIf2BsSsPkmV1TekEntry OBJECT-TYPE
        SYNTAX      WmanIf2BsSsPkmV1TekEntry
        MAX-ACCESS  not-accessible
        STATUS      current
        DESCRIPTION
            ""
        INDEX     { ifIndex,
                    wmanIf2BsSsMacAddress,
                    wmanIf2BsSsPkmV1SaidIndex }
        ::= { wmanIf2BsSsPkmV1TekTable  1 }

WmanIf2BsSsPkmV1TekEntry ::= SEQUENCE {
        wmanIf2BsSsPkmV1SaidIndex               INTEGER,
        wmanIf2BsSsPkmV1SaType                  WmanIf2SaType,
        wmanIf2BsSsPkmV1TekDataEncryptAlgorithm WmanIf2DataEncryptAlgId,
        wmanIf2BsSsPkmV1TekDataAuthentAlgorithm WmanIf2DataAuthAlgId,
        wmanIf2BsSsPkmV1TekEncryptAlgorithm     WmanIf2TekEncryptAlgId,
        wmanIf2BsSsPkmV1TekN-1SequenceNumber    Integer32,
        wmanIf2BsSsPkmV1TekN-1Lifetime          Integer32,
        wmanIf2BsSsPkmV1TekNSequenceNumber      Integer32,
        wmanIf2BsSsPkmV1TekNLifetime            Integer32,
        wmanIf2BsSsPkmV1KeyRejectError          WmanIf2PkmErrorCode,
        wmanIf2BsSsPkmV1TekInvalidError         WmanIf2PkmErrorCode,
        wmanIf2BsSsPkmV1TekN-1ExpireTime        DateAndTime,
        wmanIf2BsSsPkmV1TekNExpireTime          DateAndTime,
        wmanIf2BsSsPkmV1TekReset                TruthValue}
        
wmanIf2BsSsPkmV1SaidIndex OBJECT-TYPE
        SYNTAX      INTEGER (0 .. 65535)
        MAX-ACCESS  not-accessible
        STATUS      current
        DESCRIPTION
            "SAID index to the wmanIf2BsSsPkmV1TekTable."
        ::= { wmanIf2BsSsPkmV1TekEntry 1 }

wmanIf2BsSsPkmV1SaType OBJECT-TYPE
        SYNTAX      WmanIf2SaType
        MAX-ACCESS  read-only
        STATUS      current
        DESCRIPTION
            "SA Type attribute that is included in the Auth Reply 
             message."
        ::= { wmanIf2BsSsPkmV1TekEntry 2 }
        
wmanIf2BsSsPkmV1TekDataEncryptAlgorithm OBJECT-TYPE
        SYNTAX      WmanIf2DataEncryptAlgId
        MAX-ACCESS  read-only
        STATUS      current
        DESCRIPTION
            "The data encryption algorithm attribute that is included
             in the Auth Reply message."
        REFERENCE
             "Table 375, IEEE Std 802.16-2004"
        ::= { wmanIf2BsSsPkmV1TekEntry 3 }

wmanIf2BsSsPkmV1TekDataAuthentAlgorithm OBJECT-TYPE
        SYNTAX      WmanIf2DataAuthAlgId
        MAX-ACCESS  read-only
        STATUS      current
        DESCRIPTION
            "The data authentication algorithm attribute that is
             included in the Auth Reply message."
        REFERENCE
             "Table 376, IEEE Std 802.16-2004"
        ::= { wmanIf2BsSsPkmV1TekEntry 4 }

wmanIf2BsSsPkmV1TekEncryptAlgorithm OBJECT-TYPE
        SYNTAX      WmanIf2TekEncryptAlgId
        MAX-ACCESS  read-only
        STATUS      current
        DESCRIPTION
            "The TEK key encryption algorithm attribute that is
             included in the Auth Reply message."
        REFERENCE
             "Table 377, IEEE Std 802.16-2004"
        ::= { wmanIf2BsSsPkmV1TekEntry 5 }

wmanIf2BsSsPkmV1TekN-1SequenceNumber OBJECT-TYPE
        SYNTAX      Integer32 (0 .. 3)
        MAX-ACCESS  read-only
        STATUS      current
        DESCRIPTION
            "At all times the BS maintains two sets of active
             generations of keying material per SAID. One set
             corresponds to the 'N-1' generation of keying material,
             the second set corresponds to the 'N' generation of
             keying material. The N generation has a key sequence
             number one greater than (modulo 4) that of the N-1
             generation. This object provides the older TEK sequence
             number in the Key Reply message for an SS."
        REFERENCE
             "Subclause 11.9.8 in IEEE Std 802.16-2004"
        ::= { wmanIf2BsSsPkmV1TekEntry 6 }

wmanIf2BsSsPkmV1TekN-1Lifetime OBJECT-TYPE
        SYNTAX      Integer32 (1800 .. 604800)
        UNITS       "seconds"
        MAX-ACCESS  read-only
        STATUS      current
        DESCRIPTION
            "This object provides the N-1 TEK Remaining Lifetime."
        REFERENCE
            "Subclause 11.9.8 in IEEE Std 802.16-2004"
        ::= { wmanIf2BsSsPkmV1TekEntry 7 }

wmanIf2BsSsPkmV1TekNSequenceNumber OBJECT-TYPE
        SYNTAX      Integer32 (0 .. 3)
        MAX-ACCESS  read-only
        STATUS      current
        DESCRIPTION
            "This object provides the N TEK sequence number in the
             Key Reply message for an SS."
        REFERENCE
             "Subclause 11.9.8 in IEEE Std 802.16-2004"
        ::= { wmanIf2BsSsPkmV1TekEntry 8 }

wmanIf2BsSsPkmV1TekNLifetime OBJECT-TYPE
        SYNTAX      Integer32 (1800 .. 604800)
        UNITS       "seconds"
        MAX-ACCESS  read-only
        STATUS      current
        DESCRIPTION
            "This object provides the N TEK Remaining Lifetime."
        REFERENCE
            "Subclause 11.9.8 in IEEE Std 802.16-2004"
        ::= { wmanIf2BsSsPkmV1TekEntry 9 }
                
wmanIf2BsSsPkmV1KeyRejectError OBJECT-TYPE
        SYNTAX      WmanIf2PkmErrorCode
        MAX-ACCESS  read-only
        STATUS      current
        DESCRIPTION
            "The Error Code in the most recent Key Reject message sent
             in response to a Key Request for this SAID.
             
             The valid error codes are:
               0 - no failure
               2 - unauthorized SAID"
        REFERENCE
             "Table 373; IEEE Std 802.16-2004"
        ::= { wmanIf2BsSsPkmV1TekEntry 10 }

wmanIf2BsSsPkmV1TekInvalidError OBJECT-TYPE
        SYNTAX      WmanIf2PkmErrorCode
        MAX-ACCESS  read-only
        STATUS      current
        DESCRIPTION 
            "The Error Code in the most recent TEK Invalid message sent
             in association with this SAID.
             
             The valid error codes are:
               0 - no failure
               4 - invalid key sequence"
        REFERENCE
             "Table 373; IEEE Std 802.16-2004"
        ::= { wmanIf2BsSsPkmV1TekEntry 11 }

wmanIf2BsSsPkmV1TekN-1ExpireTime OBJECT-TYPE
        SYNTAX      DateAndTime
        MAX-ACCESS  read-only
        STATUS      current
        DESCRIPTION
            "This object is the time when TEK(N-1) expires.
             wmanIf2BsSsPkmV1TekN-1ExpireTime =
                 Key Reply[TEK(N-1)] arrival time +  TEK(N-1) lifetime

             If this FSM has only one authorization key, then
             wmanIf2BsSsPkmV1TekN-1ExpireTime = the activation of FSM."
        ::= { wmanIf2BsSsPkmV1TekEntry 12 }

wmanIf2BsSsPkmV1TekNExpireTime OBJECT-TYPE
        SYNTAX      DateAndTime
        MAX-ACCESS  read-only
        STATUS      current
        DESCRIPTION
            "This object is the time when TEK(N) expires.
             wmanIf2BsSsPkmV1TekNExpireTime =
                 Key Reply[TEK(N)] arrival time +  TEK(N) lifetime

             If this FSM has only one authorization key, then
             wmanIf2BsSsPkmV1TekNExpireTime = the activation of FSM."
        ::= { wmanIf2BsSsPkmV1TekEntry 13 }
        
wmanIf2BsSsPkmV1TekReset OBJECT-TYPE
        SYNTAX      TruthValue 
        MAX-ACCESS  read-write
        STATUS      current
        DESCRIPTION
            "Setting this object to TRUE causes the BS to invalidate
             the current active TEK(s) (plural due to key transition
             periods), and to generate a new TEK for the associated
             SAID; the BS MAY also generate an unsolicited TEK Invalid
             message, to optimize the TEK synchronization between the BS
             and the SS. Reading this object always returns FALSE."
        ::= { wmanIf2BsSsPkmV1TekEntry 14 }

wmanIf2BsPkmV2Objects OBJECT IDENTIFIER ::= { wmanIf2BsSm 4 }        

--
-- Table wmanIf2BsPkmV2ConfigTable
--
wmanIf2BsPkmV2ConfigTable OBJECT-TYPE
        SYNTAX      SEQUENCE OF WmanIf2BsPkmV2ConfigEntry
        MAX-ACCESS  not-accessible
        STATUS      current
        DESCRIPTION
            "This table contains the configuration of the PKM
             attributes that are needed to PKM operation."
        REFERENCE
            "Table 343 in IEEE Std 802.16-2004 and 802.16e-2005"
        ::= { wmanIf2BsPkmV2Objects  1 }

wmanIf2BsPkmV2ConfigEntry OBJECT-TYPE
        SYNTAX      WmanIf2BsPkmV2ConfigEntry
        MAX-ACCESS  not-accessible
        STATUS      current
        DESCRIPTION
            "Each entry contains objects that define the PKM attributes
             of each BS."
        INDEX     { ifIndex }
        ::= { wmanIf2BsPkmV2ConfigTable  1 }

WmanIf2BsPkmV2ConfigEntry ::= SEQUENCE {
        wmanIf2BsPkmPmkPrehandshakeLifetime     Integer32,
        wmanIf2BsPkmPmkLifetime                 Integer32,
        wmanIf2BsSaChallengeTimeout             Integer32,
        wmanIf2BsMaxSaTekChallenge              Integer32,
        wmanIf2BsSaTekTimeout                   Integer32,
        wmanIf2BsMaxSaTekRequest                Integer32}

wmanIf2BsPkmPmkPrehandshakeLifetime OBJECT-TYPE
        SYNTAX      Integer32 (5 .. 900)
        UNITS       "seconds"
        MAX-ACCESS  read-write
        STATUS      current
        DESCRIPTION
            "This object defines the PMK or PAK prehandshake lifetime."
        REFERENCE
             "Table 343 in IEEE Std 802.16e-2005"
        DEFVAL         { 10 }
        ::= { wmanIf2BsPkmV2ConfigEntry 1 }

wmanIf2BsPkmPmkLifetime OBJECT-TYPE
        SYNTAX      Integer32 (60 .. 86400)
        UNITS       "seconds"
        MAX-ACCESS  read-write
        STATUS      current
        DESCRIPTION
            "This object defines PMK lifetime, if MSK lifetime is
             unspecified (i.e., by AAA server)."
        REFERENCE
             "Table 343 in IEEE Std 802.16e-2005"
        DEFVAL         { 3600 }
        ::= { wmanIf2BsPkmV2ConfigEntry 2 }

wmanIf2BsSaChallengeTimeout OBJECT-TYPE
        SYNTAX      Integer32 (500 .. 2000)
        UNITS       "milliseconds"
        MAX-ACCESS  read-write
        STATUS      current
        DESCRIPTION
            "This object defines the timeout value for SA-TEKChallenge
             retransmission."
        REFERENCE
             "Table 343 in IEEE Std 802.16e-2005"
        DEFVAL         { 1000 }
        ::= { wmanIf2BsPkmV2ConfigEntry 3 }

wmanIf2BsMaxSaTekChallenge OBJECT-TYPE
        SYNTAX      Integer32 (1 .. 3)
        MAX-ACCESS  read-write
        STATUS      current
        DESCRIPTION
            "This object defines the maximum number of SA-TEK-Challenge
             transmissions."
        REFERENCE
             "Table 343 in IEEE Std 802.16e-2005"
        DEFVAL         { 3 }
        ::= { wmanIf2BsPkmV2ConfigEntry 4 }       

wmanIf2BsSaTekTimeout OBJECT-TYPE
        SYNTAX      Integer32 (100 .. 1000)
        UNITS       "milliseconds"
        MAX-ACCESS  read-write
        STATUS      current
        DESCRIPTION
            "This object defines the timeout value for SA-TEKRequest
             retransmission."
        REFERENCE
             "Table 343 in IEEE Std 802.16e-2005"
        DEFVAL         { 300 }
        ::= { wmanIf2BsPkmV2ConfigEntry 5 }                       

wmanIf2BsMaxSaTekRequest OBJECT-TYPE
        SYNTAX      Integer32 (1 .. 3)
        MAX-ACCESS  read-write
        STATUS      current
        DESCRIPTION
            "This object defines the maximum number of SA-TEK-Request
             retransmission."
        REFERENCE
             "Table 343 in IEEE Std 802.16e-2005"
        DEFVAL         { 3 }
        ::= { wmanIf2BsPkmV2ConfigEntry 6 }
        
--
-- Table wmanIf2BsSsPkmV2RsaAuthTable
--
wmanIf2BsSsPkmV2RsaAuthTable OBJECT-TYPE
        SYNTAX      SEQUENCE OF WmanIf2BsSsPkmV2RsaAuthEntry
        MAX-ACCESS  not-accessible
        STATUS      current
        DESCRIPTION
            "This table contains information related to PKMV2
             RSA based authorization process."
        REFERENCE
            "Subclause 6.3.2.3.9.11 in IEEE Std 802.16e-2005"
        ::= { wmanIf2BsPkmV2Objects 2 }

wmanIf2BsSsPkmV2RsaAuthEntry OBJECT-TYPE
        SYNTAX      WmanIf2BsSsPkmV2RsaAuthEntry
        MAX-ACCESS  not-accessible
        STATUS      current
        DESCRIPTION
            "Each entry contains objects that define the SS
             authorization attributes for each SS associated with each
             BS sector."
        INDEX     { ifIndex, wmanIf2BsSsMacAddress }
        ::= { wmanIf2BsSsPkmV2RsaAuthTable  1 }

WmanIf2BsSsPkmV2RsaAuthEntry ::= SEQUENCE {
        wmanIf2BsSsPkmV2BsCertificate           OCTET STRING,
        wmanIf2BsSsPkmV2SsCertificate           OCTET STRING,
        wmanIf2BsSsPkmV2SaId                    INTEGER,
        wmanIf2BsSsPkmV2SsRandom                OCTET STRING,
        wmanIf2BsSsPkmV2BsRandom                OCTET STRING,        
        wmanIf2BsSsPkmV2AuthKeySequenceNumber   Integer32,
        wmanIf2BsSsPkmV2AuthKeyLifetime         Integer32,
        wmanIf2BsSsPkmV2AuthResult              INTEGER,
        wmanIf2BsSsPkmV2AuthFailure             WmanIf2PkmErrorCode,
        wmanIf2BsSsPkmV2AkN-1ExpireTime         DateAndTime,
        wmanIf2BsSsPkmV2AkNExpireTime           DateAndTime,
        wmanIf2BsSsPkmV2CertificateStatus       WmanIf2CertificateStat}

wmanIf2BsSsPkmV2BsCertificate OBJECT-TYPE
        SYNTAX      OCTET STRING (SIZE(0..65535))  
        MAX-ACCESS  read-only
        STATUS      current
        DESCRIPTION
            "BS sends the BS-Certificate in the PKMV2 RSA-Reply message
             for BS-SS mutual authentication. It is the DER-encoded
             ASN.1 X.509 BS Certificate."
        REFERENCE
            "Subclause 11.9.24 in IEEE Std 802.16e-2005"
        ::= { wmanIf2BsSsPkmV2RsaAuthEntry 1 }

wmanIf2BsSsPkmV2SsCertificate OBJECT-TYPE
        SYNTAX      OCTET STRING (SIZE(0..65535)) 
        MAX-ACCESS  read-only
        STATUS      current
        DESCRIPTION
            "SS sends the SS-Certificate in the PKMV2 RSA-Request
             message. It contains an X.509 SS certificate issued by the
             SS's manufacturer. The SS's X.509 certificate is a
             public-key certificate which binds the SS's identifying
             information to its RSA public key in a verifiable manner.
             The X.509 certificate is digitally signed by the SS's
             manufacturer, and that signature can be verified by a BS
             that knows the manufacturer's public key.
             The manufacturer's public key is placed in an X.509
             certification authority (CA) certificate, which in turn
             is signed by a higher level CA."
        REFERENCE
            "Subclause 11.9.12 in IEEE Std 802.16-2004"
        ::= { wmanIf2BsSsPkmV2RsaAuthEntry 2 }

wmanIf2BsSsPkmV2SaId OBJECT-TYPE
        SYNTAX      INTEGER (0..65535) 
        MAX-ACCESS  read-only
        STATUS      current
        DESCRIPTION
            "SS's primary SAID equal to the Basic CID. SS sends the SAID
             in the PKMV2 RSA-Request message."
        REFERENCE
             "Subclause 6.3.2.3.9.2 in IEEE Std 802.16-2004"
        ::= { wmanIf2BsSsPkmV2RsaAuthEntry 3 }

wmanIf2BsSsPkmV2SsRandom OBJECT-TYPE
        SYNTAX      OCTET STRING (SIZE(8))  
        MAX-ACCESS  read-only
        STATUS      current
        DESCRIPTION
            "This attribute contains a quantity that is pseudo random
             number generated from the MS and used as fresh number for
             mutual authorization message handshake. SS sends the
             SS-Random in the PKMV2 RSA-Request message."
        REFERENCE
            "Subclause 11.9.21 in IEEE Std 802.16e-2005"
        ::= { wmanIf2BsSsPkmV2RsaAuthEntry 4 }

wmanIf2BsSsPkmV2BsRandom OBJECT-TYPE
        SYNTAX      OCTET STRING (SIZE(8))  
        MAX-ACCESS  read-only
        STATUS      current
        DESCRIPTION
            "This attribute contains a quantity that is pseudo random
             number generated from the BS and used as fresh number for
             mutual authorization message handshake.BS sends the
             BS-Random in the PKMV2 RSA-Reply message."
        REFERENCE
            "Subclause 11.9.22 in IEEE Std 802.16e-2005"
        ::= { wmanIf2BsSsPkmV2RsaAuthEntry 5 }
                
wmanIf2BsSsPkmV2AuthKeySequenceNumber OBJECT-TYPE
        SYNTAX      Integer32 (0 .. 15)
        MAX-ACCESS  read-only
        STATUS      current
        DESCRIPTION
            "This object provides the most recent authorization key
             sequence number in the PKMV2 RSA-Reply message for an SS."
        REFERENCE
             "Subclause 11.9.5 in IEEE Std 802.16e-2005"
        ::= { wmanIf2BsSsPkmV2RsaAuthEntry 6 }
        
wmanIf2BsSsPkmV2AuthKeyLifetime OBJECT-TYPE
        SYNTAX      Integer32 (86400..6048000)
        UNITS       "seconds"
        MAX-ACCESS  read-only
        STATUS      current
        DESCRIPTION
            "This object defines the lifetime of an authorization
             key (AK) the BS assigns to a SS. BS sends the key lifetime
             in the PKMV2 RSA-Reply message."
        REFERENCE
             "Subclause 11.9.4 in IEEE Std 802.16e-2005"
        ::= { wmanIf2BsSsPkmV2RsaAuthEntry 7 }
        
wmanIf2BsSsPkmV2AuthResult OBJECT-TYPE
        SYNTAX      INTEGER {success(0),
                             reject(1)}
        MAX-ACCESS  read-only
        STATUS      current
        DESCRIPTION
            "This attribute contains the result code of the RSA-based
             authorization. SS sends the result code in PKMV2 
             RSA-Acknowledgement message."
        REFERENCE
             "Subclause 11.9.4 in IEEE Std 802.16e-2005"
        ::= { wmanIf2BsSsPkmV2RsaAuthEntry 8 }
                
wmanIf2BsSsPkmV2AuthFailure OBJECT-TYPE
        SYNTAX      WmanIf2PkmErrorCode 
        MAX-ACCESS  read-only
        STATUS      current
        DESCRIPTION
            "BS returs PKMV2 RSA-Rejects message if an authorization
             failure is detected.
             
             Failure type umknownManufactur(4)- ssBsIncompatibleSc(9)are
             considered permanent authorization failure, since any
             attempts of reauthorization would continue to result in
             Authorization Rejects. Details about the cause of a
             Permanent Authorization Failure may be reported to the SS
             in an optional Display-String attribute that may accompany
             the Error-Code attribute in Authorization Reject messages.
             
             Note that the BS may log the Display-String attribute and
             Authorization failures in wmanIfDevMib, and generate a trap
             to an SNMP manager."
        REFERENCE
             "Subclause 11.9.10 in IEEE Std 802.16-2004"
        ::= { wmanIf2BsSsPkmV2RsaAuthEntry 9 }

wmanIf2BsSsPkmV2AkN-1ExpireTime OBJECT-TYPE
        SYNTAX      DateAndTime
        MAX-ACCESS  read-only
        STATUS      current
        DESCRIPTION
            "This object is the time when AK(N-1) expires.
             wmanIf2BsSsPkmV2AkN-1ExpireTime =
                 RSA-Reply[AK(N-1)] arrival time +  AK(N-1) lifetime

             If this FSM has only one authorization key, then
             wmanIf2BsSsPkmV2AkN-1ExpireTime = the activation of FSM."
        ::= { wmanIf2BsSsPkmV2RsaAuthEntry 10 }

wmanIf2BsSsPkmV2AkNExpireTime OBJECT-TYPE
        SYNTAX      DateAndTime
        MAX-ACCESS  read-only
        STATUS      current
        DESCRIPTION
            "This object is the time when AK(N) expires.
             wmanIf2BsSsPkmV2AkNExpireTime =
                 RSA-Reply[AK(N)] arrival time +  AK(N) lifetime

             If this FSM has only one authorization key, then
             wmanIf2BsSsPkmV2AkNExpireTime = the activation of FSM."
        ::= { wmanIf2BsSsPkmV2RsaAuthEntry 11 }
        
wmanIf2BsSsPkmV2CertificateStatus OBJECT-TYPE
        SYNTAX      WmanIf2CertificateStat
        MAX-ACCESS  read-only
        STATUS      current
        DESCRIPTION
            "Indicate the reason why a SS's certificate is deemed valid
             or invalid."
        ::= { wmanIf2BsSsPkmV2RsaAuthEntry 12 }

--
-- Table wmanIf2BsSsPkmV2TekTable
--
wmanIf2BsSsPkmV2TekTable OBJECT-TYPE
        SYNTAX      SEQUENCE OF WmanIf2BsSsPkmV2TekEntry
        MAX-ACCESS  not-accessible
        STATUS      current
        DESCRIPTION
            "This table contains the TEK attributes that are associated
             with each SAID."
        ::= { wmanIf2BsPkmV2Objects 3 }

wmanIf2BsSsPkmV2TekEntry OBJECT-TYPE
        SYNTAX      WmanIf2BsSsPkmV2TekEntry
        MAX-ACCESS  not-accessible
        STATUS      current
        DESCRIPTION
            ""
        INDEX     { ifIndex,
                    wmanIf2BsSsMacAddress,
                    wmanIf2BsSsPkmV2SaidIndex }
        ::= { wmanIf2BsSsPkmV2TekTable  1 }

WmanIf2BsSsPkmV2TekEntry ::= SEQUENCE {
        wmanIf2BsSsPkmV2SaidIndex               INTEGER,
        wmanIf2BsSsPkmV2SaType                  WmanIf2SaType,
        wmanIf2BsSsPkmV2SaServiceType           WmanIf2SaServiceType,
        wmanIf2BsSsPkmV2TekDataEncryptAlgorithm WmanIf2DataEncryptAlgId,
        wmanIf2BsSsPkmV2TekDataAuthentAlgorithm WmanIf2DataAuthAlgId,
        wmanIf2BsSsPkmV2TekEncryptAlgorithm     WmanIf2TekEncryptAlgId,
        wmanIf2BsSsPkmV2TekN-1SequenceNumber    Integer32,
        wmanIf2BsSsPkmV2TekN-1Lifetime          Integer32,
        wmanIf2BsSsPkmV2TekNSequenceNumber      Integer32,
        wmanIf2BsSsPkmV2TekNLifetime            Integer32,                
        wmanIf2BsSsPkmV2TekInvalidError         WmanIf2PkmErrorCode,
        wmanIf2BsSsPkmV2TekN-1ExpireTime        DateAndTime,
        wmanIf2BsSsPkmV2TekNExpireTime          DateAndTime}
        
wmanIf2BsSsPkmV2SaidIndex OBJECT-TYPE
        SYNTAX      INTEGER (0 .. 65535)
        MAX-ACCESS  not-accessible
        STATUS      current
        DESCRIPTION
            "SAID index to the wmanIf2BsSsPkmV2TekTable."
        ::= { wmanIf2BsSsPkmV2TekEntry 1 }

wmanIf2BsSsPkmV2SaType OBJECT-TYPE
        SYNTAX      WmanIf2SaType
        MAX-ACCESS  read-only
        STATUS      current
        DESCRIPTION
            "SA Type attribute that is included in the PKMv2
             SA-TEK-response message."
        REFERENCE
            "Table 567 in subclause 11.9.18"
        ::= { wmanIf2BsSsPkmV2TekEntry 2 }

wmanIf2BsSsPkmV2SaServiceType OBJECT-TYPE
        SYNTAX      WmanIf2SaServiceType
        MAX-ACCESS  read-only
        STATUS      current
        DESCRIPTION
            "SA Type attribute that is included in the PKMv2
             SA-TEK-response message."
        REFERENCE
             "Table 383"
        ::= { wmanIf2BsSsPkmV2TekEntry 3 }

wmanIf2BsSsPkmV2TekDataEncryptAlgorithm OBJECT-TYPE
        SYNTAX      WmanIf2DataEncryptAlgId
        MAX-ACCESS  read-only
        STATUS      current
        DESCRIPTION
            "The data encryption algorithm attribute that is included
             in the PKMv2 SA-TEK-response message."
        REFERENCE
             "Table 383, IEEE Std 802.16e-2005"
        ::= { wmanIf2BsSsPkmV2TekEntry 4 }

wmanIf2BsSsPkmV2TekDataAuthentAlgorithm OBJECT-TYPE
        SYNTAX      WmanIf2DataAuthAlgId
        MAX-ACCESS  read-only
        STATUS      current
        DESCRIPTION
            "The data authentication algorithm attribute that is
             included in the PKMv2 SA-TEK-response message."
        REFERENCE
             "Table 383, IEEE Std 802.16e-2005"
        ::= { wmanIf2BsSsPkmV2TekEntry 5 }

wmanIf2BsSsPkmV2TekEncryptAlgorithm OBJECT-TYPE
        SYNTAX      WmanIf2TekEncryptAlgId
        MAX-ACCESS  read-only
        STATUS      current
        DESCRIPTION
            "The TEK key encryption algorithm attribute that is
             included in the PKMv2 SA-TEK-response message."
        REFERENCE
             "Table 383, IEEE Std 802.16e-2005"
        ::= { wmanIf2BsSsPkmV2TekEntry 6 }
                
wmanIf2BsSsPkmV2TekN-1SequenceNumber OBJECT-TYPE
        SYNTAX      Integer32 (0 .. 3)
        MAX-ACCESS  read-only
        STATUS      current
        DESCRIPTION
            "At all times the BS maintains two sets of active
             generations of keying material per SAID. One set
             corresponds to the 'N-1' generation of keying material,
             the second set corresponds to the 'N' generation of
             keying material. The N generation has a key sequence
             number one greater than (modulo 4) that of the N-1
             generation. This object provides the older TEK sequence
             number in the Key Reply message for an SS."
        REFERENCE
            "Subclause 11.9.8 in IEEE Std 802.16e-2005"
        ::= { wmanIf2BsSsPkmV2TekEntry 7 }

wmanIf2BsSsPkmV2TekN-1Lifetime OBJECT-TYPE
        SYNTAX      Integer32 (1800 .. 604800)
        UNITS       "seconds"
        MAX-ACCESS  read-only
        STATUS      current
        DESCRIPTION
            "This object provides the N-1 TEK Remaining Lifetime."
        REFERENCE
            "Subclause 11.9.8 in IEEE Std 802.16e-2005"
        ::= { wmanIf2BsSsPkmV2TekEntry 8 }

wmanIf2BsSsPkmV2TekNSequenceNumber OBJECT-TYPE
        SYNTAX      Integer32 (0 .. 3)
        MAX-ACCESS  read-only
        STATUS      current
        DESCRIPTION
            "This object provides the N TEK sequence number in the
             Key Reply message for an SS."
        REFERENCE
            "Subclause 11.9.8 in IEEE Std 802.16e-2005"
        ::= { wmanIf2BsSsPkmV2TekEntry 9 }

wmanIf2BsSsPkmV2TekNLifetime OBJECT-TYPE
        SYNTAX      Integer32 (1800 .. 604800)
        UNITS       "seconds"
        MAX-ACCESS  read-only
        STATUS      current
        DESCRIPTION
            "This object provides the N TEK Remaining Lifetime."
        REFERENCE
            "Subclause 11.9.8 in IEEE Std 802.16e-2005"
        ::= { wmanIf2BsSsPkmV2TekEntry 10 }
                
wmanIf2BsSsPkmV2TekInvalidError OBJECT-TYPE
        SYNTAX      WmanIf2PkmErrorCode 
        MAX-ACCESS  read-only
        STATUS      current
        DESCRIPTION
            "BS returns the PKMv2 TEK-Invalid message if the BS
             determines that the MS encrypted an UL PDU with an invalid
             TEK.
             
             Note that the BS may log the Display-String attribute and
             PKMv2 TEK-Invalid error in wmanIfDevMib."
        REFERENCE
            "Subclause 11.9.10 in IEEE Std 802.16-2004, and
             Subclause 6.3.2.3.9.25 in IEEE Std 802.16e-2005"
        ::= { wmanIf2BsSsPkmV2TekEntry 11 }

wmanIf2BsSsPkmV2TekN-1ExpireTime OBJECT-TYPE
        SYNTAX DateAndTime
        MAX-ACCESS read-only
        STATUS current
        DESCRIPTION
            "This object is the time when TEK(N-1) expires.
             wmanIf2BsSsPkmV2TekN-1ExpireTime =
                 Key Reply[TEK(N-1)] arrival time +  TEK(N-1) lifetime

             If this FSM has only one authorization key, then
             wmanIf2BsSsPkmV2TekN-1ExpireTime = the activation of FSM."
        ::= { wmanIf2BsSsPkmV2TekEntry 12 }

wmanIf2BsSsPkmV2TekNExpireTime OBJECT-TYPE
        SYNTAX DateAndTime
        MAX-ACCESS read-only
        STATUS current
        DESCRIPTION
            "This object is the time when TEK(N) expires.
             wmanIf2BsSsPkmV2TekNExpireTime =
                 Key Reply[TEK(N)] arrival time +  TEK(N) lifetime

             If this FSM has only one authorization key, then
             wmanIf2BsSsPkmV2TekNExpireTime = the activation of FSM."
        ::= { wmanIf2BsSsPkmV2TekEntry 13 }

--
-- Table wmanIf2BsSsPkmV23wayHandshakeTable
--
wmanIf2BsSsPkmV23wayHandshakeTable OBJECT-TYPE
        SYNTAX      SEQUENCE OF WmanIf2BsSsPkmV23wayHandshakeEntry
        MAX-ACCESS  not-accessible
        STATUS      current
        DESCRIPTION
            "This table contains information related to PKMV2 3-way
             handshake process."
        REFERENCE
            "Subclause 7.8.1 in IEEE Std 802.16e-2005"
        ::= { wmanIf2BsPkmV2Objects 4 }

wmanIf2BsSsPkmV23wayHandshakeEntry OBJECT-TYPE
        SYNTAX      WmanIf2BsSsPkmV23wayHandshakeEntry
        MAX-ACCESS  not-accessible
        STATUS      current
        DESCRIPTION
            "Each entry contains objects that define the SS 3-way
             handshake attributes for each SS associated with each
             BS sector."
        INDEX     { ifIndex, wmanIf2BsSsMacAddress }
        ::= { wmanIf2BsSsPkmV23wayHandshakeTable  1 }

WmanIf2BsSsPkmV23wayHandshakeEntry ::= SEQUENCE {
        wmanIf2BsSsPkmV2SaTekBsRandom           OCTET STRING,
        wmanIf2BsSsPkmV2SaTekAkSequenceNumber   Integer32,
        wmanIf2BsSsPkmV2SaTekAkId               OCTET STRING,
        wmanIf2BsSsPkmV2KeyLifetime             Integer32,
        wmanIf2BsSsPkmV2SaTekMsRandom           OCTET STRING}

wmanIf2BsSsPkmV2SaTekBsRandom OBJECT-TYPE
        SYNTAX      OCTET STRING (SIZE(8))  
        MAX-ACCESS  read-only
        STATUS      current
        DESCRIPTION
            "This attribute contains a quantity that is a random number
             generated from the BS and used as fresh number for 3-way
             handshake process. BS sends the BS-Random in the PKMV2
             SA-TEK-Challenge message."
        REFERENCE
            "Table 37h, Subclause 11.9.22 in IEEE Std 802.16e-2005"
        ::= { wmanIf2BsSsPkmV23wayHandshakeEntry 1 }

wmanIf2BsSsPkmV2SaTekAkSequenceNumber OBJECT-TYPE
        SYNTAX      Integer32 (0 .. 15)
        MAX-ACCESS  read-only
        STATUS      current
        DESCRIPTION
            "This object indicates the sequence number of root keys
             (PAK and PMK) for the AK. This value is the most
             significant 2-bit of PAK sequence number concatenated
             with the least significant 2-bit of PMK sequence number.
             BS sends the sequence number in the PKMV2 SA-TEK-Challenge
             message."
        REFERENCE
             "Table 37h, 133a in IEEE Std 802.16-2004"
        ::= { wmanIf2BsSsPkmV23wayHandshakeEntry 2 }

wmanIf2BsSsPkmV2SaTekAkId OBJECT-TYPE
        SYNTAX      OCTET STRING (SIZE(8))
        MAX-ACCESS  read-only
        STATUS      current
        DESCRIPTION
            "This objects is used to identify the AK. BS sends the AKID
             attribute in the PKMV2 SA-TEK-Challenge message."
        REFERENCE
             "Table 37h, 133a in IEEE Std 802.16-2004"
        ::= { wmanIf2BsSsPkmV23wayHandshakeEntry 3 }
                
wmanIf2BsSsPkmV2KeyLifetime OBJECT-TYPE
        SYNTAX      Integer32 (60 .. 86400)
        UNITS       "seconds"
        MAX-ACCESS  read-only
        STATUS      current
        DESCRIPTION
            "This object indicates the PMK lifetime. BS sends the key
             lifetime attribute in the PKMV2 SA-TEK-Challenge message."
        REFERENCE
             "Table 37h, Subclause 11.9.4 in IEEE Std 802.16e-2005"
        ::= { wmanIf2BsSsPkmV23wayHandshakeEntry 4 }
                
wmanIf2BsSsPkmV2SaTekMsRandom OBJECT-TYPE
        SYNTAX      OCTET STRING (SIZE(8))  
        MAX-ACCESS  read-only
        STATUS      current
        DESCRIPTION
            "This attribute contains a quantity that is a random number
             generated from the MS and used as fresh number for 3-way
             handshake process. MS sends the MS-Random in the PKMV2
             SA-TEK-Request message."
        REFERENCE
            "Table 37i, Subclause 11.9.21 in IEEE Std 802.16e-2005"
        ::= { wmanIf2BsSsPkmV23wayHandshakeEntry 5 }
        
--
-- Conformance Information
--
wmanIf2MibConformance OBJECT IDENTIFIER ::= {wmanIf2BsMib 2}
wmanIf2BsMibGroups      OBJECT IDENTIFIER ::= {wmanIf2MibConformance 1}
wmanIf2BsMibCompliances OBJECT IDENTIFIER ::= {wmanIf2MibConformance 2}

-- compliance statements
wmanIf2BsMibCompliance MODULE-COMPLIANCE 
        STATUS      current
        DESCRIPTION
            "The compliance statement for devices that implement
             Wireless MAN interfaces as defined in IEEE Std 802.16-2004."

        MODULE  -- wmanIf2BsMib
                    
        GROUP wmanIf2MibBsGroup      -- conditionally mandatory group
        DESCRIPTION
            "This group is mandatory for Base Station."

        GROUP wmanIf2MibBsAasGroup   -- optional group
        DESCRIPTION
            "This group is mandatory for Base Station."

        GROUP wmanIf2MibBsOfdmGroup  -- conditionally mandatory group
        DESCRIPTION
            "This group is mandatory for Base Station
             implementaing the OFDM PHY."            

        GROUP wmanIf2MibBsOfdmaGroup -- conditionally mandatory group
        DESCRIPTION
            "This group is mandatory for Base Station
             implementaing the OFDMA PHY."
             
        GROUP wmanIf2MibBsNotificationGroup -- unconditionally
                                           -- mandatory groups
        DESCRIPTION
            "This group is mandatory for Base Station."
        ::= { wmanIf2BsMibCompliances 1 }
        
wmanIf2MibBsGroup     OBJECT-GROUP
        OBJECTS {-- Capability negotiation
                 wmanIf2BsSsBasicCid,
                 wmanIf2BsSsPrimaryCid,
                 wmanIf2BsSsSecondaryCid,
                 wmanIf2BsSsManagementSupport,
                 wmanIf2BsSsIpManagementMode,
                 wmanIf2Bs2ndMgmtDlQoSProfileIndex,
                 wmanIf2Bs2ndMgmtUlQoSProfileIndex,
                 wmanIf2BsAutoSfidEnabled,
                 wmanIf2BsAutoSfidRangeMin,
                 wmanIf2BsAutoSfidRangeMax,
                 wmanIf2BsResetSector, 
                 wmanIf2BsSs2ndMgmtArqEnable,
                 wmanIf2BsSs2ndMgmtArqWindowSize,
                 wmanIf2BsSs2ndMgmtArqDnLinkTxDelay,
                 wmanIf2BsSs2ndMgmtArqUpLinkTxDelay,
                 wmanIf2BsSs2ndMgmtArqDnLinkRxDelay,
                 wmanIf2BsSs2ndMgmtArqUpLinkRxDelay,
                 wmanIf2BsSs2ndMgmtArqBlockLifetime,
                 wmanIf2BsSs2ndMgmtArqSyncLossTimeout,
                 wmanIf2BsSs2ndMgmtArqDeliverInOrder,
                 wmanIf2BsSs2ndMgmtArqRxPurgeTimeout,
                 wmanIf2BsSs2ndMgmtArqBlockSize,
                 wmanIf2BsSsVendorIdEncoding,
                 wmanIf2BsSsAasBroadcastPermission, 
                 wmanIf2BsSsMaxTxPowerBpsk, 
                 wmanIf2BsSsMaxTxPowerQpsk,
                 wmanIf2BsSsMaxTxPower16Qam,
                 wmanIf2BsSsMaxTxPower64Qam,
                 
                 -- Configuration parameters
                 wmanIf2BsSsMacVersion,
                 wmanIf2BsDcdInterval,
                 wmanIf2BsUcdInterval,
                 wmanIf2BsUcdTransition,
                 wmanIf2BsDcdTransition,
                 wmanIf2BsInitialRangingInterval,
                 wmanIf2BsSsULMapProcTime,
                 wmanIf2BsSsRangRespProcTime,
                 wmanIf2BsT9Timeout,
                 wmanIf2BsT13Timeout,
                 wmanIf2BsT15Timeout,
                 wmanIf2BsT17Timeout,
                 wmanIf2BsT27IdleTimer,
                 wmanIf2BsT27ActiveTimer,
                 
                 -- Performance monitoring
                 wmanIf2BsHistogramIndex,
                 wmanIf2BsChannelNumber,
                 wmanIf2BsStartFrame,
                 wmanIf2BsDuration,
                 wmanIf2BsBasicReport,
                 wmanIf2BsMeanCinrReport,
                 wmanIf2BsMeanRssiReport,
                 wmanIf2BsStdDeviationCinrReport,
                 wmanIf2BsStdDeviationRssiReport,

                 -- Capability negotiation
                 wmanIf2BsSsActionsResetSs,
                 wmanIf2BsSsActionsAbortSs,
                 wmanIf2BsSsActionsOverrideDnFreq,
                 wmanIf2BsSsActionsOverrideChannelId,
                 wmanIf2BsSsActionsDeReRegSs,
                 wmanIf2BsSsActionsDeReRegSsCode,
                 wmanIf2BsSsActionsRowStatus,
                 
                 -- Privacy sublayer
                 wmanIf2BsPkmV1AkLifetime,
                 wmanIf2BsPkmV1TekLifetime,
                 wmanIf2BsPkmV1SelfSigManufCertTrust,
                 wmanIf2BsPkmV1CheckCertValidityPeriods,
                 
                 -- Notification
                 wmanIf2BsTrapControlRegister,
                 wmanIf2BsStatusTrapControlRegister,
                 wmanIf2BsRssiLowThreshold,
                 wmanIf2BsRssiHighThreshold,
                 wmanIf2BsSsNotificationMacAddr,
                 wmanIf2BsSsStatusValue,
                 wmanIf2BsSsStatusInfo,
                 wmanIf2BsDynamicServiceType,
                 wmanIf2BsDynamicServiceFailReason,
                 wmanIf2BsSsRssiStatus,
                 wmanIf2BsSsRssiStatusInfo,
                 wmanIf2BsSsRegisterStatus}
        STATUS       current
        DESCRIPTION
            "This group contains objects for BS, and are 
             independent of PHY."
        ::= { wmanIf2BsMibGroups 1 }                  

wmanIf2MibBsAasGroup     OBJECT-GROUP
        OBJECTS {-- AAS Configuration parameters
                 wmanIf2BsAasChanFbckReqFreq,
                 wmanIf2BsAasBeamSelectFreq,
                 wmanIf2BsAasChanFbckReqResolution,
                 wmanIf2BsAasBeamReqResolution,
                 wmanIf2BsAasNumOptDiversityZones}
        STATUS       current
        DESCRIPTION
            "This group contains objects for AAS in BS."
        ::= { wmanIf2BsMibGroups 2 }

wmanIf2MibBsOfdmGroup     OBJECT-GROUP
        OBJECTS {wmanIf2BsOfdmBwReqOppSize,
                 wmanIf2BsOfdmRangReqOppSize,
                 wmanIf2BsOfdmNumSubChReqRegionFull,
                 wmanIf2BsOfdmNumSymbolsReqRegionFull,
                 wmanIf2BsOfdmSubChFocusCtCode,   
                 wmanIf2BsOfdmFrameDurationCode,
                 wmanIf2BsOfdmUcdFecCodeType,
                 wmanIf2BsOfdmFocusCtPowerBoost,
                 wmanIf2BsOfdmUcdTcsEnable,
                 wmanIf2BsOfdmUcdBurstProfileRowStatus,
                 wmanIf2BsOfdmDcdFecCodeType,
                 wmanIf2BsOfdmTcsEnable, 
                 wmanIf2BsOfdmDcdBurstProfileRowStatus,
                 wmanIf2BsOfdmMinReqRegionFullTxOpp,
                 wmanIf2BsOfdmMinFocusedCtTxOpp,
                 wmanIf2BsOfdmMaxRoundTripDelay,
                 wmanIf2BsOfdmRangeAbortTimingThold,
                 wmanIf2BsOfdmRangeAbortPowerThold ,
                 wmanIf2BsOfdmRangeAbortFreqThold,
                 wmanIf2BsOfdmDnlkRateId}
        STATUS       current
        DESCRIPTION
            "This group contains objects for BS and OFDM PHY."
        ::= { wmanIf2BsMibGroups 3 }
        
wmanIf2MibBsOfdmaGroup     OBJECT-GROUP
        OBJECTS {wmanIf2BsOfdmaStartOfRngCodes,
                 wmanIf2BsOfdmaPermutationBase,
                 wmanIf2BsOfdmaULAllocSubchBitmap,
                 wmanIf2BsOfdmaOptPermULAllocSubchBitmap,
                 wmanIf2BsOfdmaBandAMCAllocThreshold,
                 wmanIf2BsOfdmaBandAMCReleaseThreshold,
                 wmanIf2BsOfdmaBandAMCAllocTimer,
                 wmanIf2BsOfdmaBandAMCReleaseTimer,
                 wmanIf2BsOfdmaBandStatRepMAXPeriod,
                 wmanIf2BsOfdmaBandAMCRetryTimer,
                 wmanIf2BsOfdmaFrameDurationCode,
                 wmanIf2BsOfdmaUcdFecCodeType,
                 wmanIf2BsOfdmaRangingDataRatio,
                 wmanIf2BsOfdmaUcdBurstProfileRowStatus,
                 wmanIf2BsOfdmaDcdFecCodeType,
                 wmanIf2BsOfdmaDcdBurstProfileRowStatus}        
        STATUS       current
        DESCRIPTION
            "This group contains objects for BS and OFDMA PHY."
        ::= { wmanIf2BsMibGroups 4 }
        
wmanIf2MibBsNotificationGroup     NOTIFICATION-GROUP
        NOTIFICATIONS {wmanIf2BsSsStatusNotificationTrap,
                       wmanIf2BsSsRssiStatusChangeTrap,
                       wmanIf2BsSsPkmFailTrap}
        STATUS       current
        DESCRIPTION
            "This group contains event notifications for BS."
        ::= { wmanIf2BsMibGroups 5 }                                   
END
