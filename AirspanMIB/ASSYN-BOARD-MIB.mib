--
-- ASSYN-BOARD-MIB.mib
-- MIB generated by MG-SOFT Visual MIB Builder 2010 Version 8.0  Build 400
-- Tuesday, November 29, 2011 at 16:48:15
--

    ASSYN-BOARD-MIB DEFINITIONS ::= BEGIN
 
        IMPORTS
            asSyn            
                FROM AIRSPAN-PRODUCTS-MIB            
            AsCmnTcBooleanSwitch, AsCmnTcResetCmd, AsCmnTcOperationalStatus            
                FROM ASCMN-TC-MIB            
            ifIndex            
                FROM IF-MIB            
            InetAddressType, InetAddress            
                FROM INET-ADDRESS-MIB            
            OBJECT-GROUP, MODULE-COMPLIANCE, NOTIFICATION-GROUP            
                FROM SNMPv2-CONF            
            Integer32, OBJECT-TYPE, MODULE-IDENTITY, NOTIFICATION-TYPE            
                FROM SNMPv2-SMI            
            DisplayString, RowStatus, TEXTUAL-CONVENTION            
                FROM SNMPv2-TC;
    
    
        -- 1.3.6.1.4.1.989.1.23.1
        asSynBd MODULE-IDENTITY 
            LAST-UPDATED "201108240941Z"		-- August 24, 2011 at 09:41 GMT
            ORGANIZATION 
                "Airspan Communications Ltd"
            CONTACT-INFO 
                "kdudzins@airspan.com"
            DESCRIPTION 
                "Propriatory MIB for board specific functionality on the AirSynergy platform."
            REVISION "201103150941Z"		-- March 15, 2011 at 09:41 GMT
            DESCRIPTION 
                "Pre-Draft 1:
                - initial version "
            REVISION "201103290941Z"		-- March 29, 2011 at 09:41 GMT
            DESCRIPTION 
                "Pre-Draft 3:
                - Removed: asSynBdGpsStsTauTR,asSynBdGpsStsModeMR,asSynBdGpsStsLedStatus,asSynBdGpsStsHbsqHR,asSynBdGpsStsMode, 
                asSynBdGpsStsWtrWR,asSynBdGpsStsCw25LedStatus,asSynBdGpsStsCw25HoldoverGuaranteedStatus,asSynBdGpsCfgOsaModeMU
                asSynBdGpsStsCw25HoldoverDegradedStatus,asSynBdGpsCfgCw25ModeMU,asSynBdGpsCfgCw25HoldoverGuaranteedPeriod, 
                asSynBdGpsCfgCw25HoldoverDegradedPeriod,asSynBdGpsCfgCw25DegradedBehaviour,asSynBdGpsCfgCw25ExpiredBehaviour
                asSynBdGpsStsComms.
                "
            REVISION "201105230941Z"		-- May 23, 2011 at 09:41 GMT
            DESCRIPTION 
                "Pre-Draft 4:
                - Re-formatted using MG-SOFT MIB Builder.
                Fixed SMI warnings"
            REVISION "201108090941Z"		-- August 09, 2011 at 09:41 GMT
            DESCRIPTION 
                "Pre-Draft 5:
                - Removed: asSynBdGpsInstance from GPS traps: asSynBdGpsLockChangeTrap,asSynBdGpsSnrChangeTrap,asSynBdGpsAlarmsChangeTrap.
                Added NTP configuration and status"
            REVISION "201108240941Z"		-- August 24, 2011 at 09:41 GMT
            DESCRIPTION 
                "Pre-Draft 6:
                - Fixed compilation warnings/ SMI warnings when compiled with MIB-Builder"
            REVISION "201111291644Z"		-- November 29, 2011 at 16:44 GMT
            DESCRIPTION 
                "Pre-Draft 7:
                - TectualConvention AsSynBdNtpStatus 
                corrected to have enums not to refer ebs"
            ::= { asSyn 1 }

        
    
--
-- Textual conventions
--
    
        AsSynBdNtpStatus ::= TEXTUAL-CONVENTION
            STATUS current
            DESCRIPTION 
                "The current state of the BS clock set as a result of NTP responses received"
            SYNTAX INTEGER
                {
                ntpStatusNoError(0),
                ntpStatusClockNotSet(1)
                }

        AsSynBdGpsStsLock ::= TEXTUAL-CONVENTION
            STATUS current
            DESCRIPTION 
                "Defines the current state of GPS signal lock."
            SYNTAX INTEGER
                {
                statusGpsLockNone(0),
                statusGpsLockLocked(1),
                statusGpsLockLost(2)
                }

        AsSynBdGpsStsSnr ::= TEXTUAL-CONVENTION
            STATUS current
            DESCRIPTION 
                "Defines the current state of GPS snr."
            SYNTAX INTEGER
                {
                statusGpsSnrNone(0),
                statusGpsSnrNormal(1),
                statusGpsSnrLow(2)
                }

        AsSynBdGpsAlarms ::= TEXTUAL-CONVENTION
            STATUS current
            DESCRIPTION 
                "Description."
            SYNTAX BITS
                {
                alarmInitWarmUp(0),
                alarmAntenna(1),
                alarmGpsTiming(2),
                alarmSnRange(3),
                alarmNoLock(4)
                }

    
--
-- Node definitions
--
    
        -- 1.3.6.1.4.1.989.1.23.1.1
        asSynBdConformance OBJECT IDENTIFIER ::= { asSynBd 1 }

        
        -- 1.3.6.1.4.1.989.1.23.1.1.1
        asSynBdCompliance MODULE-COMPLIANCE
            STATUS current
            DESCRIPTION 
                "Description."
            MODULE -- this module
                MANDATORY-GROUPS { asSynBdObjectGroup }
            ::= { asSynBdConformance 1 }

        
        -- 1.3.6.1.4.1.989.1.23.1.1.2
        asSynBdObjectGroup OBJECT-GROUP
            OBJECTS { asSynBdIndex, asSynBdGpsInstance, asSynBdStackStatusOperationalStatus, asSynBdStackStatusOperationalStatusInfo, asSynBdStackCfgResetRequest, 
                asSynBdStackStatusNtpStatus, asSynBdStackStatusNtpStatusInfo, asSynBdSectorCfgDummyObject, asSynBdGpsStsNumVisibleSatellites, asSynBdGpsStsNumTrackedSatellites, 
                asSynBdGpsStsLatitude, asSynBdGpsStsLongitude, asSynBdGpsStsHeight, asSynBdGpsStsAlarms, asSynBdGpsStsModuleType, 
                asSynBdGpsCfgResetGps, asSynBdNtpServerIpAddressType, asSynBdNtpServerIpAddress, asSynBdNtpServerRowStatus, asSynBdGpsStsLock, 
                asSynBdGpsStsSnr, asSynBdGpsLockChangeTrapEnabled, asSynBdGpsSnrChangeTrapEnabled, asSynBdSectorStatusDummyObject, asSynBdStackCfgOperationalStatus, 
                asSynBdOperationalStatusChangedTrapEnabled, asSynBdStackCfgUseNtp, asSynBdNtpStatusChangedTrapEnabled }
            STATUS current
            DESCRIPTION 
                "Description."
            ::= { asSynBdConformance 2 }

        
        -- 1.3.6.1.4.1.989.1.23.1.1.3
        asSynBdNotificationGroup NOTIFICATION-GROUP
            NOTIFICATIONS { asSynBdOperationalStatusChangedTrap, asSynBdGpsLockChangeTrap, asSynBdGpsSnrChangeTrap, asSynBdGpsAlarmsChangeTrap, asSynBdNtpStatusChangedTrap
                 }
            STATUS current
            DESCRIPTION 
                "Description."
            ::= { asSynBdConformance 3 }

        
        -- 1.3.6.1.4.1.989.1.23.1.2
        asSynBdNotifications OBJECT IDENTIFIER ::= { asSynBd 2 }

        
        -- 1.3.6.1.4.1.989.1.23.1.2.0
        asSynBdTrapPrefix OBJECT IDENTIFIER ::= { asSynBdNotifications 0 }

        
        -- 1.3.6.1.4.1.989.1.23.1.2.0.1
        asSynBdOperationalStatusChangedTrap NOTIFICATION-TYPE
            OBJECTS { asSynBdStackStatusOperationalStatus, asSynBdStackStatusOperationalStatusInfo }
            STATUS current
            DESCRIPTION 
                "Signifies that Board stack operational status has changed."
            ::= { asSynBdTrapPrefix 1 }

        
        -- 1.3.6.1.4.1.989.1.23.1.2.0.2
        asSynBdGpsLockChangeTrap NOTIFICATION-TYPE
            OBJECTS { asSynBdGpsStsLock }
            STATUS current
            DESCRIPTION 
                "Trap signifies GPS has lost or recovered timing lock with satellite(s)."
            ::= { asSynBdTrapPrefix 2 }

        
        -- 1.3.6.1.4.1.989.1.23.1.2.0.3
        asSynBdGpsSnrChangeTrap NOTIFICATION-TYPE
            OBJECTS { asSynBdGpsStsSnr }
            STATUS current
            DESCRIPTION 
                "Trap sent each time the value of asSynBdGpsStsGpsSnr changes indicating 
                that GPS antenna signal SNR is out of range."
            ::= { asSynBdTrapPrefix 3 }

        
        -- 1.3.6.1.4.1.989.1.23.1.2.0.4
        asSynBdGpsAlarmsChangeTrap NOTIFICATION-TYPE
            OBJECTS { asSynBdGpsStsAlarms }
            STATUS current
            DESCRIPTION 
                "Trap sent each time the value of  asSynBdGpsAlarms changes.
                For some bits of status register the alarm should be raised by EMS."
            ::= { asSynBdTrapPrefix 4 }

        
        -- 1.3.6.1.4.1.989.1.23.1.2.0.5
        asSynBdNtpStatusChangedTrap NOTIFICATION-TYPE
            OBJECTS { asSynBdStackStatusNtpStatus, asSynBdStackStatusNtpStatusInfo }
            STATUS current
            DESCRIPTION 
                "Trap signifying a change in the status of the BS clock deduced from NTP responses."
            ::= { asSynBdTrapPrefix 5 }

        
        -- 1.3.6.1.4.1.989.1.23.1.2.1
        asSynBdTrapControlTable OBJECT-TYPE
            SYNTAX SEQUENCE OF AsSynBdTrapControlEntry
            MAX-ACCESS not-accessible
            STATUS current
            DESCRIPTION
                "Defines enabled/disabled controls for each traps independently. 
                The traps are enabled/disabled simulanously across the all cells/sectors of the stack."
            ::= { asSynBdNotifications 1 }

        
        -- 1.3.6.1.4.1.989.1.23.1.2.1.1
        asSynBdTrapControlEntry OBJECT-TYPE
            SYNTAX AsSynBdTrapControlEntry
            MAX-ACCESS not-accessible
            STATUS current
            DESCRIPTION
                "Single row."
            INDEX { asSynBdTrapControlIndex }
            ::= { asSynBdTrapControlTable 1 }

        
        AsSynBdTrapControlEntry ::=
            SEQUENCE { 
                asSynBdTrapControlIndex
                    INTEGER,
                asSynBdOperationalStatusChangedTrapEnabled
                    AsCmnTcBooleanSwitch,
                asSynBdNtpStatusChangedTrapEnabled
                    AsCmnTcBooleanSwitch
             }

        -- 1.3.6.1.4.1.989.1.23.1.2.1.1.1
        asSynBdTrapControlIndex OBJECT-TYPE
            SYNTAX INTEGER (1)
            MAX-ACCESS not-accessible
            STATUS current
            DESCRIPTION
                "Arbitrary index - one row only."
            ::= { asSynBdTrapControlEntry 1 }

        
        -- 1.3.6.1.4.1.989.1.23.1.2.1.1.2
        asSynBdOperationalStatusChangedTrapEnabled OBJECT-TYPE
            SYNTAX AsCmnTcBooleanSwitch
            MAX-ACCESS read-write
            STATUS current
            DESCRIPTION
                "Enables/disables the Board Stack Operational Status change Trap"
            DEFVAL { booleanTrue }
            ::= { asSynBdTrapControlEntry 2 }

        
        -- 1.3.6.1.4.1.989.1.23.1.2.1.1.3
        asSynBdNtpStatusChangedTrapEnabled OBJECT-TYPE
            SYNTAX AsCmnTcBooleanSwitch
            MAX-ACCESS read-write
            STATUS current
            DESCRIPTION
                "Enables/disables the NTP Status Change Trap"
            DEFVAL { booleanTrue }
            ::= { asSynBdTrapControlEntry 3 }

        
        -- 1.3.6.1.4.1.989.1.23.1.2.2
        asSynBdGpsTrapControlTable OBJECT-TYPE
            SYNTAX SEQUENCE OF AsSynBdGpsTrapControlEntry
            MAX-ACCESS not-accessible
            STATUS current
            DESCRIPTION
                "Defines enabled/disabled controls for each traps independently. 
                The traps are enabled/disabled simulanously across the all cells/sectors of the stack."
            ::= { asSynBdNotifications 2 }

        
        -- 1.3.6.1.4.1.989.1.23.1.2.2.1
        asSynBdGpsTrapControlEntry OBJECT-TYPE
            SYNTAX AsSynBdGpsTrapControlEntry
            MAX-ACCESS not-accessible
            STATUS current
            DESCRIPTION
                "Single row."
            INDEX { asSynBdGpsInstance }
            ::= { asSynBdGpsTrapControlTable 1 }

        
        AsSynBdGpsTrapControlEntry ::=
            SEQUENCE { 
                asSynBdGpsLockChangeTrapEnabled
                    AsCmnTcBooleanSwitch,
                asSynBdGpsSnrChangeTrapEnabled
                    AsCmnTcBooleanSwitch
             }

        -- 1.3.6.1.4.1.989.1.23.1.2.2.1.1
        asSynBdGpsLockChangeTrapEnabled OBJECT-TYPE
            SYNTAX AsCmnTcBooleanSwitch
            MAX-ACCESS read-write
            STATUS current
            DESCRIPTION
                "Enables/disables GpsLockChangeTrap."
            DEFVAL { booleanTrue }
            ::= { asSynBdGpsTrapControlEntry 1 }

        
        -- 1.3.6.1.4.1.989.1.23.1.2.2.1.2
        asSynBdGpsSnrChangeTrapEnabled OBJECT-TYPE
            SYNTAX AsCmnTcBooleanSwitch
            MAX-ACCESS read-write
            STATUS current
            DESCRIPTION
                "Enables/disables GpsSnrChangeTrap."
            DEFVAL { booleanTrue }
            ::= { asSynBdGpsTrapControlEntry 2 }

        
        -- 1.3.6.1.4.1.989.1.23.1.3
        asSynBdDevice OBJECT IDENTIFIER ::= { asSynBd 3 }

        
        -- 1.3.6.1.4.1.989.1.23.1.3.1
        asSynBdStackCfgTable OBJECT-TYPE
            SYNTAX SEQUENCE OF AsSynBdStackCfgEntry
            MAX-ACCESS not-accessible
            STATUS current
            DESCRIPTION
                "Table grouping per iBridge stack configuration properties."
            ::= { asSynBdDevice 1 }

        
        -- 1.3.6.1.4.1.989.1.23.1.3.1.1
        asSynBdStackCfgEntry OBJECT-TYPE
            SYNTAX AsSynBdStackCfgEntry
            MAX-ACCESS not-accessible
            STATUS current
            DESCRIPTION
                "Description."
            INDEX { asSynBdIndex }
            ::= { asSynBdStackCfgTable 1 }

        
        AsSynBdStackCfgEntry ::=
            SEQUENCE { 
                asSynBdIndex
                    Integer32,
                asSynBdStackCfgResetRequest
                    AsCmnTcResetCmd,
                asSynBdStackCfgOperationalStatus
                    AsCmnTcOperationalStatus,
                asSynBdStackCfgUseNtp
                    AsCmnTcBooleanSwitch
             }

        -- 1.3.6.1.4.1.989.1.23.1.3.1.1.1
        asSynBdIndex OBJECT-TYPE
            SYNTAX Integer32 (1)
            MAX-ACCESS accessible-for-notify
            STATUS current
            DESCRIPTION
                "Arbitrary index - only one instance ever."
            ::= { asSynBdStackCfgEntry 1 }

        
        -- 1.3.6.1.4.1.989.1.23.1.3.1.1.2
        asSynBdStackCfgResetRequest OBJECT-TYPE
            SYNTAX AsCmnTcResetCmd
            MAX-ACCESS read-write
            STATUS current
            DESCRIPTION
                "Request to reset the stack"
            DEFVAL { resetCmdIdle }
            ::= { asSynBdStackCfgEntry 2 }

        
        -- 1.3.6.1.4.1.989.1.23.1.3.1.1.3
        asSynBdStackCfgOperationalStatus OBJECT-TYPE
            SYNTAX AsCmnTcOperationalStatus
            MAX-ACCESS read-write
            STATUS current
            DESCRIPTION
                "The requested operational status for the stack."
            DEFVAL { operationalStatusOutOfService }
            ::= { asSynBdStackCfgEntry 3 }

        
        -- 1.3.6.1.4.1.989.1.23.1.3.1.1.4
        asSynBdStackCfgUseNtp OBJECT-TYPE
            SYNTAX AsCmnTcBooleanSwitch
            MAX-ACCESS read-write
            STATUS current
            DESCRIPTION
                "Use NTP to set and maintain the date and time.."
            DEFVAL { booleanFalse }
            ::= { asSynBdStackCfgEntry 4 }

        
        -- 1.3.6.1.4.1.989.1.23.1.3.2
        asSynBdStackStatusTable OBJECT-TYPE
            SYNTAX SEQUENCE OF AsSynBdStackStatusEntry
            MAX-ACCESS not-accessible
            STATUS current
            DESCRIPTION
                "Table grouping per iBridge stack status properties."
            ::= { asSynBdDevice 2 }

        
        -- 1.3.6.1.4.1.989.1.23.1.3.2.1
        asSynBdStackStatusEntry OBJECT-TYPE
            SYNTAX AsSynBdStackStatusEntry
            MAX-ACCESS not-accessible
            STATUS current
            DESCRIPTION
                "Description."
            INDEX { asSynBdIndex }
            ::= { asSynBdStackStatusTable 1 }

        
        AsSynBdStackStatusEntry ::=
            SEQUENCE { 
                asSynBdStackStatusOperationalStatus
                    AsCmnTcOperationalStatus,
                asSynBdStackStatusOperationalStatusInfo
                    DisplayString,
                asSynBdStackStatusNtpStatus
                    AsSynBdNtpStatus,
                asSynBdStackStatusNtpStatusInfo
                    DisplayString
             }

        -- 1.3.6.1.4.1.989.1.23.1.3.2.1.1
        asSynBdStackStatusOperationalStatus OBJECT-TYPE
            SYNTAX AsCmnTcOperationalStatus
            MAX-ACCESS read-only
            STATUS current
            DESCRIPTION
                "The current operational status for the iBridge stack."
            ::= { asSynBdStackStatusEntry 1 }

        
        -- 1.3.6.1.4.1.989.1.23.1.3.2.1.2
        asSynBdStackStatusOperationalStatusInfo OBJECT-TYPE
            SYNTAX DisplayString
            MAX-ACCESS read-only
            STATUS current
            DESCRIPTION
                "Provides further information on the iBridge Stack Operational Status"
            ::= { asSynBdStackStatusEntry 2 }

        
        -- 1.3.6.1.4.1.989.1.23.1.3.2.1.3
        asSynBdStackStatusNtpStatus OBJECT-TYPE
            SYNTAX AsSynBdNtpStatus
            MAX-ACCESS read-only
            STATUS current
            DESCRIPTION
                "Reports the current state of the BS clock set as a result of NTP responses received."
            ::= { asSynBdStackStatusEntry 3 }

        
        -- 1.3.6.1.4.1.989.1.23.1.3.2.1.4
        asSynBdStackStatusNtpStatusInfo OBJECT-TYPE
            SYNTAX DisplayString
            MAX-ACCESS read-only
            STATUS current
            DESCRIPTION
                "Further textual string reporting the current state of the BS clock set as a result of NTP responses received."
            ::= { asSynBdStackStatusEntry 4 }

        
        -- 1.3.6.1.4.1.989.1.23.1.4
        asSynBdIf OBJECT IDENTIFIER ::= { asSynBd 4 }

        
        -- 1.3.6.1.4.1.989.1.23.1.4.1
        asSynBdSectorCfgTable OBJECT-TYPE
            SYNTAX SEQUENCE OF AsSynBdSectorCfgEntry
            MAX-ACCESS not-accessible
            STATUS current
            DESCRIPTION
                "Table grouping per iBridge cell configuration properties."
            ::= { asSynBdIf 1 }

        
        -- 1.3.6.1.4.1.989.1.23.1.4.1.1
        asSynBdSectorCfgEntry OBJECT-TYPE
            SYNTAX AsSynBdSectorCfgEntry
            MAX-ACCESS not-accessible
            STATUS current
            DESCRIPTION
                "Description."
            INDEX { ifIndex }
            ::= { asSynBdSectorCfgTable 1 }

        
        AsSynBdSectorCfgEntry ::=
            SEQUENCE { 
                asSynBdSectorCfgDummyObject
                    Integer32
             }

        -- 1.3.6.1.4.1.989.1.23.1.4.1.1.1
        asSynBdSectorCfgDummyObject OBJECT-TYPE
            SYNTAX Integer32
            MAX-ACCESS read-write
            STATUS current
            DESCRIPTION
                "Replace with first real object in this table"
            ::= { asSynBdSectorCfgEntry 1 }

        
        -- 1.3.6.1.4.1.989.1.23.1.4.2
        asSynBdSectorStatusTable OBJECT-TYPE
            SYNTAX SEQUENCE OF AsSynBdSectorStatusEntry
            MAX-ACCESS not-accessible
            STATUS current
            DESCRIPTION
                "Description."
            ::= { asSynBdIf 2 }

        
        -- 1.3.6.1.4.1.989.1.23.1.4.2.1
        asSynBdSectorStatusEntry OBJECT-TYPE
            SYNTAX AsSynBdSectorStatusEntry
            MAX-ACCESS not-accessible
            STATUS current
            DESCRIPTION
                "Description."
            INDEX { ifIndex }
            ::= { asSynBdSectorStatusTable 1 }

        
        AsSynBdSectorStatusEntry ::=
            SEQUENCE { 
                asSynBdSectorStatusDummyObject
                    Integer32
             }

        -- 1.3.6.1.4.1.989.1.23.1.4.2.1.1
        asSynBdSectorStatusDummyObject OBJECT-TYPE
            SYNTAX Integer32
            MAX-ACCESS read-only
            STATUS current
            DESCRIPTION
                "Replace with first real object in this table"
            ::= { asSynBdSectorStatusEntry 1 }

        
        -- 1.3.6.1.4.1.989.1.23.1.5
        asSynBdGps OBJECT IDENTIFIER ::= { asSynBd 5 }

        
        -- 1.3.6.1.4.1.989.1.23.1.5.1
        asSynBdGpsStsTable OBJECT-TYPE
            SYNTAX SEQUENCE OF AsSynBdGpsStsEntry
            MAX-ACCESS not-accessible
            STATUS current
            DESCRIPTION
                "Reports status of GPS receiver."
            ::= { asSynBdGps 1 }

        
        -- 1.3.6.1.4.1.989.1.23.1.5.1.1
        asSynBdGpsStsEntry OBJECT-TYPE
            SYNTAX AsSynBdGpsStsEntry
            MAX-ACCESS not-accessible
            STATUS current
            DESCRIPTION
                "Each row reports a status of an instance of GPS receiver (normally
                only one instance present).
                General parameters in this table are shared by all types of GPS modules.
                Refer to corresponding specific table for those parameters for other types of GPS modules."
            INDEX { asSynBdGpsInstance }
            ::= { asSynBdGpsStsTable 1 }

        
        AsSynBdGpsStsEntry ::=
            SEQUENCE { 
                asSynBdGpsInstance
                    INTEGER,
                asSynBdGpsStsLock
                    AsSynBdGpsStsLock,
                asSynBdGpsStsSnr
                    AsSynBdGpsStsSnr,
                asSynBdGpsStsNumVisibleSatellites
                    INTEGER,
                asSynBdGpsStsNumTrackedSatellites
                    INTEGER,
                asSynBdGpsStsLatitude
                    INTEGER,
                asSynBdGpsStsLongitude
                    INTEGER,
                asSynBdGpsStsHeight
                    INTEGER,
                asSynBdGpsStsAlarms
                    AsSynBdGpsAlarms,
                asSynBdGpsStsModuleType
                    INTEGER
             }

        -- 1.3.6.1.4.1.989.1.23.1.5.1.1.1
        asSynBdGpsInstance OBJECT-TYPE
            SYNTAX INTEGER (1..255)
            MAX-ACCESS accessible-for-notify
            STATUS current
            DESCRIPTION
                "Identifies instance of GPS device (normally only one instance-row 
                expected), used as an index to GPS configuation and status tables."
            ::= { asSynBdGpsStsEntry 1 }

        
        -- 1.3.6.1.4.1.989.1.23.1.5.1.1.2
        asSynBdGpsStsLock OBJECT-TYPE
            SYNTAX AsSynBdGpsStsLock
            MAX-ACCESS read-only
            STATUS current
            DESCRIPTION
                "Defines the current state of GPS signal lock."
            ::= { asSynBdGpsStsEntry 2 }

        
        -- 1.3.6.1.4.1.989.1.23.1.5.1.1.3
        asSynBdGpsStsSnr OBJECT-TYPE
            SYNTAX AsSynBdGpsStsSnr
            MAX-ACCESS read-only
            STATUS current
            DESCRIPTION
                "Defines the current state of GPS snr."
            ::= { asSynBdGpsStsEntry 3 }

        
        -- 1.3.6.1.4.1.989.1.23.1.5.1.1.4
        asSynBdGpsStsNumVisibleSatellites OBJECT-TYPE
            SYNTAX INTEGER (0..12)
            MAX-ACCESS read-only
            STATUS current
            DESCRIPTION
                "Number of visible satellites."
            DEFVAL { 0 }
            ::= { asSynBdGpsStsEntry 4 }

        
        -- 1.3.6.1.4.1.989.1.23.1.5.1.1.5
        asSynBdGpsStsNumTrackedSatellites OBJECT-TYPE
            SYNTAX INTEGER (0..8)
            MAX-ACCESS read-only
            STATUS current
            DESCRIPTION
                "Number of tracked satellites."
            DEFVAL { 0 }
            ::= { asSynBdGpsStsEntry 5 }

        
        -- 1.3.6.1.4.1.989.1.23.1.5.1.1.6
        asSynBdGpsStsLatitude OBJECT-TYPE
            SYNTAX INTEGER (-900000..900000)
            UNITS "ddmmss"
            MAX-ACCESS read-only
            STATUS current
            DESCRIPTION
                "Latitude represented in +/- ddmmss"
            DEFVAL { 0 }
            ::= { asSynBdGpsStsEntry 6 }

        
        -- 1.3.6.1.4.1.989.1.23.1.5.1.1.7
        asSynBdGpsStsLongitude OBJECT-TYPE
            SYNTAX INTEGER (-1800000..1800000)
            UNITS "dddmmss"
            MAX-ACCESS read-only
            STATUS current
            DESCRIPTION
                "Longitude represented in +/- dddmmss"
            DEFVAL { 0 }
            ::= { asSynBdGpsStsEntry 7 }

        
        -- 1.3.6.1.4.1.989.1.23.1.5.1.1.8
        asSynBdGpsStsHeight OBJECT-TYPE
            SYNTAX INTEGER (-100000..999999)
            UNITS "cm"
            MAX-ACCESS read-only
            STATUS current
            DESCRIPTION
                "Height in centimetres"
            DEFVAL { 0 }
            ::= { asSynBdGpsStsEntry 8 }

        
        -- 1.3.6.1.4.1.989.1.23.1.5.1.1.9
        asSynBdGpsStsAlarms OBJECT-TYPE
            SYNTAX AsSynBdGpsAlarms
            MAX-ACCESS read-only
            STATUS current
            DESCRIPTION
                "Returns current status of GPS-SB. It includes the alarms information
                ALARMS: for each bit, '0' means alarm condition not active 
                while '1' means alarm condition active
                "
            ::= { asSynBdGpsStsEntry 9 }

        
        -- 1.3.6.1.4.1.989.1.23.1.5.1.1.10
        asSynBdGpsStsModuleType OBJECT-TYPE
            SYNTAX INTEGER { condorGpsModule(0) }
            MAX-ACCESS read-only
            STATUS current
            DESCRIPTION
                "Module type as one of the enumerated ones.
                By default, it is assumed as Condor. 
                This enumeration matches definition in IIB."
            ::= { asSynBdGpsStsEntry 10 }

        
        -- 1.3.6.1.4.1.989.1.23.1.5.2
        asSynBdGpsCfgTable OBJECT-TYPE
            SYNTAX SEQUENCE OF AsSynBdGpsCfgEntry
            MAX-ACCESS not-accessible
            STATUS current
            DESCRIPTION
                "Configures GPS configuration."
            ::= { asSynBdGps 2 }

        
        -- 1.3.6.1.4.1.989.1.23.1.5.2.1
        asSynBdGpsCfgEntry OBJECT-TYPE
            SYNTAX AsSynBdGpsCfgEntry
            MAX-ACCESS not-accessible
            STATUS current
            DESCRIPTION
                "GPS configuration."
            INDEX { asSynBdGpsInstance }
            ::= { asSynBdGpsCfgTable 1 }

        
        AsSynBdGpsCfgEntry ::=
            SEQUENCE { 
                asSynBdGpsCfgResetGps
                    AsCmnTcBooleanSwitch
             }

        -- 1.3.6.1.4.1.989.1.23.1.5.2.1.1
        asSynBdGpsCfgResetGps OBJECT-TYPE
            SYNTAX AsCmnTcBooleanSwitch
            MAX-ACCESS read-write
            STATUS current
            DESCRIPTION
                "Set to TRUE to force reset of GPS module."
            DEFVAL { booleanFalse }
            ::= { asSynBdGpsCfgEntry 1 }

        
        -- 1.3.6.1.4.1.989.1.23.1.6
        asSynBdMisc OBJECT IDENTIFIER ::= { asSynBd 6 }

        
        -- 1.3.6.1.4.1.989.1.23.1.6.1
        asSynBdNtpServerTable OBJECT-TYPE
            SYNTAX SEQUENCE OF AsSynBdNtpServerEntry
            MAX-ACCESS not-accessible
            STATUS current
            DESCRIPTION
                "Table containing the NTP Server definitions to be configured on the basestation."
            ::= { asSynBdMisc 1 }

        
        -- 1.3.6.1.4.1.989.1.23.1.6.1.1
        asSynBdNtpServerEntry OBJECT-TYPE
            SYNTAX AsSynBdNtpServerEntry
            MAX-ACCESS not-accessible
            STATUS current
            DESCRIPTION
                "Description."
            INDEX { asSynBdNtpServerId }
            ::= { asSynBdNtpServerTable 1 }

        
        AsSynBdNtpServerEntry ::=
            SEQUENCE { 
                asSynBdNtpServerId
                    Integer32,
                asSynBdNtpServerIpAddressType
                    InetAddressType,
                asSynBdNtpServerIpAddress
                    InetAddress,
                asSynBdNtpServerRowStatus
                    RowStatus
             }

        -- 1.3.6.1.4.1.989.1.23.1.6.1.1.1
        asSynBdNtpServerId OBJECT-TYPE
            SYNTAX Integer32 (1..2147483647)
            MAX-ACCESS not-accessible
            STATUS current
            DESCRIPTION
                "Arbitrary index for entry in NTP server table. "
            ::= { asSynBdNtpServerEntry 1 }

        
        -- 1.3.6.1.4.1.989.1.23.1.6.1.1.2
        asSynBdNtpServerIpAddressType OBJECT-TYPE
            SYNTAX InetAddressType
            MAX-ACCESS read-create
            STATUS current
            DESCRIPTION
                "The type of IP address of the NTP Server."
            DEFVAL { ipv4 }
            ::= { asSynBdNtpServerEntry 2 }

        
        -- 1.3.6.1.4.1.989.1.23.1.6.1.1.3
        asSynBdNtpServerIpAddress OBJECT-TYPE
            SYNTAX InetAddress
            MAX-ACCESS read-create
            STATUS current
            DESCRIPTION
                "IP address of the NTP server."
            DEFVAL { "0.0.0.0" }
            ::= { asSynBdNtpServerEntry 3 }

        
        -- 1.3.6.1.4.1.989.1.23.1.6.1.1.4
        asSynBdNtpServerRowStatus OBJECT-TYPE
            SYNTAX RowStatus
            MAX-ACCESS read-create
            STATUS current
            DESCRIPTION
                "Handles Row Creation/ Deletion in the table."
            ::= { asSynBdNtpServerEntry 4 }

        
    
    END

--
-- ASSYN-BOARD-MIB.mib
--
