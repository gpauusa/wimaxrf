--
-- AIRSPAN-BS-HMAX-MIB.mib
-- MIB generated by MG-SOFT Visual MIB Builder Version 5.0  Build 250
-- Monday, December 17, 2007 at 10:18:49
--

	AIRSPAN-BS-HMAX-MIB DEFINITIONS ::= BEGIN
 
		IMPORTS
			AsmaxBooleanSwitch			
				FROM AIRSPAN-ASMAX-COMMON-MIB			
			asMaxBS			
				FROM AIRSPAN-PRODUCTS-MIB			
			ifIndex			
				FROM IF-MIB			
			OBJECT-GROUP			
				FROM SNMPv2-CONF			
			Integer32, OBJECT-TYPE, MODULE-IDENTITY			
				FROM SNMPv2-SMI			
			DisplayString			
				FROM SNMPv2-TC;
	
	
		-- 1.3.6.1.4.1.989.1.16.2.2
		asMaxBSHiperMax MODULE-IDENTITY 
			LAST-UPDATED "200606161636Z"		-- June 16, 2006 at 16:36 GMT
			ORGANIZATION 
				"Airspan Communications Ltd"
			CONTACT-INFO 
				"Contact-info."
			DESCRIPTION 
				"MIB module with objects specific to HiperMax product. 
				This MIB is normally implemented by SDR ATCA blade.
				"
			REVISION "200606161636Z"		-- June 16, 2006 at 16:36 GMT
			DESCRIPTION 
				"Pre-draft
				- Initial with GPS connectivity configuration"
			REVISION "200609141518Z"		-- September 14, 2006 at 15:18 GMT
			DESCRIPTION 
				"Pre-draft
				- Changed default to True for PrimaryMasterManageGps
				- Added IPMC firmware version to inventory
				- Added Front/rear Traffic port setting"
			REVISION "200609201213Z"		-- September 20, 2006 at 12:13 GMT
			DESCRIPTION 
				"Draft 1 (SR3.0)
				- Moved Front/Back Panel traffic route to Inventory Table as RO"
			REVISION "200711121200Z"		-- November 12, 2007 at 12:00 GMT
			DESCRIPTION 
				"Draft 2:
				- reference to draft1 removed."
			REVISION "200712171016Z"		-- December 17, 2007 at 10:16 GMT
			DESCRIPTION 
				"Draft 3:
				- Changed ashmaxAtcaBladeShelfId from read-only to read-write
				- Added ashmaxAtcaBladeShelfManagerFitted
				- Added ashmaxAtcaBladeShelfSize"
			::= { asMaxBS 2 }

		
	
	
--
-- Node definitions
--
	
		-- 1.3.6.1.4.1.989.1.16.2.2.1
		ashmaxConformance OBJECT IDENTIFIER ::= { asMaxBSHiperMax 1 }

		
		-- 1.3.6.1.4.1.989.1.16.2.2.1.1
		ashmaxConfigurationGroup OBJECT-GROUP
			OBJECTS { ashmaxAtcaBladeHardwareAddress, ashmaxAtcaBladeSiteNumber, ashmaxAtcaBladeSiteType, ashmaxAtcaBladeShelfId, ashmaxAtcaBladeClockSynchronisationRole, 
				ashmaxAtcaBladeIpmcFirmwareVersion, ashmaxAtcaBladeTrafficRoute, ashmaxAtcaBladeCfgPrimaryMasterManageGps, ashmaxAtcaBladeCfgSecondaryMasterManageGps, ashmaxAtcaBladeShelfManagerFitted, 
				ashmaxAtcaBladeShelfSize }
			STATUS current
			DESCRIPTION 
				"Description."
			::= { ashmaxConformance 1 }

		
		-- 1.3.6.1.4.1.989.1.16.2.2.2
		ashmaxNotifications OBJECT IDENTIFIER ::= { asMaxBSHiperMax 2 }

		
		-- 1.3.6.1.4.1.989.1.16.2.2.3
		ashmaxDevice OBJECT IDENTIFIER ::= { asMaxBSHiperMax 3 }

		
		-- 1.3.6.1.4.1.989.1.16.2.2.3.1
		ashmaxAtcaBladeInventoryTable OBJECT-TYPE
			SYNTAX SEQUENCE OF AshmaxAtcaBladeInventoryEntry
			MAX-ACCESS not-accessible
			STATUS current
			DESCRIPTION
				"Table reports inventory like information for self-identification of SDR blade 
				inside ATCA rack."
			::= { ashmaxDevice 1 }

		
		-- 1.3.6.1.4.1.989.1.16.2.2.3.1.1
		ashmaxAtcaBladeInventoryEntry OBJECT-TYPE
			SYNTAX AshmaxAtcaBladeInventoryEntry
			MAX-ACCESS not-accessible
			STATUS current
			DESCRIPTION
				"Description."
			INDEX { ashmaxAtcaBladeIndex }
			::= { ashmaxAtcaBladeInventoryTable 1 }

		
		AshmaxAtcaBladeInventoryEntry ::=
			SEQUENCE { 
				ashmaxAtcaBladeIndex
					Integer32,
				ashmaxAtcaBladeHardwareAddress
					Integer32,
				ashmaxAtcaBladeSiteNumber
					Integer32,
				ashmaxAtcaBladeSiteType
					INTEGER,
				ashmaxAtcaBladeShelfId
					DisplayString,
				ashmaxAtcaBladeClockSynchronisationRole
					INTEGER,
				ashmaxAtcaBladeIpmcFirmwareVersion
					DisplayString,
				ashmaxAtcaBladeTrafficRoute
					INTEGER,
				ashmaxAtcaBladeShelfManagerFitted
					AsmaxBooleanSwitch,
				ashmaxAtcaBladeShelfSize
					Integer32
			 }

		-- 1.3.6.1.4.1.989.1.16.2.2.3.1.1.1
		ashmaxAtcaBladeIndex OBJECT-TYPE
			SYNTAX Integer32 (1)
			MAX-ACCESS not-accessible
			STATUS current
			DESCRIPTION
				"Arbitrary index - always = 1. Only one row in this table."
			::= { ashmaxAtcaBladeInventoryEntry 1 }

		
		-- 1.3.6.1.4.1.989.1.16.2.2.3.1.1.2
		ashmaxAtcaBladeHardwareAddress OBJECT-TYPE
			SYNTAX Integer32 (0..255)
			MAX-ACCESS read-only
			STATUS current
			DESCRIPTION
				"ATCA Hardware Address of the SDR Blade"
			::= { ashmaxAtcaBladeInventoryEntry 2 }

		
		-- 1.3.6.1.4.1.989.1.16.2.2.3.1.1.3
		ashmaxAtcaBladeSiteNumber OBJECT-TYPE
			SYNTAX Integer32 (0..255)
			MAX-ACCESS read-only
			STATUS current
			DESCRIPTION
				"ATCA Hardware SDR physical slot e.g Slot 6"
			::= { ashmaxAtcaBladeInventoryEntry 3 }

		
		-- 1.3.6.1.4.1.989.1.16.2.2.3.1.1.4
		ashmaxAtcaBladeSiteType OBJECT-TYPE
			SYNTAX INTEGER { atcaBladeSiteTypeSdr(0) }
			MAX-ACCESS read-only
			STATUS current
			DESCRIPTION
				"Normally enumeration but expected only one value for the moment = 0 (SDR)"
			::= { ashmaxAtcaBladeInventoryEntry 4 }

		
		-- 1.3.6.1.4.1.989.1.16.2.2.3.1.1.5
		ashmaxAtcaBladeShelfId OBJECT-TYPE
			SYNTAX DisplayString
			MAX-ACCESS read-write
			STATUS current
			DESCRIPTION
				"Shelf address string intended to reflect the physical location of the shelf"
			::= { ashmaxAtcaBladeInventoryEntry 5 }

		
		-- 1.3.6.1.4.1.989.1.16.2.2.3.1.1.6
		ashmaxAtcaBladeClockSynchronisationRole OBJECT-TYPE
			SYNTAX INTEGER
				{
				clockSyncRolePrimaryMaster(0),
				clockSyncRoleSecondaryMaster(1),
				clockSyncRoleSlave(2)
				}
			MAX-ACCESS read-only
			STATUS current
			DESCRIPTION
				"Defines the clock Synchronisaton role off the ATCA SDR Blade.
				It maps directly to the blade address as follows:
				Primary Master(0) : Hardware Address 0x43
				Secondary Master(1) : Hardware Address 0x44
				Slave(2) : Hardware address anything other than 0x43 or 0x44
				"
			::= { ashmaxAtcaBladeInventoryEntry 6 }

		
		-- 1.3.6.1.4.1.989.1.16.2.2.3.1.1.7
		ashmaxAtcaBladeIpmcFirmwareVersion OBJECT-TYPE
			SYNTAX DisplayString
			MAX-ACCESS read-only
			STATUS current
			DESCRIPTION
				"Intelligent Platform Management Controller firmware version"
			::= { ashmaxAtcaBladeInventoryEntry 7 }

		
		-- 1.3.6.1.4.1.989.1.16.2.2.3.1.1.8
		ashmaxAtcaBladeTrafficRoute OBJECT-TYPE
			SYNTAX INTEGER
				{
				viaFrontPanel(0),
				viaPrimaryBackplane(1),
				viaSecondaryBackplane(2)
				}
			MAX-ACCESS read-only
			STATUS current
			DESCRIPTION
				"Identifies the current configuration for HiperMAX traffic routing."
			::= { ashmaxAtcaBladeInventoryEntry 8 }

		
		-- 1.3.6.1.4.1.989.1.16.2.2.3.1.1.9
		ashmaxAtcaBladeShelfManagerFitted OBJECT-TYPE
			SYNTAX AsmaxBooleanSwitch
			MAX-ACCESS read-write
			STATUS current
			DESCRIPTION
				"Indicates whether the shelf is fitted with a shelf manager."
			DEFVAL { booleanTrue }
			::= { ashmaxAtcaBladeInventoryEntry 9 }

		
		-- 1.3.6.1.4.1.989.1.16.2.2.3.1.1.10
		ashmaxAtcaBladeShelfSize OBJECT-TYPE
			SYNTAX Integer32 (1..20)
			MAX-ACCESS read-write
			STATUS current
			DESCRIPTION
				"Number of slots that the shelf contains (5 or 14)."
			::= { ashmaxAtcaBladeInventoryEntry 10 }

		
		-- 1.3.6.1.4.1.989.1.16.2.2.3.2
		ashmaxAtcaBladeConfigTable OBJECT-TYPE
			SYNTAX SEQUENCE OF AshmaxAtcaBladeConfigEntry
			MAX-ACCESS not-accessible
			STATUS current
			DESCRIPTION
				"Contains blade configuration objects."
			::= { ashmaxDevice 2 }

		
		-- 1.3.6.1.4.1.989.1.16.2.2.3.2.1
		ashmaxAtcaBladeConfigEntry OBJECT-TYPE
			SYNTAX AshmaxAtcaBladeConfigEntry
			MAX-ACCESS not-accessible
			STATUS current
			DESCRIPTION
				"Description."
			INDEX { ashmaxAtcaBladeIndex }
			::= { ashmaxAtcaBladeConfigTable 1 }

		
		AshmaxAtcaBladeConfigEntry ::=
			SEQUENCE { 
				ashmaxAtcaBladeCfgPrimaryMasterManageGps
					AsmaxBooleanSwitch,
				ashmaxAtcaBladeCfgSecondaryMasterManageGps
					AsmaxBooleanSwitch
			 }

		-- 1.3.6.1.4.1.989.1.16.2.2.3.2.1.1
		ashmaxAtcaBladeCfgPrimaryMasterManageGps OBJECT-TYPE
			SYNTAX AsmaxBooleanSwitch
			MAX-ACCESS read-write
			STATUS current
			DESCRIPTION
				"Instructs SDR blade to manage(booleanTrue)/not manage(booleanFalse) 
				the connected GPS if it is inserted in the primary master position 
				in the shelf.
				"
			DEFVAL { booleanTrue }
			::= { ashmaxAtcaBladeConfigEntry 1 }

		
		-- 1.3.6.1.4.1.989.1.16.2.2.3.2.1.2
		ashmaxAtcaBladeCfgSecondaryMasterManageGps OBJECT-TYPE
			SYNTAX AsmaxBooleanSwitch
			MAX-ACCESS read-write
			STATUS current
			DESCRIPTION
				"Instructs SDR blade to manage(booleanTrue)/not manage(booleanFalse) 
				the connected GPS if it is inserted in the secondary master position 
				in the shelf.
				"
			DEFVAL { booleanTrue }
			::= { ashmaxAtcaBladeConfigEntry 2 }

		
	
	END

--
-- AIRSPAN-BS-HMAX-MIB.mib
--
