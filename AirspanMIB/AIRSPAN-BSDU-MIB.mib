--
-- AIRSPAN-BSDU-MIB.mib
-- MIB generated by MG-SOFT Visual MIB Builder Version 5.0  Build 250
-- Friday, May 18, 2007 at 11:07:37
--

	AIRSPAN-BSDU-MIB DEFINITIONS ::= BEGIN
 
		IMPORTS
			asMax			
				FROM AIRSPAN-PRODUCTS-MIB			
			ifIndex			
				FROM IF-MIB			
			InetAddressType, InetAddress			
				FROM INET-ADDRESS-MIB			
			OBJECT-GROUP, NOTIFICATION-GROUP			
				FROM SNMPv2-CONF			
			OBJECT-TYPE, MODULE-IDENTITY, NOTIFICATION-TYPE			
				FROM SNMPv2-SMI			
			DisplayString, RowStatus, MacAddress			
				FROM SNMPv2-TC			
			WmanIfBsIdType			
				FROM WMAN-IF-MIB;
	
	
		-- 1.3.6.1.4.1.989.1.16.4
		asMaxBSDU MODULE-IDENTITY 
			LAST-UPDATED "200705011037Z"		-- May 01, 2007 at 10:37 GMT
			ORGANIZATION 
				"Airspan Communications Ltd"
			CONTACT-INFO 
				"www.airspan.com"
			DESCRIPTION 
				"Module defines management objects for BSDU equipment."
			REVISION "200704131700Z"		-- April 13, 2007 at 17:00 GMT
			DESCRIPTION 
				"Draft 1
				- initial"
			REVISION "200704171500Z"		-- April 17, 2007 at 15:00 GMT
			DESCRIPTION 
				"Draft 2:
				Corrections following review.
				- asBsduBsPortIndex replaced with ifIndex
				- new objects: asBsduBsPortStatusPowerState, asBsduBsPortStatusBsid
				- changed enumeration and access for asBsduBsPortStatusConnectionState (separated power status)
				- changed name prefixes of the objects of table asBsduSnmpTrapDestTable to match the table name prefix
				- added trap asBsduBsPortPowerStateChanedTrap"
			REVISION "200705011037Z"		-- May 01, 2007 at 10:37 GMT
			DESCRIPTION 
				"Draft 3:
				- asBsduBsPortStatusPowerState extended."
			::= { asMax 4 }

		
	
	
--
-- Node definitions
--
	
		-- 1.3.6.1.4.1.989.1.16.4.1
		asBsduConformance OBJECT IDENTIFIER ::= { asMaxBSDU 1 }

		
		-- 1.3.6.1.4.1.989.1.16.4.1.1
		asBsduObjectGroup OBJECT-GROUP
			OBJECTS { asBsduBsPortStatusConnectionState, asBsduBsPortStatusBsIpAddressType, asBsduBsPortStatusBsIpAddress, asBsduBsPortStatusBsMacAddress, asBsduBsPortStatusBsid, 
				asBsduBsPortStatusPowerState, asBsduBsPortStatusBsProductType, asBsduSnmpV1V2TrapDestAddrType, asBsduSnmpV1V2TrapDestAddress, asBsduSnmpV1V2TrapDestPort, 
				asBsduSnmpTrapDestDescription, asBsduSnmpTrapDestRowStatus }
			STATUS current
			DESCRIPTION 
				"Description."
			::= { asBsduConformance 1 }

		
		-- 1.3.6.1.4.1.989.1.16.4.1.2
		asBsduNotificationGroup NOTIFICATION-GROUP
			NOTIFICATIONS { asBsduBsPortStateChangedTrap, asBsduBsPortPowerStateChangedTrap }
			STATUS current
			DESCRIPTION 
				"Description."
			::= { asBsduConformance 2 }

		
		-- 1.3.6.1.4.1.989.1.16.4.2
		asBsduNotification OBJECT IDENTIFIER ::= { asMaxBSDU 2 }

		
-- Special object identifier to make trap definitions V1 compliant.
		-- 1.3.6.1.4.1.989.1.16.4.2.0
		asBsduTrapPrefix OBJECT IDENTIFIER ::= { asBsduNotification 0 }

		
		-- 1.3.6.1.4.1.989.1.16.4.2.0.1
		asBsduBsPortStateChangedTrap NOTIFICATION-TYPE
			OBJECTS { asBsduBsPortStatusConnectionState, asBsduBsPortStatusBsIpAddressType, asBsduBsPortStatusBsIpAddress, asBsduBsPortStatusBsMacAddress, asBsduBsPortStatusBsProductType, 
				ifIndex }
			STATUS current
			DESCRIPTION 
				"Sent when asBsduBsPortStatusConnectionState changes or when BS, conencted to the port has changed
				changed. The change of connected BS normally should by reported by sending 2 traps:
				- first for old BS with state not connected
				- second for new BS with state connected
				Fast changes of connected BS are normally identified by change in reported MAC address."
			::= { asBsduTrapPrefix 1 }

		
		-- 1.3.6.1.4.1.989.1.16.4.2.0.2
		asBsduBsPortPowerStateChangedTrap NOTIFICATION-TYPE
			OBJECTS { ifIndex, asBsduBsPortStatusPowerState }
			STATUS current
			DESCRIPTION 
				"Sent when power state changes as defined by object asBsduBsPortStatusPowerState. 
				This trap may be used by manager to generate a power failure alarm."
			::= { asBsduTrapPrefix 2 }

		
		-- 1.3.6.1.4.1.989.1.16.4.2.1
		asBsduSnmpTrapDestTable OBJECT-TYPE
			SYNTAX SEQUENCE OF AsBsduSnmpTrapDestEntry
			MAX-ACCESS not-accessible
			STATUS current
			DESCRIPTION
				"Defines trap destinations."
			::= { asBsduNotification 1 }

		
		-- 1.3.6.1.4.1.989.1.16.4.2.1.1
		asBsduSnmpTrapDestEntry OBJECT-TYPE
			SYNTAX AsBsduSnmpTrapDestEntry
			MAX-ACCESS not-accessible
			STATUS current
			DESCRIPTION
				"Description."
			INDEX { asBsduSnmpTrapDestIndex }
			::= { asBsduSnmpTrapDestTable 1 }

		
		AsBsduSnmpTrapDestEntry ::=
			SEQUENCE { 
				asBsduSnmpTrapDestIndex
					INTEGER,
				asBsduSnmpV1V2TrapDestAddrType
					InetAddressType,
				asBsduSnmpV1V2TrapDestAddress
					InetAddress,
				asBsduSnmpV1V2TrapDestPort
					INTEGER,
				asBsduSnmpTrapDestDescription
					DisplayString,
				asBsduSnmpTrapDestRowStatus
					RowStatus
			 }

		-- 1.3.6.1.4.1.989.1.16.4.2.1.1.1
		asBsduSnmpTrapDestIndex OBJECT-TYPE
			SYNTAX INTEGER (1..8)
			MAX-ACCESS not-accessible
			STATUS current
			DESCRIPTION
				"Index to trap destination table."
			::= { asBsduSnmpTrapDestEntry 1 }

		
		-- 1.3.6.1.4.1.989.1.16.4.2.1.1.2
		asBsduSnmpV1V2TrapDestAddrType OBJECT-TYPE
			SYNTAX InetAddressType
			MAX-ACCESS read-create
			STATUS current
			DESCRIPTION
				"The type of IP address used in the object
				asdmaxSnmpV1V2TrapDestAddress."
			DEFVAL { ipv4 }
			::= { asBsduSnmpTrapDestEntry 2 }

		
		-- 1.3.6.1.4.1.989.1.16.4.2.1.1.3
		asBsduSnmpV1V2TrapDestAddress OBJECT-TYPE
			SYNTAX InetAddress
			MAX-ACCESS read-create
			STATUS current
			DESCRIPTION
				"IP address of SNMP manager configured as a trap
				destination for versions V1 and V2 of SNMP. If this object
				is not created or empty the traps are not sent."
			DEFVAL { "" }
			::= { asBsduSnmpTrapDestEntry 3 }

		
		-- 1.3.6.1.4.1.989.1.16.4.2.1.1.4
		asBsduSnmpV1V2TrapDestPort OBJECT-TYPE
			SYNTAX INTEGER (0..65535)
			MAX-ACCESS read-create
			STATUS current
			DESCRIPTION
				"Port number of SNMP manager configured as a trap
				destination for versions V1 and V2 of SNMP."
			DEFVAL { 0 }
			::= { asBsduSnmpTrapDestEntry 4 }

		
		-- 1.3.6.1.4.1.989.1.16.4.2.1.1.5
		asBsduSnmpTrapDestDescription OBJECT-TYPE
			SYNTAX DisplayString
			MAX-ACCESS read-create
			STATUS current
			DESCRIPTION
				"Text describing the manager configured to receive traps.
				This object is for information purposes only. It can for example
				say 'Netspan @Netview'."
			::= { asBsduSnmpTrapDestEntry 5 }

		
		-- 1.3.6.1.4.1.989.1.16.4.2.1.1.6
		asBsduSnmpTrapDestRowStatus OBJECT-TYPE
			SYNTAX RowStatus
			MAX-ACCESS read-create
			STATUS current
			DESCRIPTION
				"Description."
			::= { asBsduSnmpTrapDestEntry 6 }

		
		-- 1.3.6.1.4.1.989.1.16.4.3
		asBsduBsPortStatusTable OBJECT-TYPE
			SYNTAX SEQUENCE OF AsBsduBsPortStatusEntry
			MAX-ACCESS not-accessible
			STATUS current
			DESCRIPTION
				"State reporting table for BS port.
				The table is indexed by ifIndex. Only interfaces used for BS connection
				should have a row in this table.
				ifIndex is also used in this case as a port identifier."
			REFERENCE
				"WiMAX BSDU, Network topology: BS discovery - Top level design"
			::= { asMaxBSDU 3 }

		
		-- 1.3.6.1.4.1.989.1.16.4.3.1
		asBsduBsPortStatusEntry OBJECT-TYPE
			SYNTAX AsBsduBsPortStatusEntry
			MAX-ACCESS not-accessible
			STATUS current
			DESCRIPTION
				"Description."
			INDEX { ifIndex }
			::= { asBsduBsPortStatusTable 1 }

		
		AsBsduBsPortStatusEntry ::=
			SEQUENCE { 
				asBsduBsPortStatusPowerState
					INTEGER,
				asBsduBsPortStatusConnectionState
					INTEGER,
				asBsduBsPortStatusBsIpAddressType
					InetAddressType,
				asBsduBsPortStatusBsIpAddress
					InetAddress,
				asBsduBsPortStatusBsMacAddress
					MacAddress,
				asBsduBsPortStatusBsProductType
					DisplayString,
				asBsduBsPortStatusBsid
					WmanIfBsIdType
			 }

		-- 1.3.6.1.4.1.989.1.16.4.3.1.1
		asBsduBsPortStatusPowerState OBJECT-TYPE
			SYNTAX INTEGER
				{
				powerStateDisabled(0),
				powerStateOk(1),
				powerStateFailed(2)
				}
			MAX-ACCESS read-only
			STATUS current
			DESCRIPTION
				"Reports the state of power line for each BS port."
			::= { asBsduBsPortStatusEntry 1 }

		
		-- 1.3.6.1.4.1.989.1.16.4.3.1.2
		asBsduBsPortStatusConnectionState OBJECT-TYPE
			SYNTAX INTEGER
				{
				bsPortConnStateNotMonitored(1),
				bsPortConnStateUnknown(2),
				bsPortConnStateErroneous(3),
				bsPortConnStateConnected(4)
				}
			MAX-ACCESS read-only
			STATUS current
			DESCRIPTION
				"The state of the connection on the BS port."
			::= { asBsduBsPortStatusEntry 2 }

		
		-- 1.3.6.1.4.1.989.1.16.4.3.1.3
		asBsduBsPortStatusBsIpAddressType OBJECT-TYPE
			SYNTAX InetAddressType
			MAX-ACCESS read-only
			STATUS current
			DESCRIPTION
				"The type of IP address of the connected BS discovered automatically by BSDU."
			::= { asBsduBsPortStatusEntry 3 }

		
		-- 1.3.6.1.4.1.989.1.16.4.3.1.4
		asBsduBsPortStatusBsIpAddress OBJECT-TYPE
			SYNTAX InetAddress
			MAX-ACCESS read-only
			STATUS current
			DESCRIPTION
				"IP address of the connected BS discovered automatically by BSDU."
			::= { asBsduBsPortStatusEntry 4 }

		
		-- 1.3.6.1.4.1.989.1.16.4.3.1.5
		asBsduBsPortStatusBsMacAddress OBJECT-TYPE
			SYNTAX MacAddress
			MAX-ACCESS read-only
			STATUS current
			DESCRIPTION
				"MAC address of the connected BS discovered automatically by BSDU."
			::= { asBsduBsPortStatusEntry 5 }

		
		-- 1.3.6.1.4.1.989.1.16.4.3.1.6
		asBsduBsPortStatusBsProductType OBJECT-TYPE
			SYNTAX DisplayString
			MAX-ACCESS read-only
			STATUS current
			DESCRIPTION
				"Product type reported by connected BS."
			::= { asBsduBsPortStatusEntry 6 }

		
		-- 1.3.6.1.4.1.989.1.16.4.3.1.7
		asBsduBsPortStatusBsid OBJECT-TYPE
			SYNTAX WmanIfBsIdType
			MAX-ACCESS read-only
			STATUS current
			DESCRIPTION
				"Description."
			::= { asBsduBsPortStatusEntry 7 }

		
	
	END

--
-- AIRSPAN-BSDU-MIB.mib
--
