--
-- AIRSPAN-OIDS-MIB.mib
-- MIB generated by MG-SOFT Visual MIB Builder Version 5.0  Build 250
-- Friday, November 23, 2007 at 17:09:22
--

	AIRSPAN-OIDS-MIB DEFINITIONS ::= BEGIN
 
		IMPORTS
			airspan			
				FROM AIRSPAN-MIB			
			MODULE-IDENTITY			
				FROM SNMPv2-SMI;
	
	
		-- 1.3.6.1.4.1.989.2
		airspanOIDs MODULE-IDENTITY 
			LAST-UPDATED "201103160941Z"		-- March 16, 2011 at 09:41 GMT
			ORGANIZATION 
				"Airspan Networks, Inc."
			CONTACT-INFO 
				"kdudzins@airspan.com"
			DESCRIPTION 
				"This module defines the object identifiers that are
				assigned to various Airspan software platforms, and hence are
				returned as values for sysObjectID"
			REVISION "200708211128Z"		-- August 21, 2007 at 11:28 GMT
			DESCRIPTION 
				"Draft 1:
				- started revision history
				- oid for eBsTrx added."
			REVISION "200711231704Z"		-- November 23, 2007 at 17:04 GMT
			DESCRIPTION 
				"Draft 2
				- added OID for ASMAX Netspan"
			REVISION "201103150941Z"		-- March 15, 2011 at 09:41 GMT
			DESCRIPTION 
				"Draft 3
				- added OIDs for airspanAsLte, airspanAsLteSyn, airspanAsLte4G, airspanAsBrd and airspanAsIb"
			REVISION "201103160941Z"		-- March 16, 2011 at 09:41 GMT
			DESCRIPTION 
				"Draft 4
				- Restructured to replace Lte, Brd and Ib subtrees with airspanAsSyn and airspanAs4G subtrees"
			::= { airspan 2 }

		
	
--
-- Node definitions
--
	
		-- 1.3.6.1.4.1.989.2.1
		airspanASWipLL OBJECT IDENTIFIER ::= { airspanOIDs 1 }

		
--  ASWipLL Node System Object ID
		-- 1.3.6.1.4.1.989.2.11
		airspanNetspan OBJECT IDENTIFIER ::= { airspanOIDs 11 }

		
		-- 1.3.6.1.4.1.989.2.15
		airspanAsMaxNetspan OBJECT IDENTIFIER ::= { airspanOIDs 15 }

		
--  AS8200 Netspan SNMP agent's System Object ID
		-- 1.3.6.1.4.1.989.2.16
		airspanAsMax OBJECT IDENTIFIER ::= { airspanOIDs 16 }

		
--  Root for AsMax family of equipment
		-- 1.3.6.1.4.1.989.2.16.1
		airspanAsMaxBsdu OBJECT IDENTIFIER ::= { airspanAsMax 1 }

		
		-- 1.3.6.1.4.1.989.2.16.2
		airspanAsMaxEbsTrx OBJECT IDENTIFIER ::= { airspanAsMax 2 }

		
		-- 1.3.6.1.4.1.989.2.17
		airspanAsNet OBJECT IDENTIFIER ::= { airspanOIDs 17 }

		
--  Root for AS.NET familiy of equipment
		-- 1.3.6.1.4.1.989.2.18
		airspanVoiceMax OBJECT IDENTIFIER ::= { airspanOIDs 18 }


--  Root for Multi-stack AirSynergy SNMP agents
		-- 1.3.6.1.4.1.989.2.20
		airspanAsSyn OBJECT IDENTIFIER ::= { airspanOIDs 20 }


--  SNMP Agent supporting Board functionality
		-- 1.3.6.1.4.1.989.2.20.1
		airspanAsSynBoard OBJECT IDENTIFIER ::= { airspanAsSyn 1 }


--  SNMP Agent supporting LTE functionality
		-- 1.3.6.1.4.1.989.2.20.2
		airspanAsSynLte OBJECT IDENTIFIER ::= { airspanAsSyn 2 }


--  SNMP Agent supporting iBridge Feeder Terminal functionality
		-- 1.3.6.1.4.1.989.2.20.3
		airspanAsSynFt OBJECT IDENTIFIER ::= { airspanAsSyn 3 }


--  SNMP Agent supporting iBridge Feeder Base functionality
		-- 1.3.6.1.4.1.989.2.20.4
		airspanAsSynFb OBJECT IDENTIFIER ::= { airspanAsSyn 4 }


--  SNMP Agent supporting 16e functionality
		-- 1.3.6.1.4.1.989.2.20.4
		airspanAsSyn16e OBJECT IDENTIFIER ::= { airspanAsSyn 5 }


--  SNMP Agent supporting 16d functionality
		-- 1.3.6.1.4.1.989.2.20.4
		airspanAsSyn16d OBJECT IDENTIFIER ::= { airspanAsSyn 6 }


--  Root for Multi-stack Air4G SNMP agents
		-- 1.3.6.1.4.1.989.2.21
		airspanAs4G OBJECT IDENTIFIER ::= { airspanOIDs 21 }


--  SNMP Agent supporting LTE functionality
		-- 1.3.6.1.4.1.989.2.21.1
		airspanAs4GLte OBJECT IDENTIFIER ::= { airspanAs4G 1 }


--  Root for VoiceMax family of equipment
		-- 1.3.6.1.4.1.989.2.3030
		airspanAS3030 OBJECT IDENTIFIER ::= { airspanOIDs 3030 }

		
--  AS3030 PTP Node System Object ID
		-- 1.3.6.1.4.1.989.2.3031
		airspanAS3030PMP OBJECT IDENTIFIER ::= { airspanOIDs 3031 }

		
--  AS3030 PMP Node System Object ID
		-- 1.3.6.1.4.1.989.2.3032
		airspanAS3030E1T1 OBJECT IDENTIFIER ::= { airspanOIDs 3032 }

		
--  AS3030 E1T1 Node System Object ID
		-- 1.3.6.1.4.1.989.2.4030
		airspanAS4030 OBJECT IDENTIFIER ::= { airspanOIDs 4030 }

		
--  AS4030 Basestation Node System Object ID
		-- 1.3.6.1.4.1.989.2.4031
		airspanAS4030SS OBJECT IDENTIFIER ::= { airspanOIDs 4031 }
	
	END
--  AS4030 Subscriber Station Node System Object ID

--
-- AIRSPAN-OIDS-MIB.mib
--
