--
-- ASCMN-SW-MIB.mib
-- MIB generated by MG-SOFT Visual MIB Builder 2010 Version 8.0  Build 400
-- Wednesday, March 16, 2011 at 23:12:45
--

	ASCMN-SW-MIB DEFINITIONS ::= BEGIN
 
		IMPORTS
			asCmn			
				FROM AIRSPAN-PRODUCTS-MIB			
			AsCmnTcSoftwareType			
				FROM ASCMN-TC-MIB			
			ifIndex			
				FROM IF-MIB			
			InetAddressType, InetAddress			
				FROM INET-ADDRESS-MIB			
			OBJECT-GROUP, MODULE-COMPLIANCE			
				FROM SNMPv2-CONF			
			Integer32, OBJECT-TYPE, MODULE-IDENTITY			
				FROM SNMPv2-SMI			
			DisplayString			
				FROM SNMPv2-TC;
	
	
		-- 1.3.6.1.4.1.989.1.22.2
		asCmnSw MODULE-IDENTITY 
			LAST-UPDATED "201103162141Z"		-- March 16, 2011 at 21:41 GMT
			ORGANIZATION 
				"Airspan Communications Ltd"
			CONTACT-INFO 
				"kdudzins@airspan.com"
			DESCRIPTION 
				"Propriatory MIB to support software download to Airspan platforms"
			REVISION "201103162141Z"		-- March 16, 2011 at 21:41 GMT
			DESCRIPTION 
				"Pre-Draft 2:
				- split SwUpgrade table into separate Config and Status tables
				            updated Syntax to use Integer32"
			REVISION "201103150941Z"		-- March 15, 2011 at 09:41 GMT
			DESCRIPTION 
				"Pre-Draft 1:
				- initial version "
			::= { asCmn 2 }

		
	
	
--
-- Node definitions
--
	
		-- 1.3.6.1.4.1.989.1.22.2.1
		asCmnSwConformance OBJECT IDENTIFIER ::= { asCmnSw 1 }

		
		-- 1.3.6.1.4.1.989.1.22.2.1.1
		asCmnSwCompliance MODULE-COMPLIANCE
			STATUS current
			DESCRIPTION 
				"Description."
			MODULE -- this module
				MANDATORY-GROUPS { asCmnSwObjectGroup }
			::= { asCmnSwConformance 1 }

		
		-- 1.3.6.1.4.1.989.1.22.2.1.2
		asCmnSwObjectGroup OBJECT-GROUP
			OBJECTS { asCmnSwCfgCommand, asCmnSwCfgFileToInstall, asCmnSwCfgFileServerAddrType, asCmnSwCfgFileServerAddr, asCmnSwCfgVersionToBecomePrimary, 
				asCmnSwCfgServerType, asCmnSwCfgServerUserName, asCmnSwCfgServerPassword, asCmnSwStsStatusCode, asCmnSwStsStatusString, 
				asCmnSwStsProgress, asCmnSwStsPrimaryVersion, asCmnSwStsPrimaryVersionDetails, asCmnSwStsSecondaryVersion, asCmnSwStsSecondaryVersionDetails, 
				asCmnSwStsTypeDescription, asCmnSwStsRunningVersion, asCmnSwStsRunningVersionDetails }
			STATUS current
			DESCRIPTION 
				"Description."
			::= { asCmnSwConformance 2 }

		
		-- 1.3.6.1.4.1.989.1.22.2.2
		asCmnSwCfgTable OBJECT-TYPE
			SYNTAX SEQUENCE OF AsCmnSwCfgEntry
			MAX-ACCESS not-accessible
			STATUS current
			DESCRIPTION
				"Table responsible for configuring software download to Airspan products."
			::= { asCmnSw 2 }

		
		-- 1.3.6.1.4.1.989.1.22.2.2.1
		asCmnSwCfgEntry OBJECT-TYPE
			SYNTAX AsCmnSwCfgEntry
			MAX-ACCESS not-accessible
			STATUS current
			DESCRIPTION
				"Description."
			INDEX { asCmnSwType }
			::= { asCmnSwCfgTable 1 }

		
		AsCmnSwCfgEntry ::=
			SEQUENCE { 
				asCmnSwType
					AsCmnTcSoftwareType,
				asCmnSwCfgCommand
					INTEGER,
				asCmnSwCfgFileToInstall
					DisplayString,
				asCmnSwCfgFileServerAddrType
					InetAddressType,
				asCmnSwCfgFileServerAddr
					InetAddress,
				asCmnSwCfgVersionToBecomePrimary
					DisplayString,
				asCmnSwCfgServerType
					INTEGER,
				asCmnSwCfgServerUserName
					DisplayString,
				asCmnSwCfgServerPassword
					DisplayString
			 }

		-- 1.3.6.1.4.1.989.1.22.2.2.1.1
		asCmnSwType OBJECT-TYPE
			SYNTAX AsCmnTcSoftwareType
			MAX-ACCESS not-accessible
			STATUS current
			DESCRIPTION
				"Identifies the type of image or image package to install. 
				Different types may require different implementation
				of the upgrade process.
				'swTypeOs' is typically a maintenance operation 
				used in exceptional circumstance and by default doesn't 
				have the standby storage."
			::= { asCmnSwCfgEntry 1 }

		
		-- 1.3.6.1.4.1.989.1.22.2.2.1.2
		asCmnSwCfgCommand OBJECT-TYPE
			SYNTAX INTEGER
				{
				swCommandIdle(0),
				swCommandAbort(1),
				swCommandInstallOnly(2),
				swCommandSwapToPrimary(3),
				swCommandResetToPrimary(4),
				swCommandSwapAndResetToPrimary(5)
				}
			MAX-ACCESS read-write
			STATUS current
			DESCRIPTION
				"Object carries request to initiate a part of upgrate process as follows:
				- swCommandIdle - no action
				- swCommandAbort - aborts any upgrade operation reported 
				  as failed or in progress.
				- swCommandInstallOnly - instructs target to download and store 
				  the file from the file server. The file to install is identified 
				  by object 'asdmaxSwCfgFileToInstall'. The newly installed file version 
				  is reported in 'asCmnSwSecondaryVersion' object.
				- swCommandSwapToPrimary - instructs the target to swap versions in the storage
				  such that the version of primary storage (asCmnSwPrimaryVersion) matches 
				  the version set in object 'asCmnSwCfgVersionToBecomePrimary'. 
				  If primary storage already contains requested version no action is required.
				- swCommandResetToPrimary - instructs the target to auto-reset in order to
				  change running version to match the primary storage version. The reported 
				  running version (asCmnSwRunningVersion) should change as a result.
				- swCommandSwapAndResetToPrimary - instructs the target to execute the command
				  swCommandSwapToPrimary and subsequently the command swCommandResetToPrimary
				  as one atomic operation. All objects reporting versions should be updated 
				  accordingly but only after the whole operation is completed.
				This object should be treated as write-only but if read by 
				generic browser it should return always a value of 'swCommandIdle'
				"
			::= { asCmnSwCfgEntry 2 }

		
		-- 1.3.6.1.4.1.989.1.22.2.2.1.3
		asCmnSwCfgFileToInstall OBJECT-TYPE
			SYNTAX DisplayString
			MAX-ACCESS read-write
			STATUS current
			DESCRIPTION
				"The name of the file to install when command 'swCommandInstallOnly' is issued."
			::= { asCmnSwCfgEntry 3 }

		
		-- 1.3.6.1.4.1.989.1.22.2.2.1.4
		asCmnSwCfgFileServerAddrType OBJECT-TYPE
			SYNTAX InetAddressType
			MAX-ACCESS read-write
			STATUS current
			DESCRIPTION
				"Defines the type of 'asCmnSwCfgFileServerAddr'."
			DEFVAL { ipv4 }
			::= { asCmnSwCfgEntry 4 }

		
		-- 1.3.6.1.4.1.989.1.22.2.2.1.5
		asCmnSwCfgFileServerAddr OBJECT-TYPE
			SYNTAX InetAddress
			MAX-ACCESS read-write
			STATUS current
			DESCRIPTION
				"Defines the address of the server the file to install 
				is available to download from."
			::= { asCmnSwCfgEntry 5 }

		
		-- 1.3.6.1.4.1.989.1.22.2.2.1.6
		asCmnSwCfgVersionToBecomePrimary OBJECT-TYPE
			SYNTAX DisplayString
			MAX-ACCESS read-write
			STATUS current
			DESCRIPTION
				"Defines the version of the software to become version of image stored 
				in the primary storage (bank, file etc.). This object is used as an additional
				information for command 'swCommandSwapToPrimary'.
				If the version is not installed i.e. not reported by neither asCmnSwPrimaryVersion
				nor asCmnSwSecondaryVersion the requested operation 
				(swCommandSwapToPrimary, swCommandSwapAndResetToPrimary) should fail 
				and the relevant error code should be reported in 'asCmnSwStatusCode'."
			::= { asCmnSwCfgEntry 6 }

		
		-- 1.3.6.1.4.1.989.1.22.2.2.1.7
		asCmnSwCfgServerType OBJECT-TYPE
			SYNTAX INTEGER
				{
				swServerTypeFtp(1),
				swServerTypeTftp(2)
				}
			MAX-ACCESS read-write
			STATUS current
			DESCRIPTION
				"Defines the type of file server used to install(download) file image.
				FTP server requires user name and password defined by objects 
				asCmnSwServerUserName and asCmnSwServerPassword."
			DEFVAL { swServerTypeTftp }
			::= { asCmnSwCfgEntry 7 }

		
		-- 1.3.6.1.4.1.989.1.22.2.2.1.8
		asCmnSwCfgServerUserName OBJECT-TYPE
			SYNTAX DisplayString
			MAX-ACCESS read-write
			STATUS current
			DESCRIPTION
				"User name is required to open session on file servers with user authentication
				implemented like FTP."
			::= { asCmnSwCfgEntry 8 }

		
		-- 1.3.6.1.4.1.989.1.22.2.2.1.9
		asCmnSwCfgServerPassword OBJECT-TYPE
			SYNTAX DisplayString
			MAX-ACCESS read-write
			STATUS current
			DESCRIPTION
				"Password is required to open session on file servers with user authentication
				implemented like FTP. The password is given for the user specified by object
				asCmnSwServerUserName."
			::= { asCmnSwCfgEntry 9 }

		
		-- 1.3.6.1.4.1.989.1.22.2.3
		asCmnSwStsTable OBJECT-TYPE
			SYNTAX SEQUENCE OF AsCmnSwStsEntry
			MAX-ACCESS not-accessible
			STATUS current
			DESCRIPTION
				"Table responsible for reporting software download details on Airspan products."
			::= { asCmnSw 3 }

		
		-- 1.3.6.1.4.1.989.1.22.2.3.1
		asCmnSwStsEntry OBJECT-TYPE
			SYNTAX AsCmnSwStsEntry
			MAX-ACCESS not-accessible
			STATUS current
			DESCRIPTION
				"Description."
			INDEX { asCmnSwType }
			::= { asCmnSwStsTable 1 }

		
		AsCmnSwStsEntry ::=
			SEQUENCE { 
				asCmnSwStsStatusCode
					INTEGER,
				asCmnSwStsStatusString
					DisplayString,
				asCmnSwStsProgress
					Integer32,
				asCmnSwStsPrimaryVersion
					DisplayString,
				asCmnSwStsPrimaryVersionDetails
					DisplayString,
				asCmnSwStsSecondaryVersion
					DisplayString,
				asCmnSwStsSecondaryVersionDetails
					DisplayString,
				asCmnSwStsTypeDescription
					DisplayString,
				asCmnSwStsRunningVersion
					DisplayString,
				asCmnSwStsRunningVersionDetails
					DisplayString
			 }

		-- 1.3.6.1.4.1.989.1.22.2.3.1.7
		asCmnSwStsStatusCode OBJECT-TYPE
			SYNTAX INTEGER
				{
				swStatusIdle(1),
				swStatusInstallInProgress(2),
				swStatusActivationInProgress(3),
				swStatusInstallFailure(4),
				swStatusActivationFailure(5)
				}
			MAX-ACCESS read-only
			STATUS current
			DESCRIPTION
				"Reported status of the operation in progress. The values 
				of this object mean:
				  swStatusIdle - no operation in progress or last requested 
				operation completed successfully
				  swStatusInstallInProgress - Install operation in progress
				  swStatusActivationInProgress - Activation operation in progress
				  swStatusInstallFailure - Install operation terminated with error
				  swStatusActivationFailure - Activation operation terminated with error where
				activation is the process defined by 3 commands: swCommandSwapToPrimary,
				swCommandResetToPrimary, swCommandSwapAndResetToPrimary
				
				"
			::= { asCmnSwStsEntry 7 }

		
		-- 1.3.6.1.4.1.989.1.22.2.3.1.8
		asCmnSwStsStatusString OBJECT-TYPE
			SYNTAX DisplayString
			MAX-ACCESS read-only
			STATUS current
			DESCRIPTION
				"Implementation specific reporting message. If operation is 
				terminated with an error this object will report error details."
			::= { asCmnSwStsEntry 8 }

		
		-- 1.3.6.1.4.1.989.1.22.2.3.1.9
		asCmnSwStsProgress OBJECT-TYPE
			SYNTAX Integer32 (0..100)
			UNITS "%"
			MAX-ACCESS read-only
			STATUS current
			DESCRIPTION
				"The progress of the operation expressed in %. If exact 
				progress is not available the object should report:
				0% if no operation is in progress
				50% if operation is in progress
				100% when operation is complete
				The progress value can change from non zero value back 
				to zero percent only when the operation has been aborted 
				or when a new operation has been requested by setting 
				the object asdmaxSwCfgCommand.
				"
			::= { asCmnSwStsEntry 9 }

		
		-- 1.3.6.1.4.1.989.1.22.2.3.1.10
		asCmnSwStsPrimaryVersion OBJECT-TYPE
			SYNTAX DisplayString
			MAX-ACCESS read-only
			STATUS current
			DESCRIPTION
				"The version of the software image stored in primary storage (bank, file etc).
				There is no format restriction on reported version.
				Typically the primary software image is stored in FLASH or other non-volatile
				memory."
			::= { asCmnSwStsEntry 10 }

		
		-- 1.3.6.1.4.1.989.1.22.2.3.1.11
		asCmnSwStsPrimaryVersionDetails OBJECT-TYPE
			SYNTAX DisplayString
			MAX-ACCESS read-only
			STATUS current
			DESCRIPTION
				"The details of version of the software image stored in primary 
				storage (bank, file etc). This is implementation specific."
			::= { asCmnSwStsEntry 11 }

		
		-- 1.3.6.1.4.1.989.1.22.2.3.1.12
		asCmnSwStsSecondaryVersion OBJECT-TYPE
			SYNTAX DisplayString
			MAX-ACCESS read-only
			STATUS current
			DESCRIPTION
				"The version of the software image stored in secondary storage (bank, file etc).
				There is no format restriction on reported version.
				Typically the secondary software image is stored in FLASH or other non-volatile
				memory."
			::= { asCmnSwStsEntry 12 }

		
		-- 1.3.6.1.4.1.989.1.22.2.3.1.13
		asCmnSwStsSecondaryVersionDetails OBJECT-TYPE
			SYNTAX DisplayString
			MAX-ACCESS read-only
			STATUS current
			DESCRIPTION
				"The details of version of the software image stored in secondary 
				storage (bank, file etc). This is implementation specific."
			::= { asCmnSwStsEntry 13 }

		
		-- 1.3.6.1.4.1.989.1.22.2.3.1.14
		asCmnSwStsTypeDescription OBJECT-TYPE
			SYNTAX DisplayString
			MAX-ACCESS read-only
			STATUS current
			DESCRIPTION
				"Describes the role of the software type. This object has a free text format
				and is implementation specific. The role of this object is to provide textual 
				definition of the type of the image identified by asCmnSwType code.
				"
			::= { asCmnSwStsEntry 14 }

		
		-- 1.3.6.1.4.1.989.1.22.2.3.1.15
		asCmnSwStsRunningVersion OBJECT-TYPE
			SYNTAX DisplayString
			MAX-ACCESS read-only
			STATUS current
			DESCRIPTION
				"The version of the software the target is now running.
				There is no format restriction on reported version.
				Typically the running software is stored in RAM."
			::= { asCmnSwStsEntry 15 }

		
		-- 1.3.6.1.4.1.989.1.22.2.3.1.16
		asCmnSwStsRunningVersionDetails OBJECT-TYPE
			SYNTAX DisplayString
			MAX-ACCESS read-only
			STATUS current
			DESCRIPTION
				"The details of version of the software the target is now running. 
				This is implementation specific."
			::= { asCmnSwStsEntry 16 }

		
	
	END

--
-- ASCMN-SW-MIB.mib
--
