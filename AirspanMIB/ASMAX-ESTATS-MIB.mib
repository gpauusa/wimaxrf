--
-- ASMAX-ESTATS-MIB.mib
-- MIB generated by MG-SOFT Visual MIB Builder 2010 Version 8.0  Build 400
-- Tuesday, September 27, 2011 at 09:12:18
--

    ASMAX-ESTATS-MIB DEFINITIONS ::= BEGIN
 
        IMPORTS
            asMaxBSCommon            
                FROM AIRSPAN-ASMAX-BS-COMMON-MIB            
            asMaxBS, asMaxBSHiperMax, asMaxBSPicoMax, asMaxBSDemoMax, asMaxBSSoc, 
            asMaxBsStats, asMaxEbs, asMaxEsvc            
                FROM AIRSPAN-PRODUCTS-MIB            
            AsxEbsBsIdType            
                FROM ASMAX-EBS-MIB            
            ifIndex            
                FROM IF-MIB            
            OBJECT-GROUP, MODULE-COMPLIANCE            
                FROM SNMPv2-CONF            
            Integer32, Counter32, Counter64, OBJECT-TYPE, MODULE-IDENTITY            
                FROM SNMPv2-SMI            
            wmanIf2BsSsMacAddress, wmanIf2BsOfdmaUiucIndex, wmanIf2BsOfdmaDiucIndex            
                FROM WMAN-IF2-BS-MIB;
    
    
        -- 1.3.6.1.4.1.989.1.16.2.9
        asMaxEstats MODULE-IDENTITY 
            LAST-UPDATED "200809031034Z"		-- September 03, 2008 at 10:34 GMT
            ORGANIZATION 
                "Airspan Communications Ltd"
            CONTACT-INFO 
                "kdudzins@airspan.com"
            DESCRIPTION 
                "Propriatory MIB for Airspan BS for WiMAX mobile systems.
                This modules covers EBS statistics."
            REVISION "200810011633Z"		-- October 01, 2008 at 16:33 GMT
            DESCRIPTION 
                "Draft2:
                MsRfStats column types changed to Counter32.
                Added Handover stats tables."
            REVISION "200810291436Z"		-- October 29, 2008 at 14:36 GMT
            DESCRIPTION 
                "Draft 3:
                Connection Activity Stats table added"
            REVISION "200903271044Z"		-- March 27, 2009 at 10:44 GMT
            DESCRIPTION 
                "Draft 4:
                - added asxEstatsActiveMsUlBytes
                - added asxEstatsActiveMsDlBytes
                - added descriptions and units to some asxEstatsMsRfStatsTable entries"
            REVISION "200905181028Z"		-- May 18, 2009 at 10:28 GMT
            DESCRIPTION 
                "Draft 5:
                - Added asxEstatsMsUiuc
                - Added asxEstatsMsDiuc
                - Added asxEstatsMsDlZoneIndex
                - Added asxEstatsMsUplinkErroredPackets
                - Added asxEstatsMsMaxUlSubChannels
                - Added asxEstatsMsDynamicDlMatrix"
            REVISION "201008231209Z"		-- August 23, 2010 at 12:09 GMT
            DESCRIPTION 
                "Draft 6:
                - Added asxEstatsSectorTable"
            REVISION "201101270919Z"		-- January 27, 2011 at 09:19 GMT
            DESCRIPTION 
                "Draft 7:
                - Added asxEstatsMsDlCinr
                - Added asxEstatsMsUlTxPower
                - Corrected some asxEstatsMsRfStatsTable OIDs to ro from rw
                - Added asxEstatsSectorUlSubframeUtilization.
                - Added asxEstatsSectorDlSubframeUtilization"
            REVISION "201107251632Z"		-- July 25, 2011 at 16:32 GMT
            DESCRIPTION 
                "Draft 8:
                - Added asxEstatsSectorUlTotalPkts
                - Added asxEstatsSectorStatsTable"
            REVISION "201108181139Z"		-- August 18, 2011 at 11:39 GMT
            DESCRIPTION 
                "Draft 9:
                - Added asxEstatsMsHarqDiuc"
            REVISION "201109270902Z"		-- September 27, 2011 at 09:02 GMT
            DESCRIPTION 
                "Draft 10:
                - Added asxEstatsSectorUlSubFrameSlots
                - Added asxEstatsSectorUsedUlSubFrameSlots
                - Added asxEstatsSectorUlOverheadSlots
                - Added asxEstatsSectorDlSubframeSlots
                - Added asxEstatsSectorUsedDlSubframeSlots
                - Added asxEstatsSectorDlOverheadSlots"
            ::= { asMaxBS 9 }

        
    
    
--
-- Node definitions
--
    
        -- 1.3.6.1.4.1.989.1.16.2.9.1
        asMaxEstatsConformance OBJECT IDENTIFIER ::= { asMaxEstats 1 }

        
        -- 1.3.6.1.4.1.989.1.16.2.9.1.1
        asMaxEstatsCompliance MODULE-COMPLIANCE
            STATUS current
            DESCRIPTION 
                "Description."
            MODULE -- this module
                MANDATORY-GROUPS { asMaxEstatsObjectGroup }
            ::= { asMaxEstatsConformance 1 }

        
        -- 1.3.6.1.4.1.989.1.16.2.9.1.2
        asMaxEstatsObjectGroup OBJECT-GROUP
            OBJECTS { asxEstatsMsDlRssi, asxEstatsMsUlRssi, asxEstatsMsDlCinr1, asxEstatsMsDlCinr3, asxEstatsMsUlCinr, 
                asxEstatsControlledHoIndicator, asxEstatsControlledHoCancel, asxEstatsControlledHoRejection, asxEstatsControlledBsHoRequestTo, asxEstatsControlledHoAttemptTo, 
                asxEstatsControlledHoCompleteTo, asxEstatsHoRequestFrom, asxEstatsHoAttemptFrom, asxEstatsHoCompleteFrom, asxEstatsControlledHoAttemptFrom, 
                asxEstatsControlledHoCompleteFrom, asxEstatsUncontrolledHoAttemptFrom, asxEstatsUncontrolledHoCompleteFrom, asxEstatsControlledMsHoRequestTo, asxEstatsRegisteredMs, 
                asxEstatsRangingAttempt, asxEstatsRangingComplete, asxEstatsIneAttempt, asxEstatsIneComplete, asxEstatsMsInitiatedNxRequest, 
                asxEstatsMsInitiatedNxResponse, asxEstatsActiveMsDlBytes, asxEstatsActiveMsUlBytes, asxEstatsMsUiuc, asxEstatsMsDiuc, 
                asxEstatsMsDlZoneIndex, asxEstatsMsUplinkErroredPackets, asxEstatsMsMaxUlSubChannels, asxEstatsMsDynamicDlMatrix, asxEstatsSectorUlErrorPkts, 
                asxEstatsSectorUlPkts, asxEstatsSectorUlBytes, asxEstatsSectorDlPkts, asxEstatsSectorDlBytes, asxEstatsSectorHarqUlBursts, 
                asxEstatsSectorHarqUlAcks, asxEstatsSectorHarqUlNacks, asxEstatsSectorHarqDlBursts, asxEstatsSectorHarqDlAcks, asxEstatsSectorHarqDlNacks, 
                asxEstatsSectorArqUlBlocks, asxEstatsSectorArqUlRetrans, asxEstatsSectorArqUlDiscards, asxEstatsSectorArqDlBlocks, asxEstatsSectorArqDlRetrans, 
                asxEstatsSectorArqDlAcks, asxEstatsSectorArqDlNacks, asxEstatsSectorIdleModeEntryReq, asxEstatsSectorIdleModeEntryRsp, asxEstatsSectorIdleModeExitAttempt, 
                asxEstatsSectorIdleModeExitSuccess, asxEstatsSectorLocUpdAttempt, asxEstatsSectorLocUpdComplete, asxEstatsSectorLocUpdFail, asxEstatsMsDlCinr, 
                asxEstatsMsUlTxPower, asxEstatsSectorUlSubframeUtilization, asxEstatsSectorDlSubframeUtilization, asxEstatsSectorUlTotalPkts, asxESectorStatsNoiseLevelLowCounter, 
                asxESectorStatsNoiseLevelMedCounter, asxESectorStatsNoiseLevelHighCounter, asxESectorStatsDlSlotsAtQpsk12rep6, asxESectorStatsDlSlotsAtQpsk12rep4, asxESectorStatsDlSlotsAtQpsk12rep2, 
                asxESectorStatsDlSlotsAtQpsk12, asxESectorStatsDlSlotsAtQpsk34, asxESectorStatsDlSlotsAt16QAM12, asxESectorStatsDlSlotsAt16QAM34, asxESectorStatsDlSlotsAt64QAM12, 
                asxESectorStatsDlSlotsAt64QAM23, asxESectorStatsDlSlotsAt64QAM34, asxESectorStatsDlSlotsAt64QAM56, asxESectorStatsUlSlotsAtQpsk12rep6, asxESectorStatsUlSlotsAtQpsk12rep4, 
                asxESectorStatsUlSlotsAtQpsk12rep2, asxESectorStatsUlSlotsAtQpsk12, asxESectorStatsUlSlotsAtQpsk34, asxESectorStatsUlSlotsAt16QAM12, asxESectorStatsUlSlotsAt16QAM34, 
                asxESectorStatsUlSlotsAt64QAM12, asxESectorStatsUlSlotsAt64QAM23, asxESectorStatsUlSlotsAt64QAM34, asxESectorStatsUlSlotsAt64QAM56, asxEstatsMsDrop, 
                asxEstatsNwInitiatedNxRequest, asxEstatsNwInitiatedNxResponse, asxEstatsSectorUlSubFrameSlots, asxEstatsSectorUsedUlSubFrameSlots, asxEstatsSectorUlOverheadSlots, 
                asxEstatsSectorDlSubframeSlots, asxEstatsSectorUsedDlSubframeSlots, asxEstatsSectorDlOverheadSlots, asxEstatsNwInitiatedNxReject, asxEstatsMsHarqDiuc
                 }
            STATUS current
            DESCRIPTION 
                "Description."
            ::= { asMaxEstatsConformance 2 }

        
        -- 1.3.6.1.4.1.989.1.16.2.9.2
        asxEstatsMsRfStatusTable OBJECT-TYPE
            SYNTAX SEQUENCE OF AsxEstatsMsRfStatusEntry
            MAX-ACCESS not-accessible
            STATUS current
            DESCRIPTION
                "Status table to report Ms Rf statuses."
            ::= { asMaxEstats 2 }

        
        -- 1.3.6.1.4.1.989.1.16.2.9.2.1
        asxEstatsMsRfStatusEntry OBJECT-TYPE
            SYNTAX AsxEstatsMsRfStatusEntry
            MAX-ACCESS not-accessible
            STATUS current
            DESCRIPTION
                "Description."
            INDEX { ifIndex, wmanIf2BsSsMacAddress }
            ::= { asxEstatsMsRfStatusTable 1 }

        
        AsxEstatsMsRfStatusEntry ::=
            SEQUENCE { 
                asxEstatsMsDlRssi
                    Integer32,
                asxEstatsMsUlRssi
                    Integer32,
                asxEstatsMsDlCinr1
                    Counter32,
                asxEstatsMsDlCinr3
                    Counter32,
                asxEstatsMsUlCinr
                    Counter32,
                asxEstatsMsUiuc
                    Integer32,
                asxEstatsMsDiuc
                    Integer32,
                asxEstatsMsDlZoneIndex
                    Integer32,
                asxEstatsMsUplinkErroredPackets
                    Counter32,
                asxEstatsMsMaxUlSubChannels
                    Integer32,
                asxEstatsMsDynamicDlMatrix
                    INTEGER,
                asxEstatsMsDlCinr
                    Integer32,
                asxEstatsMsUlTxPower
                    Integer32,
                asxEstatsMsHarqDiuc
                    Integer32
             }

        -- 1.3.6.1.4.1.989.1.16.2.9.2.1.1
        asxEstatsMsDlRssi OBJECT-TYPE
            SYNTAX Integer32
            MAX-ACCESS read-only
            STATUS current
            DESCRIPTION
                "The filtered RSSI reading for this SS."
            DEFVAL { 0 }
            ::= { asxEstatsMsRfStatusEntry 1 }

        
        -- 1.3.6.1.4.1.989.1.16.2.9.2.1.2
        asxEstatsMsUlRssi OBJECT-TYPE
            SYNTAX Integer32
            MAX-ACCESS read-only
            STATUS current
            DESCRIPTION
                "Description."
            ::= { asxEstatsMsRfStatusEntry 2 }

        
        -- 1.3.6.1.4.1.989.1.16.2.9.2.1.3
        asxEstatsMsDlCinr1 OBJECT-TYPE
            SYNTAX Counter32
            UNITS "0.25dB"
            MAX-ACCESS read-only
            STATUS current
            DESCRIPTION
                "The most recent downlink preamble physical CINR for reuse 1."
            ::= { asxEstatsMsRfStatusEntry 3 }

        
        -- 1.3.6.1.4.1.989.1.16.2.9.2.1.4
        asxEstatsMsDlCinr3 OBJECT-TYPE
            SYNTAX Counter32
            UNITS "0.25dB"
            MAX-ACCESS read-only
            STATUS current
            DESCRIPTION
                "The most recent downlink preamble physical CINR for reuse 3."
            ::= { asxEstatsMsRfStatusEntry 4 }

        
        -- 1.3.6.1.4.1.989.1.16.2.9.2.1.5
        asxEstatsMsUlCinr OBJECT-TYPE
            SYNTAX Counter32
            UNITS "0.25dB"
            MAX-ACCESS read-only
            STATUS current
            DESCRIPTION
                "The most recent uplink CINR measurement."
            ::= { asxEstatsMsRfStatusEntry 5 }

        
        -- 1.3.6.1.4.1.989.1.16.2.9.2.1.6
        asxEstatsMsUiuc OBJECT-TYPE
            SYNTAX Integer32 (1..10)
            MAX-ACCESS read-only
            STATUS current
            DESCRIPTION
                "Reports the burst profile currently in use for uplink transmissions by this SS."
            ::= { asxEstatsMsRfStatusEntry 6 }

        
        -- 1.3.6.1.4.1.989.1.16.2.9.2.1.7
        asxEstatsMsDiuc OBJECT-TYPE
            SYNTAX Integer32 (0..12)
            MAX-ACCESS read-only
            STATUS current
            DESCRIPTION
                "Reports the burst profile currently in use for downlink transmissions by this SS."
            ::= { asxEstatsMsRfStatusEntry 7 }

        
        -- 1.3.6.1.4.1.989.1.16.2.9.2.1.8
        asxEstatsMsDlZoneIndex OBJECT-TYPE
            SYNTAX Integer32 (0..2147483647)
            MAX-ACCESS read-only
            STATUS current
            DESCRIPTION
                "Reports the current zone in which downlink transmissions to this SS will occur."
            ::= { asxEstatsMsRfStatusEntry 8 }

        
        -- 1.3.6.1.4.1.989.1.16.2.9.2.1.9
        asxEstatsMsUplinkErroredPackets OBJECT-TYPE
            SYNTAX Counter32
            MAX-ACCESS read-only
            STATUS current
            DESCRIPTION
                "The number of errored uplink packets received by this SS."
            ::= { asxEstatsMsRfStatusEntry 9 }

        
        -- 1.3.6.1.4.1.989.1.16.2.9.2.1.10
        asxEstatsMsMaxUlSubChannels OBJECT-TYPE
            SYNTAX Integer32 (0..2147483647)
            MAX-ACCESS read-only
            STATUS current
            DESCRIPTION
                "Indicates the maximum number of subchannels that an uplink burst from this SS may use.
                A value of 0 inidicates that there is no limit."
            DEFVAL { 0 }
            ::= { asxEstatsMsRfStatusEntry 10 }

        
        -- 1.3.6.1.4.1.989.1.16.2.9.2.1.11
        asxEstatsMsDynamicDlMatrix OBJECT-TYPE
            SYNTAX INTEGER
                {
                matrixA(0),
                matrixB(1)
                }
            MAX-ACCESS read-only
            STATUS current
            DESCRIPTION
                "When dynamic matrix selection is enabled, the currently selected STC Matrix. 0 = MatrixA, 1 = MatrixB."
            ::= { asxEstatsMsRfStatusEntry 11 }

        
        -- 1.3.6.1.4.1.989.1.16.2.9.2.1.12
        asxEstatsMsDlCinr OBJECT-TYPE
            SYNTAX Integer32
            MAX-ACCESS read-only
            STATUS current
            DESCRIPTION
                "Downlink CINR"
            DEFVAL { 0 }
            ::= { asxEstatsMsRfStatusEntry 12 }

        
        -- 1.3.6.1.4.1.989.1.16.2.9.2.1.13
        asxEstatsMsUlTxPower OBJECT-TYPE
            SYNTAX Integer32
            MAX-ACCESS read-only
            STATUS current
            DESCRIPTION
                "Uplink Tx Power"
            DEFVAL { 0 }
            ::= { asxEstatsMsRfStatusEntry 13 }

        
        -- 1.3.6.1.4.1.989.1.16.2.9.2.1.14
        asxEstatsMsHarqDiuc OBJECT-TYPE
            SYNTAX Integer32 (0..12)
            MAX-ACCESS read-only
            STATUS current
            DESCRIPTION
                "Reports the burst profile currently in use for downlink HARQ traffic to this SS."
            DEFVAL { 0 }
            ::= { asxEstatsMsRfStatusEntry 14 }

        
        -- 1.3.6.1.4.1.989.1.16.2.9.3
        asxEstatsSectorHoTable OBJECT-TYPE
            SYNTAX SEQUENCE OF AsxEstatsSectorHoEntry
            MAX-ACCESS not-accessible
            STATUS current
            DESCRIPTION
                "Provides Controlled handover statistics per sector."
            ::= { asMaxEstats 3 }

        
        -- 1.3.6.1.4.1.989.1.16.2.9.3.1
        asxEstatsSectorHoEntry OBJECT-TYPE
            SYNTAX AsxEstatsSectorHoEntry
            MAX-ACCESS not-accessible
            STATUS current
            DESCRIPTION
                "Description."
            INDEX { ifIndex }
            ::= { asxEstatsSectorHoTable 1 }

        
        AsxEstatsSectorHoEntry ::=
            SEQUENCE { 
                asxEstatsControlledHoIndicator
                    Counter32,
                asxEstatsControlledHoCancel
                    Counter32,
                asxEstatsControlledHoRejection
                    Counter32
             }

        -- 1.3.6.1.4.1.989.1.16.2.9.3.1.1
        asxEstatsControlledHoIndicator OBJECT-TYPE
            SYNTAX Counter32
            MAX-ACCESS read-only
            STATUS current
            DESCRIPTION
                "Count of MOB_HO-IND"
            ::= { asxEstatsSectorHoEntry 1 }

        
        -- 1.3.6.1.4.1.989.1.16.2.9.3.1.2
        asxEstatsControlledHoCancel OBJECT-TYPE
            SYNTAX Counter32
            MAX-ACCESS read-only
            STATUS current
            DESCRIPTION
                "Count of MOB_HO-IND with HO-IND type 0b01"
            ::= { asxEstatsSectorHoEntry 2 }

        
        -- 1.3.6.1.4.1.989.1.16.2.9.3.1.3
        asxEstatsControlledHoRejection OBJECT-TYPE
            SYNTAX Counter32
            MAX-ACCESS read-only
            STATUS current
            DESCRIPTION
                "Count of MOB_HO-IND with HO-IND type 0b10"
            ::= { asxEstatsSectorHoEntry 3 }

        
        -- 1.3.6.1.4.1.989.1.16.2.9.4
        asxEstatsNeighbourHoTable OBJECT-TYPE
            SYNTAX SEQUENCE OF AsxEstatsNeighbourHoEntry
            MAX-ACCESS not-accessible
            STATUS current
            DESCRIPTION
                "Provides detailed handover statistics per sector for each of its neighbour."
            ::= { asMaxEstats 4 }

        
        -- 1.3.6.1.4.1.989.1.16.2.9.4.1
        asxEstatsNeighbourHoEntry OBJECT-TYPE
            SYNTAX AsxEstatsNeighbourHoEntry
            MAX-ACCESS not-accessible
            STATUS current
            DESCRIPTION
                "Description."
            INDEX { ifIndex, asxEstatsNeighbourBsid }
            ::= { asxEstatsNeighbourHoTable 1 }

        
        AsxEstatsNeighbourHoEntry ::=
            SEQUENCE { 
                asxEstatsNeighbourBsid
                    AsxEbsBsIdType,
                asxEstatsControlledMsHoRequestTo
                    Counter32,
                asxEstatsControlledBsHoRequestTo
                    Counter32,
                asxEstatsControlledHoAttemptTo
                    Counter32,
                asxEstatsControlledHoCompleteTo
                    Counter32,
                asxEstatsHoRequestFrom
                    Counter32,
                asxEstatsHoAttemptFrom
                    Counter32,
                asxEstatsHoCompleteFrom
                    Counter32,
                asxEstatsControlledHoAttemptFrom
                    Counter32,
                asxEstatsControlledHoCompleteFrom
                    Counter32,
                asxEstatsUncontrolledHoAttemptFrom
                    Counter32,
                asxEstatsUncontrolledHoCompleteFrom
                    Counter32
             }

        -- 1.3.6.1.4.1.989.1.16.2.9.4.1.1
        asxEstatsNeighbourBsid OBJECT-TYPE
            SYNTAX AsxEbsBsIdType
            MAX-ACCESS not-accessible
            STATUS current
            DESCRIPTION
                "Description."
            ::= { asxEstatsNeighbourHoEntry 1 }

        
        -- 1.3.6.1.4.1.989.1.16.2.9.4.1.2
        asxEstatsControlledMsHoRequestTo OBJECT-TYPE
            SYNTAX Counter32
            MAX-ACCESS read-only
            STATUS current
            DESCRIPTION
                "Count of MOB_MSHO-REQ, or BS sending HO_Req for MS initiated HO. Collected per target BS. (Controlled HO)"
            ::= { asxEstatsNeighbourHoEntry 2 }

        
        -- 1.3.6.1.4.1.989.1.16.2.9.4.1.3
        asxEstatsControlledBsHoRequestTo OBJECT-TYPE
            SYNTAX Counter32
            MAX-ACCESS read-only
            STATUS current
            DESCRIPTION
                "Count of MOB_BSHO-REQ, or BS sending HO_Req for BS initiated HO. Collected per target BS. (Controlled HO)"
            ::= { asxEstatsNeighbourHoEntry 3 }

        
        -- 1.3.6.1.4.1.989.1.16.2.9.4.1.4
        asxEstatsControlledHoAttemptTo OBJECT-TYPE
            SYNTAX Counter32
            MAX-ACCESS read-only
            STATUS current
            DESCRIPTION
                "Count of MOB_HO-IND with HO-IND type 0b00. Collected per target BS."
            ::= { asxEstatsNeighbourHoEntry 4 }

        
        -- 1.3.6.1.4.1.989.1.16.2.9.4.1.5
        asxEstatsControlledHoCompleteTo OBJECT-TYPE
            SYNTAX Counter32
            MAX-ACCESS read-only
            STATUS current
            DESCRIPTION
                "Count of HO_Complete received from the target BS for controlled HO only. Collected per target BS."
            ::= { asxEstatsNeighbourHoEntry 5 }

        
        -- 1.3.6.1.4.1.989.1.16.2.9.4.1.6
        asxEstatsHoRequestFrom OBJECT-TYPE
            SYNTAX Counter32
            MAX-ACCESS read-only
            STATUS current
            DESCRIPTION
                "Count of HO_Req received by the BS from serving BS. Collected per serving BS."
            ::= { asxEstatsNeighbourHoEntry 6 }

        
        -- 1.3.6.1.4.1.989.1.16.2.9.4.1.7
        asxEstatsHoAttemptFrom OBJECT-TYPE
            SYNTAX Counter32
            MAX-ACCESS read-only
            STATUS current
            DESCRIPTION
                "Count of RNG-REQ, Ranging Purpose Indication bit#0=1. Collected per Service BS."
            ::= { asxEstatsNeighbourHoEntry 7 }

        
        -- 1.3.6.1.4.1.989.1.16.2.9.4.1.8
        asxEstatsHoCompleteFrom OBJECT-TYPE
            SYNTAX Counter32
            MAX-ACCESS read-only
            STATUS current
            DESCRIPTION
                "Count of RNG-RSP (sent by BS) with Ranging Status 3(Success). Collected per serving BS."
            ::= { asxEstatsNeighbourHoEntry 8 }

        
        -- 1.3.6.1.4.1.989.1.16.2.9.4.1.9
        asxEstatsControlledHoAttemptFrom OBJECT-TYPE
            SYNTAX Counter32
            MAX-ACCESS read-only
            STATUS current
            DESCRIPTION
                "Count of HO_Cnf received by the BS from serving BS with confirm type (confirm). Collected per serving BS."
            ::= { asxEstatsNeighbourHoEntry 9 }

        
        -- 1.3.6.1.4.1.989.1.16.2.9.4.1.10
        asxEstatsControlledHoCompleteFrom OBJECT-TYPE
            SYNTAX Counter32
            MAX-ACCESS read-only
            STATUS current
            DESCRIPTION
                "Count of HO_Complete received by the BS, for the Controlled HO only. Collected per serving BS."
            ::= { asxEstatsNeighbourHoEntry 10 }

        
        -- 1.3.6.1.4.1.989.1.16.2.9.4.1.11
        asxEstatsUncontrolledHoAttemptFrom OBJECT-TYPE
            SYNTAX Counter32
            MAX-ACCESS read-only
            STATUS current
            DESCRIPTION
                "Count of RNG-REQ, Ranging Purpose Indication bit#0=1, without first receiving HO-Cnf (Uncontrolled HO). Collected per serving BS."
            ::= { asxEstatsNeighbourHoEntry 11 }

        
        -- 1.3.6.1.4.1.989.1.16.2.9.4.1.12
        asxEstatsUncontrolledHoCompleteFrom OBJECT-TYPE
            SYNTAX Counter32
            MAX-ACCESS read-only
            STATUS current
            DESCRIPTION
                "Count of RNG-RSP (sent by BS) with Ranging Status 3(Success), without first receiving HO-cnf (Uncontrolled HO). Collected per serving BS."
            ::= { asxEstatsNeighbourHoEntry 12 }

        
        -- 1.3.6.1.4.1.989.1.16.2.9.5
        asxEstatsConnectionActivityTable OBJECT-TYPE
            SYNTAX SEQUENCE OF AsxEstatsConnectionActivityEntry
            MAX-ACCESS not-accessible
            STATUS current
            DESCRIPTION
                "Provides Connection Activity statistics per sector."
            ::= { asMaxEstats 5 }

        
        -- 1.3.6.1.4.1.989.1.16.2.9.5.1
        asxEstatsConnectionActivityEntry OBJECT-TYPE
            SYNTAX AsxEstatsConnectionActivityEntry
            MAX-ACCESS not-accessible
            STATUS current
            DESCRIPTION
                "Description."
            INDEX { ifIndex }
            ::= { asxEstatsConnectionActivityTable 1 }

        
        AsxEstatsConnectionActivityEntry ::=
            SEQUENCE { 
                asxEstatsRegisteredMs
                    Counter32,
                asxEstatsRangingAttempt
                    Counter32,
                asxEstatsRangingComplete
                    Counter32,
                asxEstatsIneAttempt
                    Counter32,
                asxEstatsIneComplete
                    Counter32,
                asxEstatsMsInitiatedNxRequest
                    Counter32,
                asxEstatsMsInitiatedNxResponse
                    Counter32,
                asxEstatsNwInitiatedNxRequest
                    Counter32,
                asxEstatsNwInitiatedNxResponse
                    Counter32,
                asxEstatsNwInitiatedNxReject
                    Counter32,
                asxEstatsMsDrop
                    Counter32
             }

        -- 1.3.6.1.4.1.989.1.16.2.9.5.1.1
        asxEstatsRegisteredMs OBJECT-TYPE
            SYNTAX Counter32
            MAX-ACCESS read-only
            STATUS current
            DESCRIPTION
                "Number of registered MS"
            ::= { asxEstatsConnectionActivityEntry 1 }

        
        -- 1.3.6.1.4.1.989.1.16.2.9.5.1.2
        asxEstatsRangingAttempt OBJECT-TYPE
            SYNTAX Counter32
            MAX-ACCESS read-only
            STATUS current
            DESCRIPTION
                "Count of CDMA code with initial ranging code"
            ::= { asxEstatsConnectionActivityEntry 2 }

        
        -- 1.3.6.1.4.1.989.1.16.2.9.5.1.3
        asxEstatsRangingComplete OBJECT-TYPE
            SYNTAX Counter32
            MAX-ACCESS read-only
            STATUS current
            DESCRIPTION
                "Count of Initial Ranging RNG-RSP on Intial Ranging CID with Ranging Status = 3"
            ::= { asxEstatsConnectionActivityEntry 3 }

        
        -- 1.3.6.1.4.1.989.1.16.2.9.5.1.4
        asxEstatsIneAttempt OBJECT-TYPE
            SYNTAX Counter32
            MAX-ACCESS read-only
            STATUS current
            DESCRIPTION
                "Count of REG-REQ with Basic CID"
            ::= { asxEstatsConnectionActivityEntry 4 }

        
        -- 1.3.6.1.4.1.989.1.16.2.9.5.1.5
        asxEstatsIneComplete OBJECT-TYPE
            SYNTAX Counter32
            MAX-ACCESS read-only
            STATUS current
            DESCRIPTION
                "Count of REG-RSP"
            ::= { asxEstatsConnectionActivityEntry 5 }

        
        -- 1.3.6.1.4.1.989.1.16.2.9.5.1.6
        asxEstatsMsInitiatedNxRequest OBJECT-TYPE
            SYNTAX Counter32
            MAX-ACCESS read-only
            STATUS current
            DESCRIPTION
                "Count of DREG-REQ with Deregistration request code 0x00"
            ::= { asxEstatsConnectionActivityEntry 6 }

        
        -- 1.3.6.1.4.1.989.1.16.2.9.5.1.7
        asxEstatsMsInitiatedNxResponse OBJECT-TYPE
            SYNTAX Counter32
            MAX-ACCESS read-only
            STATUS current
            DESCRIPTION
                "Count of DREG-CMD with action code 0x04"
            ::= { asxEstatsConnectionActivityEntry 7 }

        
        -- 1.3.6.1.4.1.989.1.16.2.9.5.1.8
        asxEstatsNwInitiatedNxRequest OBJECT-TYPE
            SYNTAX Counter32
            MAX-ACCESS read-only
            STATUS current
            DESCRIPTION
                "Count of DREG-CMD with action code 0x00"
            ::= { asxEstatsConnectionActivityEntry 8 }

        
        -- 1.3.6.1.4.1.989.1.16.2.9.5.1.9
        asxEstatsNwInitiatedNxResponse OBJECT-TYPE
            SYNTAX Counter32
            MAX-ACCESS read-only
            STATUS current
            DESCRIPTION
                "Count of DREG-REQ with Deregistration request code 0x02"
            ::= { asxEstatsConnectionActivityEntry 9 }

        
        -- 1.3.6.1.4.1.989.1.16.2.9.5.1.10
        asxEstatsNwInitiatedNxReject OBJECT-TYPE
            SYNTAX Counter32
            MAX-ACCESS read-only
            STATUS current
            DESCRIPTION
                "Count of DREG-REQ with Deregistration request code 0x03"
            ::= { asxEstatsConnectionActivityEntry 10 }

        
        -- 1.3.6.1.4.1.989.1.16.2.9.5.1.11
        asxEstatsMsDrop OBJECT-TYPE
            SYNTAX Counter32
            MAX-ACCESS read-only
            STATUS current
            DESCRIPTION
                "Count of times the Keep_Alive_Timer times out"
            ::= { asxEstatsConnectionActivityEntry 11 }

        
        -- 1.3.6.1.4.1.989.1.16.2.9.6
        asxEstatsActiveMsTable OBJECT-TYPE
            SYNTAX SEQUENCE OF AsxEstatsActiveMsEntry
            MAX-ACCESS not-accessible
            STATUS current
            DESCRIPTION
                "Description."
            ::= { asMaxEstats 6 }

        
        -- 1.3.6.1.4.1.989.1.16.2.9.6.1
        asxEstatsActiveMsEntry OBJECT-TYPE
            SYNTAX AsxEstatsActiveMsEntry
            MAX-ACCESS not-accessible
            STATUS current
            DESCRIPTION
                "Description."
            INDEX { ifIndex, wmanIf2BsSsMacAddress }
            ::= { asxEstatsActiveMsTable 1 }

        
        AsxEstatsActiveMsEntry ::=
            SEQUENCE { 
                asxEstatsActiveMsUlBytes
                    Counter32,
                asxEstatsActiveMsDlBytes
                    Counter32
             }

        -- 1.3.6.1.4.1.989.1.16.2.9.6.1.1
        asxEstatsActiveMsUlBytes OBJECT-TYPE
            SYNTAX Counter32
            MAX-ACCESS read-only
            STATUS current
            DESCRIPTION
                "The number of uplink bytes received from this SS."
            ::= { asxEstatsActiveMsEntry 1 }

        
        -- 1.3.6.1.4.1.989.1.16.2.9.6.1.2
        asxEstatsActiveMsDlBytes OBJECT-TYPE
            SYNTAX Counter32
            MAX-ACCESS read-only
            STATUS current
            DESCRIPTION
                "The number of downlink bytes received by this SS."
            ::= { asxEstatsActiveMsEntry 2 }

        
        -- 1.3.6.1.4.1.989.1.16.2.9.7
        asxEstatsSectorTable OBJECT-TYPE
            SYNTAX SEQUENCE OF AsxEstatsSectorEntry
            MAX-ACCESS not-accessible
            STATUS current
            DESCRIPTION
                "Provides statistics per sector."
            ::= { asMaxEstats 7 }

        
        -- 1.3.6.1.4.1.989.1.16.2.9.7.1
        asxEstatsSectorEntry OBJECT-TYPE
            SYNTAX AsxEstatsSectorEntry
            MAX-ACCESS not-accessible
            STATUS current
            DESCRIPTION
                "Description."
            INDEX { ifIndex }
            ::= { asxEstatsSectorTable 1 }

        
        AsxEstatsSectorEntry ::=
            SEQUENCE { 
                asxEstatsSectorUlErrorPkts
                    Counter64,
                asxEstatsSectorUlPkts
                    Counter64,
                asxEstatsSectorUlBytes
                    Counter64,
                asxEstatsSectorDlPkts
                    Counter64,
                asxEstatsSectorDlBytes
                    Counter64,
                asxEstatsSectorHarqUlBursts
                    Counter64,
                asxEstatsSectorHarqUlAcks
                    Counter64,
                asxEstatsSectorHarqUlNacks
                    Counter64,
                asxEstatsSectorHarqDlBursts
                    Counter64,
                asxEstatsSectorHarqDlAcks
                    Counter64,
                asxEstatsSectorHarqDlNacks
                    Counter64,
                asxEstatsSectorArqUlBlocks
                    Counter64,
                asxEstatsSectorArqUlRetrans
                    Counter64,
                asxEstatsSectorArqUlDiscards
                    Counter64,
                asxEstatsSectorArqDlBlocks
                    Counter64,
                asxEstatsSectorArqDlRetrans
                    Counter64,
                asxEstatsSectorArqDlAcks
                    Counter64,
                asxEstatsSectorArqDlNacks
                    Counter64,
                asxEstatsSectorIdleModeEntryReq
                    Counter64,
                asxEstatsSectorIdleModeEntryRsp
                    Counter64,
                asxEstatsSectorIdleModeExitAttempt
                    Counter64,
                asxEstatsSectorIdleModeExitSuccess
                    Counter64,
                asxEstatsSectorLocUpdAttempt
                    Counter64,
                asxEstatsSectorLocUpdComplete
                    Counter64,
                asxEstatsSectorLocUpdFail
                    Counter64,
                asxEstatsSectorUlSubframeUtilization
                    Integer32,
                asxEstatsSectorDlSubframeUtilization
                    Integer32,
                asxEstatsSectorUlTotalPkts
                    Counter64,
                asxEstatsSectorUlSubFrameSlots
                    Counter64,
                asxEstatsSectorUsedUlSubFrameSlots
                    Counter64,
                asxEstatsSectorUlOverheadSlots
                    Counter64,
                asxEstatsSectorDlSubframeSlots
                    Counter64,
                asxEstatsSectorUsedDlSubframeSlots
                    Counter64,
                asxEstatsSectorDlOverheadSlots
                    Counter64
             }

        -- 1.3.6.1.4.1.989.1.16.2.9.7.1.1
        asxEstatsSectorUlErrorPkts OBJECT-TYPE
            SYNTAX Counter64
            MAX-ACCESS read-only
            STATUS current
            DESCRIPTION
                "Count of uplink errored packets."
            ::= { asxEstatsSectorEntry 1 }

        
        -- 1.3.6.1.4.1.989.1.16.2.9.7.1.2
        asxEstatsSectorUlPkts OBJECT-TYPE
            SYNTAX Counter64
            MAX-ACCESS read-only
            STATUS current
            DESCRIPTION
                "Count of uplink packets."
            ::= { asxEstatsSectorEntry 2 }

        
        -- 1.3.6.1.4.1.989.1.16.2.9.7.1.3
        asxEstatsSectorUlBytes OBJECT-TYPE
            SYNTAX Counter64
            MAX-ACCESS read-only
            STATUS current
            DESCRIPTION
                "Count of uplink bytes."
            ::= { asxEstatsSectorEntry 3 }

        
        -- 1.3.6.1.4.1.989.1.16.2.9.7.1.4
        asxEstatsSectorDlPkts OBJECT-TYPE
            SYNTAX Counter64
            MAX-ACCESS read-only
            STATUS current
            DESCRIPTION
                "Count of downlink packets."
            ::= { asxEstatsSectorEntry 4 }

        
        -- 1.3.6.1.4.1.989.1.16.2.9.7.1.5
        asxEstatsSectorDlBytes OBJECT-TYPE
            SYNTAX Counter64
            MAX-ACCESS read-only
            STATUS current
            DESCRIPTION
                "Count of downlink bytes."
            ::= { asxEstatsSectorEntry 5 }

        
        -- 1.3.6.1.4.1.989.1.16.2.9.7.1.6
        asxEstatsSectorHarqUlBursts OBJECT-TYPE
            SYNTAX Counter64
            MAX-ACCESS read-only
            STATUS current
            DESCRIPTION
                "Count of uplink HARQ bursts."
            ::= { asxEstatsSectorEntry 6 }

        
        -- 1.3.6.1.4.1.989.1.16.2.9.7.1.7
        asxEstatsSectorHarqUlAcks OBJECT-TYPE
            SYNTAX Counter64
            MAX-ACCESS read-only
            STATUS current
            DESCRIPTION
                "Count of uplink HARQ ACKs."
            ::= { asxEstatsSectorEntry 7 }

        
        -- 1.3.6.1.4.1.989.1.16.2.9.7.1.8
        asxEstatsSectorHarqUlNacks OBJECT-TYPE
            SYNTAX Counter64
            MAX-ACCESS read-only
            STATUS current
            DESCRIPTION
                "Count of uplink HARQ NACKs."
            ::= { asxEstatsSectorEntry 8 }

        
        -- 1.3.6.1.4.1.989.1.16.2.9.7.1.9
        asxEstatsSectorHarqDlBursts OBJECT-TYPE
            SYNTAX Counter64
            MAX-ACCESS read-only
            STATUS current
            DESCRIPTION
                "Count of downlink HARQ bursts."
            ::= { asxEstatsSectorEntry 9 }

        
        -- 1.3.6.1.4.1.989.1.16.2.9.7.1.10
        asxEstatsSectorHarqDlAcks OBJECT-TYPE
            SYNTAX Counter64
            MAX-ACCESS read-only
            STATUS current
            DESCRIPTION
                "Count of downlink HARQ ACKs."
            ::= { asxEstatsSectorEntry 10 }

        
        -- 1.3.6.1.4.1.989.1.16.2.9.7.1.11
        asxEstatsSectorHarqDlNacks OBJECT-TYPE
            SYNTAX Counter64
            MAX-ACCESS read-only
            STATUS current
            DESCRIPTION
                "Count of downlink HARQ NACKs."
            ::= { asxEstatsSectorEntry 11 }

        
        -- 1.3.6.1.4.1.989.1.16.2.9.7.1.12
        asxEstatsSectorArqUlBlocks OBJECT-TYPE
            SYNTAX Counter64
            MAX-ACCESS read-only
            STATUS current
            DESCRIPTION
                "Count of uplink ARQ blocks."
            ::= { asxEstatsSectorEntry 12 }

        
        -- 1.3.6.1.4.1.989.1.16.2.9.7.1.13
        asxEstatsSectorArqUlRetrans OBJECT-TYPE
            SYNTAX Counter64
            MAX-ACCESS read-only
            STATUS current
            DESCRIPTION
                "Count of uplink ARQ retransmission blocks."
            ::= { asxEstatsSectorEntry 13 }

        
        -- 1.3.6.1.4.1.989.1.16.2.9.7.1.14
        asxEstatsSectorArqUlDiscards OBJECT-TYPE
            SYNTAX Counter64
            MAX-ACCESS read-only
            STATUS current
            DESCRIPTION
                "Count of uplink ARQ discards."
            ::= { asxEstatsSectorEntry 14 }

        
        -- 1.3.6.1.4.1.989.1.16.2.9.7.1.15
        asxEstatsSectorArqDlBlocks OBJECT-TYPE
            SYNTAX Counter64
            MAX-ACCESS read-only
            STATUS current
            DESCRIPTION
                "Count of downlink ARQ blocks."
            ::= { asxEstatsSectorEntry 15 }

        
        -- 1.3.6.1.4.1.989.1.16.2.9.7.1.16
        asxEstatsSectorArqDlRetrans OBJECT-TYPE
            SYNTAX Counter64
            MAX-ACCESS read-only
            STATUS current
            DESCRIPTION
                "Count of downlink ARQ retransmission blocks."
            ::= { asxEstatsSectorEntry 16 }

        
        -- 1.3.6.1.4.1.989.1.16.2.9.7.1.17
        asxEstatsSectorArqDlAcks OBJECT-TYPE
            SYNTAX Counter64
            MAX-ACCESS read-only
            STATUS current
            DESCRIPTION
                "Count of downlink ARQ ACKs."
            ::= { asxEstatsSectorEntry 17 }

        
        -- 1.3.6.1.4.1.989.1.16.2.9.7.1.18
        asxEstatsSectorArqDlNacks OBJECT-TYPE
            SYNTAX Counter64
            MAX-ACCESS read-only
            STATUS current
            DESCRIPTION
                "Count of downlink ARQ ACKs."
            ::= { asxEstatsSectorEntry 18 }

        
        -- 1.3.6.1.4.1.989.1.16.2.9.7.1.19
        asxEstatsSectorIdleModeEntryReq OBJECT-TYPE
            SYNTAX Counter64
            MAX-ACCESS read-only
            STATUS current
            DESCRIPTION
                "Count of idle mode entry requests (DREG-REQ with Deregistration request code 0x01)."
            ::= { asxEstatsSectorEntry 19 }

        
        -- 1.3.6.1.4.1.989.1.16.2.9.7.1.20
        asxEstatsSectorIdleModeEntryRsp OBJECT-TYPE
            SYNTAX Counter64
            MAX-ACCESS read-only
            STATUS current
            DESCRIPTION
                "Count of idle mode entry responses (DREG-CMD with action code 0x05)."
            ::= { asxEstatsSectorEntry 20 }

        
        -- 1.3.6.1.4.1.989.1.16.2.9.7.1.21
        asxEstatsSectorIdleModeExitAttempt OBJECT-TYPE
            SYNTAX Counter64
            MAX-ACCESS read-only
            STATUS current
            DESCRIPTION
                "Count of idle mode exit attempts (RNG-REQ, Ranging Purpose Indication bit#0)."
            ::= { asxEstatsSectorEntry 21 }

        
        -- 1.3.6.1.4.1.989.1.16.2.9.7.1.22
        asxEstatsSectorIdleModeExitSuccess OBJECT-TYPE
            SYNTAX Counter64
            MAX-ACCESS read-only
            STATUS current
            DESCRIPTION
                "Count of idle mode exit success (RNG-RSP relating to idle mode exit success)."
            ::= { asxEstatsSectorEntry 22 }

        
        -- 1.3.6.1.4.1.989.1.16.2.9.7.1.23
        asxEstatsSectorLocUpdAttempt OBJECT-TYPE
            SYNTAX Counter64
            MAX-ACCESS read-only
            STATUS current
            DESCRIPTION
                "Count of idle mode location update attempt (RNG-REQ with Ranging Purpose Indication bit#1 = set)."
            ::= { asxEstatsSectorEntry 23 }

        
        -- 1.3.6.1.4.1.989.1.16.2.9.7.1.24
        asxEstatsSectorLocUpdComplete OBJECT-TYPE
            SYNTAX Counter64
            MAX-ACCESS read-only
            STATUS current
            DESCRIPTION
                "Count of idle mode location update completion (RNG-RSP with Location Update Response = 0x00)."
            ::= { asxEstatsSectorEntry 24 }

        
        -- 1.3.6.1.4.1.989.1.16.2.9.7.1.25
        asxEstatsSectorLocUpdFail OBJECT-TYPE
            SYNTAX Counter64
            MAX-ACCESS read-only
            STATUS current
            DESCRIPTION
                "Count of idle mode location update failure (RNG-RSP with Location Update Response = 0x01)."
            ::= { asxEstatsSectorEntry 25 }

        
        -- 1.3.6.1.4.1.989.1.16.2.9.7.1.26
        asxEstatsSectorUlSubframeUtilization OBJECT-TYPE
            SYNTAX Integer32 (0..100)
            UNITS "percentage"
            MAX-ACCESS read-only
            STATUS current
            DESCRIPTION
                "Number of slots divided by total available uplink - over the air as percentage."
            ::= { asxEstatsSectorEntry 26 }

        
        -- 1.3.6.1.4.1.989.1.16.2.9.7.1.27
        asxEstatsSectorDlSubframeUtilization OBJECT-TYPE
            SYNTAX Integer32 (0..100)
            UNITS "percentage"
            MAX-ACCESS read-only
            STATUS current
            DESCRIPTION
                "Number of slots divided by total available downlink - over the air as percentage."
            ::= { asxEstatsSectorEntry 27 }

        
        -- 1.3.6.1.4.1.989.1.16.2.9.7.1.28
        asxEstatsSectorUlTotalPkts OBJECT-TYPE
            SYNTAX Counter64
            MAX-ACCESS read-only
            STATUS current
            DESCRIPTION
                "Count of uplink packets received in the BS. Collected per sector."
            ::= { asxEstatsSectorEntry 28 }

        
        -- 1.3.6.1.4.1.989.1.16.2.9.7.1.29
        asxEstatsSectorUlSubFrameSlots OBJECT-TYPE
            SYNTAX Counter64
            MAX-ACCESS read-only
            STATUS current
            DESCRIPTION
                "Number of total slots in uplink - over the air"
            ::= { asxEstatsSectorEntry 29 }

        
        -- 1.3.6.1.4.1.989.1.16.2.9.7.1.30
        asxEstatsSectorUsedUlSubFrameSlots OBJECT-TYPE
            SYNTAX Counter64
            MAX-ACCESS read-only
            STATUS current
            DESCRIPTION
                "Number of total used slots in uplink - over the air"
            ::= { asxEstatsSectorEntry 30 }

        
        -- 1.3.6.1.4.1.989.1.16.2.9.7.1.31
        asxEstatsSectorUlOverheadSlots OBJECT-TYPE
            SYNTAX Counter64
            MAX-ACCESS read-only
            STATUS current
            DESCRIPTION
                "Number of total slots in uplink used for - over the air"
            ::= { asxEstatsSectorEntry 31 }

        
        -- 1.3.6.1.4.1.989.1.16.2.9.7.1.32
        asxEstatsSectorDlSubframeSlots OBJECT-TYPE
            SYNTAX Counter64
            MAX-ACCESS read-only
            STATUS current
            DESCRIPTION
                "Number of total slots in downlink - over the air"
            ::= { asxEstatsSectorEntry 32 }

        
        -- 1.3.6.1.4.1.989.1.16.2.9.7.1.33
        asxEstatsSectorUsedDlSubframeSlots OBJECT-TYPE
            SYNTAX Counter64
            MAX-ACCESS read-only
            STATUS current
            DESCRIPTION
                "Number of total used slots in downlink - over the air"
            ::= { asxEstatsSectorEntry 33 }

        
        -- 1.3.6.1.4.1.989.1.16.2.9.7.1.34
        asxEstatsSectorDlOverheadSlots OBJECT-TYPE
            SYNTAX Counter64
            MAX-ACCESS read-only
            STATUS current
            DESCRIPTION
                "Number of total slots in downlink used for FCH and UL/DL MAPs- over the air"
            ::= { asxEstatsSectorEntry 34 }

        
        -- 1.3.6.1.4.1.989.1.16.2.9.8
        asxEstatsSectorStatsTable OBJECT-TYPE
            SYNTAX SEQUENCE OF AsxEstatsSectorStatsEntry
            MAX-ACCESS not-accessible
            STATUS current
            DESCRIPTION
                "This table contains Sector Statistics."
            ::= { asMaxEstats 8 }

        
        -- 1.3.6.1.4.1.989.1.16.2.9.8.1
        asxEstatsSectorStatsEntry OBJECT-TYPE
            SYNTAX AsxEstatsSectorStatsEntry
            MAX-ACCESS not-accessible
            STATUS current
            DESCRIPTION
                "Description."
            INDEX { ifIndex }
            ::= { asxEstatsSectorStatsTable 1 }

        
        AsxEstatsSectorStatsEntry ::=
            SEQUENCE { 
                asxESectorStatsNoiseLevelLowCounter
                    Counter32,
                asxESectorStatsNoiseLevelMedCounter
                    Counter32,
                asxESectorStatsNoiseLevelHighCounter
                    Counter32,
                asxESectorStatsDlSlotsAtQpsk12rep6
                    Counter64,
                asxESectorStatsDlSlotsAtQpsk12rep4
                    Counter64,
                asxESectorStatsDlSlotsAtQpsk12rep2
                    Counter64,
                asxESectorStatsDlSlotsAtQpsk12
                    Counter64,
                asxESectorStatsDlSlotsAtQpsk34
                    Counter64,
                asxESectorStatsDlSlotsAt16QAM12
                    Counter64,
                asxESectorStatsDlSlotsAt16QAM34
                    Counter64,
                asxESectorStatsDlSlotsAt64QAM12
                    Counter64,
                asxESectorStatsDlSlotsAt64QAM23
                    Counter64,
                asxESectorStatsDlSlotsAt64QAM34
                    Counter64,
                asxESectorStatsDlSlotsAt64QAM56
                    Counter64,
                asxESectorStatsUlSlotsAtQpsk12rep6
                    Counter64,
                asxESectorStatsUlSlotsAtQpsk12rep4
                    Counter64,
                asxESectorStatsUlSlotsAtQpsk12rep2
                    Counter64,
                asxESectorStatsUlSlotsAtQpsk12
                    Counter64,
                asxESectorStatsUlSlotsAtQpsk34
                    Counter64,
                asxESectorStatsUlSlotsAt16QAM12
                    Counter64,
                asxESectorStatsUlSlotsAt16QAM34
                    Counter64,
                asxESectorStatsUlSlotsAt64QAM12
                    Counter64,
                asxESectorStatsUlSlotsAt64QAM23
                    Counter64,
                asxESectorStatsUlSlotsAt64QAM34
                    Counter64,
                asxESectorStatsUlSlotsAt64QAM56
                    Counter64
             }

        -- 1.3.6.1.4.1.989.1.16.2.9.8.1.1
        asxESectorStatsNoiseLevelLowCounter OBJECT-TYPE
            SYNTAX Counter32
            MAX-ACCESS read-only
            STATUS current
            DESCRIPTION
                "Number of noise bursts whose RSSI was under -122dBm."
            ::= { asxEstatsSectorStatsEntry 1 }

        
        -- 1.3.6.1.4.1.989.1.16.2.9.8.1.2
        asxESectorStatsNoiseLevelMedCounter OBJECT-TYPE
            SYNTAX Counter32
            MAX-ACCESS read-only
            STATUS current
            DESCRIPTION
                "Number of noise bursts whose RSSI was between -122dBm and -110dBm."
            ::= { asxEstatsSectorStatsEntry 2 }

        
        -- 1.3.6.1.4.1.989.1.16.2.9.8.1.3
        asxESectorStatsNoiseLevelHighCounter OBJECT-TYPE
            SYNTAX Counter32
            MAX-ACCESS read-only
            STATUS current
            DESCRIPTION
                "Number of noise bursts whose RSSI was over -110dBm"
            ::= { asxEstatsSectorStatsEntry 3 }

        
        -- 1.3.6.1.4.1.989.1.16.2.9.8.1.4
        asxESectorStatsDlSlotsAtQpsk12rep6 OBJECT-TYPE
            SYNTAX Counter64
            MAX-ACCESS read-only
            STATUS current
            DESCRIPTION
                "Number of slots allocated in the DL at QPSK1/2 repetition 6"
            ::= { asxEstatsSectorStatsEntry 4 }

        
        -- 1.3.6.1.4.1.989.1.16.2.9.8.1.5
        asxESectorStatsDlSlotsAtQpsk12rep4 OBJECT-TYPE
            SYNTAX Counter64
            MAX-ACCESS read-only
            STATUS current
            DESCRIPTION
                "Number of slots allocated in the DL at QPSK1/2 repetition 4"
            ::= { asxEstatsSectorStatsEntry 5 }

        
        -- 1.3.6.1.4.1.989.1.16.2.9.8.1.6
        asxESectorStatsDlSlotsAtQpsk12rep2 OBJECT-TYPE
            SYNTAX Counter64
            MAX-ACCESS read-only
            STATUS current
            DESCRIPTION
                "Number of slots allocated in the DL at QPSK1/2 repetition 2"
            ::= { asxEstatsSectorStatsEntry 6 }

        
        -- 1.3.6.1.4.1.989.1.16.2.9.8.1.7
        asxESectorStatsDlSlotsAtQpsk12 OBJECT-TYPE
            SYNTAX Counter64
            MAX-ACCESS read-only
            STATUS current
            DESCRIPTION
                "Number of slots allocated in the DL at QPSK1/2 with no repetition"
            ::= { asxEstatsSectorStatsEntry 7 }

        
        -- 1.3.6.1.4.1.989.1.16.2.9.8.1.8
        asxESectorStatsDlSlotsAtQpsk34 OBJECT-TYPE
            SYNTAX Counter64
            MAX-ACCESS read-only
            STATUS current
            DESCRIPTION
                "Number of slots allocated in the DL at QPSK3/4"
            ::= { asxEstatsSectorStatsEntry 8 }

        
        -- 1.3.6.1.4.1.989.1.16.2.9.8.1.9
        asxESectorStatsDlSlotsAt16QAM12 OBJECT-TYPE
            SYNTAX Counter64
            MAX-ACCESS read-only
            STATUS current
            DESCRIPTION
                "Number of slots allocated in the DL at 16QAM1/2"
            ::= { asxEstatsSectorStatsEntry 9 }

        
        -- 1.3.6.1.4.1.989.1.16.2.9.8.1.10
        asxESectorStatsDlSlotsAt16QAM34 OBJECT-TYPE
            SYNTAX Counter64
            MAX-ACCESS read-only
            STATUS current
            DESCRIPTION
                "Number of slots allocated in the DL at 16QAM3/4"
            ::= { asxEstatsSectorStatsEntry 10 }

        
        -- 1.3.6.1.4.1.989.1.16.2.9.8.1.11
        asxESectorStatsDlSlotsAt64QAM12 OBJECT-TYPE
            SYNTAX Counter64
            MAX-ACCESS read-only
            STATUS current
            DESCRIPTION
                "Number of slots allocated in the DL at 64QAM1/2"
            ::= { asxEstatsSectorStatsEntry 11 }

        
        -- 1.3.6.1.4.1.989.1.16.2.9.8.1.12
        asxESectorStatsDlSlotsAt64QAM23 OBJECT-TYPE
            SYNTAX Counter64
            MAX-ACCESS read-only
            STATUS current
            DESCRIPTION
                "Number of slots allocated in the DL at 64QAM2/3"
            ::= { asxEstatsSectorStatsEntry 12 }

        
        -- 1.3.6.1.4.1.989.1.16.2.9.8.1.13
        asxESectorStatsDlSlotsAt64QAM34 OBJECT-TYPE
            SYNTAX Counter64
            MAX-ACCESS read-only
            STATUS current
            DESCRIPTION
                "Number of slots allocated in the DL at 64QAM3/4"
            ::= { asxEstatsSectorStatsEntry 13 }

        
        -- 1.3.6.1.4.1.989.1.16.2.9.8.1.14
        asxESectorStatsDlSlotsAt64QAM56 OBJECT-TYPE
            SYNTAX Counter64
            MAX-ACCESS read-only
            STATUS current
            DESCRIPTION
                "Number of slots allocated in the DL at 64QAM5/6"
            ::= { asxEstatsSectorStatsEntry 14 }

        
        -- 1.3.6.1.4.1.989.1.16.2.9.8.1.15
        asxESectorStatsUlSlotsAtQpsk12rep6 OBJECT-TYPE
            SYNTAX Counter64
            MAX-ACCESS read-only
            STATUS current
            DESCRIPTION
                "Number of slots allocated in the UL at QPSK1/2 repetition 6"
            ::= { asxEstatsSectorStatsEntry 15 }

        
        -- 1.3.6.1.4.1.989.1.16.2.9.8.1.16
        asxESectorStatsUlSlotsAtQpsk12rep4 OBJECT-TYPE
            SYNTAX Counter64
            MAX-ACCESS read-only
            STATUS current
            DESCRIPTION
                "Number of slots allocated in the UL at QPSK1/2 repetition 4"
            ::= { asxEstatsSectorStatsEntry 16 }

        
        -- 1.3.6.1.4.1.989.1.16.2.9.8.1.17
        asxESectorStatsUlSlotsAtQpsk12rep2 OBJECT-TYPE
            SYNTAX Counter64
            MAX-ACCESS read-only
            STATUS current
            DESCRIPTION
                "Number of slots allocated in the UL at QPSK1/2 repetition 2"
            ::= { asxEstatsSectorStatsEntry 17 }

        
        -- 1.3.6.1.4.1.989.1.16.2.9.8.1.18
        asxESectorStatsUlSlotsAtQpsk12 OBJECT-TYPE
            SYNTAX Counter64
            MAX-ACCESS read-only
            STATUS current
            DESCRIPTION
                "Number of slots allocated in the UL at QPSK1/2 with no repetition"
            ::= { asxEstatsSectorStatsEntry 18 }

        
        -- 1.3.6.1.4.1.989.1.16.2.9.8.1.19
        asxESectorStatsUlSlotsAtQpsk34 OBJECT-TYPE
            SYNTAX Counter64
            MAX-ACCESS read-only
            STATUS current
            DESCRIPTION
                "Number of slots allocated in the UL at QPSK3/4"
            ::= { asxEstatsSectorStatsEntry 19 }

        
        -- 1.3.6.1.4.1.989.1.16.2.9.8.1.20
        asxESectorStatsUlSlotsAt16QAM12 OBJECT-TYPE
            SYNTAX Counter64
            MAX-ACCESS read-only
            STATUS current
            DESCRIPTION
                "Number of slots allocated in the UL at 16QAM1/2"
            ::= { asxEstatsSectorStatsEntry 20 }

        
        -- 1.3.6.1.4.1.989.1.16.2.9.8.1.21
        asxESectorStatsUlSlotsAt16QAM34 OBJECT-TYPE
            SYNTAX Counter64
            MAX-ACCESS read-only
            STATUS current
            DESCRIPTION
                "Number of slots allocated in the UL at 16QAM3/4"
            ::= { asxEstatsSectorStatsEntry 21 }

        
        -- 1.3.6.1.4.1.989.1.16.2.9.8.1.22
        asxESectorStatsUlSlotsAt64QAM12 OBJECT-TYPE
            SYNTAX Counter64
            MAX-ACCESS read-only
            STATUS current
            DESCRIPTION
                "Number of slots allocated in the UL at 64QAM1/2"
            ::= { asxEstatsSectorStatsEntry 22 }

        
        -- 1.3.6.1.4.1.989.1.16.2.9.8.1.23
        asxESectorStatsUlSlotsAt64QAM23 OBJECT-TYPE
            SYNTAX Counter64
            MAX-ACCESS read-only
            STATUS current
            DESCRIPTION
                "Number of slots allocated in the UL at 64QAM2/3"
            ::= { asxEstatsSectorStatsEntry 23 }

        
        -- 1.3.6.1.4.1.989.1.16.2.9.8.1.24
        asxESectorStatsUlSlotsAt64QAM34 OBJECT-TYPE
            SYNTAX Counter64
            MAX-ACCESS read-only
            STATUS current
            DESCRIPTION
                "Number of slots allocated in the UL at 64QAM3/4"
            ::= { asxEstatsSectorStatsEntry 24 }

        
        -- 1.3.6.1.4.1.989.1.16.2.9.8.1.25
        asxESectorStatsUlSlotsAt64QAM56 OBJECT-TYPE
            SYNTAX Counter64
            MAX-ACCESS read-only
            STATUS current
            DESCRIPTION
                "Number of slots allocated in the UL at 64QAM5/6"
            ::= { asxEstatsSectorStatsEntry 25 }

        
    
    END

--
-- ASMAX-ESTATS-MIB.mib
--
