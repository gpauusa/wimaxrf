--
-- ASCMN-AGENT-MIB.mib
-- MIB generated by MG-SOFT Visual MIB Builder 2010 Version 8.0  Build 400
-- Wednesday, March 16, 2011 at 16:57:31
--

	ASCMN-AGENT-MIB DEFINITIONS ::= BEGIN
 
		IMPORTS
			asCmn			
				FROM AIRSPAN-PRODUCTS-MIB			
			AsCmnTcBooleanSwitch			
				FROM ASCMN-TC-MIB			
			ifIndex			
				FROM IF-MIB			
			InetAddressType, InetAddress			
				FROM INET-ADDRESS-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			DisplayString, RowStatus, MacAddress			
				FROM SNMPv2-TC;
	
	
		-- 1.3.6.1.4.1.989.1.22.1
		asCmnAgent MODULE-IDENTITY 
			LAST-UPDATED "201103162250Z"		-- March 16, 2011 at 22:50 GMT
			ORGANIZATION 
				"Airspan Communications Ltd"
			CONTACT-INFO 
				"kdudzins@airspan.com"
			DESCRIPTION 
				"Propriatory MIB to be supported by all SNMP agents operating in a multi-stack 
				environment."
			REVISION "201103150941Z"		-- March 15, 2011 at 09:41 GMT
			DESCRIPTION 
				"Pre-Draft 1:
				- initial version "
			REVISION "201103162250Z"		-- March 16, 2011 at 22:50 GMT
			DESCRIPTION 
				"Pre-Draft 2:
				- updated syntax - replaced INTEGER with Integer32 in places"
			::= { asCmn 1 }

		
	
	
--
-- Node definitions
--
	
		-- 1.3.6.1.4.1.989.1.22.1.1
		asCmnAgentConformance OBJECT IDENTIFIER ::= { asCmnAgent 1 }

		
--  this module
		-- 1.3.6.1.4.1.989.1.22.1.1.1
		asCmnAgentCompliance MODULE-COMPLIANCE
			STATUS current
			DESCRIPTION 
				"Description."
			MODULE -- this module
				MANDATORY-GROUPS { asCmnAgentObjectGroup }
			::= { asCmnAgentConformance 1 }

		
		-- 1.3.6.1.4.1.989.1.22.1.1.2
		asCmnAgentObjectGroup OBJECT-GROUP
			OBJECTS { asCmnAgentSnmpV1V2TrapDestIpAddrType, asCmnAgentSnmpV1V2TrapDestIpAddr, asCmnAgentSnmpV1V2TrapDestPort, asCmnAgentShutdownReasonInfo, asCmnAgentShutdownReasonCode, 
				asCmnAgentInventoryItemDescription, asCmnAgentSnmpV1V2TrapDestRowStatus, asCmnAgentShutdownTrapEnabled, asCmnAgentInventoryType, asCmnAgentInventoryInstance, 
				asCmnAgentInventoryBoardNumber, asCmnAgentInventoryBoardRevision, asCmnAgentInventorySerialNumber, asCmnAgentInventoryHardwareIdentifier, asCmnAgentInventorySoftwareProductNumber, 
				asCmnAgentInventoryDescription, asCmnAgentInventoryCurrentSwVersion, asCmnAgentInventoryProductCode, asCmnAgentInventoryAssemblyNumber, asCmnAgentInventoryAssemblyRevision, 
				asCmnAgentInventoryCleiCode, asCmnAgentInventoryManufDate, asCmnAgentInventoryHardwareMacAddress, asCmnAgentInventoryManufName, asCmnAgentInventoryFactoryCode
				 }
			STATUS current
			DESCRIPTION 
				"Description."
			::= { asCmnAgentConformance 2 }

		
		-- 1.3.6.1.4.1.989.1.22.1.1.3
		asCmnAgentNotificationGroup NOTIFICATION-GROUP
			NOTIFICATIONS { asCmnAgentShutdownTrap }
			STATUS current
			DESCRIPTION 
				"Description."
			::= { asCmnAgentConformance 3 }

		
		-- 1.3.6.1.4.1.989.1.22.1.2
		asCmnAgentNotifications OBJECT IDENTIFIER ::= { asCmnAgent 2 }

		
		-- 1.3.6.1.4.1.989.1.22.1.2.0
		asCmnAgentTrapPrefix OBJECT IDENTIFIER ::= { asCmnAgentNotifications 0 }

		
		-- 1.3.6.1.4.1.989.1.22.1.2.0.1
		asCmnAgentShutdownTrap NOTIFICATION-TYPE
			OBJECTS { asCmnAgentShutdownReasonCode, asCmnAgentShutdownReasonInfo }
			STATUS current
			DESCRIPTION 
				"The trap is sent when the agent system controller identifies the condition critical to the system 
				operation e.g. overheating, and the imminent system shutdown is scheduled. 
				The exact reason of the shutdown is defined in ReasonCode object and additional details are given 
				in ReasonInfo trap object.
				This trap is not sent when the condition clears. Instead expect one of the start related traps (coldstart/warmstart).
				Default severity: Critical"
			::= { asCmnAgentTrapPrefix 1 }

		
		-- 1.3.6.1.4.1.989.1.22.1.2.1
		asCmnAgentTrapControlTable OBJECT-TYPE
			SYNTAX SEQUENCE OF AsCmnAgentTrapControlEntry
			MAX-ACCESS not-accessible
			STATUS current
			DESCRIPTION
				"Description."
			::= { asCmnAgentNotifications 1 }

		
		-- 1.3.6.1.4.1.989.1.22.1.2.1.1
		asCmnAgentTrapControlEntry OBJECT-TYPE
			SYNTAX AsCmnAgentTrapControlEntry
			MAX-ACCESS not-accessible
			STATUS current
			DESCRIPTION
				"Single row."
			INDEX { asCmnAgentTrapControlIndex }
			::= { asCmnAgentTrapControlTable 1 }

		
		AsCmnAgentTrapControlEntry ::=
			SEQUENCE { 
				asCmnAgentTrapControlIndex
					Integer32,
				asCmnAgentShutdownTrapEnabled
					AsCmnTcBooleanSwitch
			 }

		-- 1.3.6.1.4.1.989.1.22.1.2.1.1.1
		asCmnAgentTrapControlIndex OBJECT-TYPE
			SYNTAX Integer32 (1)
			MAX-ACCESS not-accessible
			STATUS current
			DESCRIPTION
				"Arbitrary index - one row only."
			::= { asCmnAgentTrapControlEntry 1 }

		
		-- 1.3.6.1.4.1.989.1.22.1.2.1.1.2
		asCmnAgentShutdownTrapEnabled OBJECT-TYPE
			SYNTAX AsCmnTcBooleanSwitch
			MAX-ACCESS read-write
			STATUS current
			DESCRIPTION
				"Enables/disables ShutdownTrap"
			DEFVAL { booleanTrue }
			::= { asCmnAgentTrapControlEntry 2 }

		
		-- 1.3.6.1.4.1.989.1.22.1.2.2
		asCmnAgentTrapStatusTable OBJECT-TYPE
			SYNTAX SEQUENCE OF AsCmnAgentTrapStatusEntry
			MAX-ACCESS not-accessible
			STATUS current
			DESCRIPTION
				"Reports current status of objects associated with traps. The table is designed for the single
				instance traps i.e. the table has only one row showing the status of all possible single instance traps
				defined in the system."
			::= { asCmnAgentNotifications 2 }

		
		-- 1.3.6.1.4.1.989.1.22.1.2.2.1
		asCmnAgentTrapStatusEntry OBJECT-TYPE
			SYNTAX AsCmnAgentTrapStatusEntry
			MAX-ACCESS not-accessible
			STATUS current
			DESCRIPTION
				"Single row."
			INDEX { asCmnAgentTrapStatusIndex }
			::= { asCmnAgentTrapStatusTable 1 }

		
		AsCmnAgentTrapStatusEntry ::=
			SEQUENCE { 
				asCmnAgentTrapStatusIndex
					Integer32,
				asCmnAgentShutdownReasonCode
					INTEGER,
				asCmnAgentShutdownReasonInfo
					DisplayString
			 }

		-- 1.3.6.1.4.1.989.1.22.1.2.2.1.1
		asCmnAgentTrapStatusIndex OBJECT-TYPE
			SYNTAX Integer32 (1)
			MAX-ACCESS not-accessible
			STATUS current
			DESCRIPTION
				"Arbitrary index - one row only."
			::= { asCmnAgentTrapStatusEntry 1 }

		
		-- 1.3.6.1.4.1.989.1.22.1.2.2.1.2
		asCmnAgentShutdownReasonCode OBJECT-TYPE
			SYNTAX INTEGER
				{
				noShutdown(0),
				reasonManualReset(1),
				reasonUnrecoverableSoftError(2),
				reasonHotBoardProtection(3)
				}
			MAX-ACCESS read-only
			STATUS current
			DESCRIPTION
				"Reports the reason the board (box) executed shut down as defined in the value list."
			::= { asCmnAgentTrapStatusEntry 2 }

		
		-- 1.3.6.1.4.1.989.1.22.1.2.2.1.3
		asCmnAgentShutdownReasonInfo OBJECT-TYPE
			SYNTAX DisplayString
			MAX-ACCESS read-only
			STATUS current
			DESCRIPTION
				"Implementation specific free text description of the trap raised. e.g.
				- Manual reset requested from console
				- System overheated"
			::= { asCmnAgentTrapStatusEntry 3 }

		
		-- 1.3.6.1.4.1.989.1.22.1.3
		asCmnAgentDevice OBJECT IDENTIFIER ::= { asCmnAgent 3 }

		
		-- 1.3.6.1.4.1.989.1.22.1.3.1
		asCmnAgentSnmpV1V2TrapDestTable OBJECT-TYPE
			SYNTAX SEQUENCE OF AsCmnAgentSnmpV1V2TrapDestEntry
			MAX-ACCESS not-accessible
			STATUS current
			DESCRIPTION
				"This table contains the configuration objects to configure the trap destination(s) for
				a V1 or V2 SNMP agent."
			::= { asCmnAgentDevice 1 }

		
		-- 1.3.6.1.4.1.989.1.22.1.3.1.1
		asCmnAgentSnmpV1V2TrapDestEntry OBJECT-TYPE
			SYNTAX AsCmnAgentSnmpV1V2TrapDestEntry
			MAX-ACCESS not-accessible
			STATUS current
			DESCRIPTION
				"This table is indexed by asCmnAgentSnmpV1V2TrapDestIndex."
			INDEX { asCmnAgentSnmpV1V2TrapDestIndex }
			::= { asCmnAgentSnmpV1V2TrapDestTable 1 }

		
		AsCmnAgentSnmpV1V2TrapDestEntry ::=
			SEQUENCE { 
				asCmnAgentSnmpV1V2TrapDestIndex
					Integer32,
				asCmnAgentSnmpV1V2TrapDestIpAddrType
					InetAddressType,
				asCmnAgentSnmpV1V2TrapDestIpAddr
					InetAddress,
				asCmnAgentSnmpV1V2TrapDestPort
					Integer32,
				asCmnAgentSnmpV1V2TrapDestRowStatus
					RowStatus
			 }

		-- 1.3.6.1.4.1.989.1.22.1.3.1.1.1
		asCmnAgentSnmpV1V2TrapDestIndex OBJECT-TYPE
			SYNTAX Integer32 (1..8)
			MAX-ACCESS not-accessible
			STATUS current
			DESCRIPTION
				"The index identifies the trap destination. The number of
				rows is limited to eight."
			::= { asCmnAgentSnmpV1V2TrapDestEntry 1 }

		
		-- 1.3.6.1.4.1.989.1.22.1.3.1.1.2
		asCmnAgentSnmpV1V2TrapDestIpAddrType OBJECT-TYPE
			SYNTAX InetAddressType
			MAX-ACCESS read-create
			STATUS current
			DESCRIPTION
				"The type of IP address used in the object
				asCmnAgentSnmpV1V2TrapDestV1V2TrapDestIpAddr."
			::= { asCmnAgentSnmpV1V2TrapDestEntry 2 }

		
		-- 1.3.6.1.4.1.989.1.22.1.3.1.1.3
		asCmnAgentSnmpV1V2TrapDestIpAddr OBJECT-TYPE
			SYNTAX InetAddress
			MAX-ACCESS read-create
			STATUS current
			DESCRIPTION
				"IP address of SNMP manager configured as a trap
				destination for versions V1 and V2 of SNMP. If this object
				is not created or empty the traps are not sent."
			::= { asCmnAgentSnmpV1V2TrapDestEntry 3 }

		
		-- 1.3.6.1.4.1.989.1.22.1.3.1.1.4
		asCmnAgentSnmpV1V2TrapDestPort OBJECT-TYPE
			SYNTAX Integer32 (0..65535)
			MAX-ACCESS read-create
			STATUS current
			DESCRIPTION
				"Port number of SNMP manager configured as a trap
				destination for versions V1 and V2 of SNMP."
			REFERENCE
				"Section 11.13.19.3.4.6 in IEEE 802.16-2004"
			::= { asCmnAgentSnmpV1V2TrapDestEntry 4 }

		
		-- 1.3.6.1.4.1.989.1.22.1.3.1.1.5
		asCmnAgentSnmpV1V2TrapDestRowStatus OBJECT-TYPE
			SYNTAX RowStatus
			MAX-ACCESS read-create
			STATUS current
			DESCRIPTION
				"This object is used to ensure that the write operation to
				multiple columns is guaranteed to be treated as atomic
				operation by agent."
			::= { asCmnAgentSnmpV1V2TrapDestEntry 5 }

		
		-- 1.3.6.1.4.1.989.1.22.1.3.2
		asCmnAgentInventoryTable OBJECT-TYPE
			SYNTAX SEQUENCE OF AsCmnAgentInventoryEntry
			MAX-ACCESS not-accessible
			STATUS current
			DESCRIPTION
				"This table would describe all inventories that constitute current product.
				(eg: 1 SDR + 2 SCRTs + 3 PSUs + ...)"
			::= { asCmnAgentDevice 2 }

		
		-- 1.3.6.1.4.1.989.1.22.1.3.2.1
		asCmnAgentInventoryEntry OBJECT-TYPE
			SYNTAX AsCmnAgentInventoryEntry
			MAX-ACCESS not-accessible
			STATUS current
			DESCRIPTION
				"Each entry would describe the hardware & software properties of the inventory 
				that is part of current product. "
			INDEX { asCmnAgentInventoryItem }
			::= { asCmnAgentInventoryTable 1 }

		
		AsCmnAgentInventoryEntry ::=
			SEQUENCE { 
				asCmnAgentInventoryItem
					Integer32,
				asCmnAgentInventoryType
					INTEGER,
				asCmnAgentInventoryInstance
					Integer32,
				asCmnAgentInventoryBoardNumber
					OCTET STRING,
				asCmnAgentInventoryBoardRevision
					OCTET STRING,
				asCmnAgentInventorySerialNumber
					OCTET STRING,
				asCmnAgentInventoryHardwareIdentifier
					Unsigned32,
				asCmnAgentInventorySoftwareProductNumber
					OCTET STRING,
				asCmnAgentInventoryDescription
					DisplayString,
				asCmnAgentInventoryCurrentSwVersion
					OCTET STRING,
				asCmnAgentInventoryProductCode
					OCTET STRING,
				asCmnAgentInventoryAssemblyNumber
					OCTET STRING,
				asCmnAgentInventoryAssemblyRevision
					OCTET STRING,
				asCmnAgentInventoryCleiCode
					OCTET STRING,
				asCmnAgentInventoryItemDescription
					DisplayString,
				asCmnAgentInventoryManufDate
					OCTET STRING,
				asCmnAgentInventoryHardwareMacAddress
					MacAddress,
				asCmnAgentInventoryManufName
					OCTET STRING,
				asCmnAgentInventoryFactoryCode
					OCTET STRING
			 }

		-- 1.3.6.1.4.1.989.1.22.1.3.2.1.1
		asCmnAgentInventoryItem OBJECT-TYPE
			SYNTAX Integer32 (1..65535)
			MAX-ACCESS not-accessible
			STATUS current
			DESCRIPTION
				"Uniquely identifies each inventory that constitute current product."
			::= { asCmnAgentInventoryEntry 1 }

		
		-- 1.3.6.1.4.1.989.1.22.1.3.2.1.2
		asCmnAgentInventoryType OBJECT-TYPE
			SYNTAX INTEGER
				{
				other(0),
				system(1),
				equipment(2)
				}
			MAX-ACCESS read-only
			STATUS current
			DESCRIPTION
				"Definition of available inventory types.
				system: top level inventory - identification of a product as a whole BS or SS. 
				    It doesn't have to have all the numbers filled.
				equipment: board level inventory - one row for inventory holding board (e.g.SDR, SCRT)
				    It has most of the numbers filled.
				other: used if none of the above fits the purpose.
				"
			::= { asCmnAgentInventoryEntry 2 }

		
		-- 1.3.6.1.4.1.989.1.22.1.3.2.1.3
		asCmnAgentInventoryInstance OBJECT-TYPE
			SYNTAX Integer32 (0..255)
			MAX-ACCESS read-only
			STATUS current
			DESCRIPTION
				"Instance of the inventory item for items having the same part number.
				e.g. SCRT instance 1 and 2 have the same BoardNumber and have 
				different SerialNumber.
				"
			::= { asCmnAgentInventoryEntry 3 }

		
		-- 1.3.6.1.4.1.989.1.22.1.3.2.1.4
		asCmnAgentInventoryBoardNumber OBJECT-TYPE
			SYNTAX OCTET STRING (SIZE (0..64))
			MAX-ACCESS read-only
			STATUS current
			DESCRIPTION
				"Octet string to identify the board number if relevant to this inventory type:
				eg: '303-xxxx-xxx'"
			::= { asCmnAgentInventoryEntry 4 }

		
		-- 1.3.6.1.4.1.989.1.22.1.3.2.1.5
		asCmnAgentInventoryBoardRevision OBJECT-TYPE
			SYNTAX OCTET STRING (SIZE (0..64))
			MAX-ACCESS read-only
			STATUS current
			DESCRIPTION
				"Octet string to identify the the revision of the board identified with BoardNumber."
			::= { asCmnAgentInventoryEntry 5 }

		
		-- 1.3.6.1.4.1.989.1.22.1.3.2.1.6
		asCmnAgentInventorySerialNumber OBJECT-TYPE
			SYNTAX OCTET STRING (SIZE (0..64))
			MAX-ACCESS read-only
			STATUS current
			DESCRIPTION
				"Octet string to uniquely identify a physical entity.
				eg: x########x####x"
			::= { asCmnAgentInventoryEntry 6 }

		
		-- 1.3.6.1.4.1.989.1.22.1.3.2.1.7
		asCmnAgentInventoryHardwareIdentifier OBJECT-TYPE
			SYNTAX Unsigned32 (0..2147483647)
			MAX-ACCESS read-only
			STATUS current
			DESCRIPTION
				"Identifier, which is read-only, hardwired in the schematics,
				design specific hardware identifier. 
				It can contain info about BOM and board version. 
				E.g. for BS it is defined as follows:
				7-5:bom_var
				4-0:Version
				"
			::= { asCmnAgentInventoryEntry 7 }

		
		-- 1.3.6.1.4.1.989.1.22.1.3.2.1.8
		asCmnAgentInventorySoftwareProductNumber OBJECT-TYPE
			SYNTAX OCTET STRING (SIZE (0..64))
			MAX-ACCESS read-only
			STATUS current
			DESCRIPTION
				"Octet string to identify the software product running 
				on the current inventory. Empty string when inventory item 
				doesn't have software or the software doesn't have software 
				produlct like identification."
			::= { asCmnAgentInventoryEntry 8 }

		
		-- 1.3.6.1.4.1.989.1.22.1.3.2.1.9
		asCmnAgentInventoryDescription OBJECT-TYPE
			SYNTAX DisplayString
			MAX-ACCESS read-only
			STATUS current
			DESCRIPTION
				"User friendly description about current inventory as entered by embedded software."
			::= { asCmnAgentInventoryEntry 9 }

		
		-- 1.3.6.1.4.1.989.1.22.1.3.2.1.10
		asCmnAgentInventoryCurrentSwVersion OBJECT-TYPE
			SYNTAX OCTET STRING (SIZE (0..64))
			MAX-ACCESS read-only
			STATUS current
			DESCRIPTION
				"Current software version running on this inventory item.
				There might be different software versions running on different
				instances of the same inventory part number.
				eg: reflecting software versions running on multiple SCRTs"
			::= { asCmnAgentInventoryEntry 10 }

		
		-- 1.3.6.1.4.1.989.1.22.1.3.2.1.11
		asCmnAgentInventoryProductCode OBJECT-TYPE
			SYNTAX OCTET STRING (SIZE (0..64))
			MAX-ACCESS read-only
			STATUS current
			DESCRIPTION
				"String based code dentifying product specified by this inventory row.
				e.g. SCRT-1-4.9T"
			::= { asCmnAgentInventoryEntry 11 }

		
		-- 1.3.6.1.4.1.989.1.22.1.3.2.1.12
		asCmnAgentInventoryAssemblyNumber OBJECT-TYPE
			SYNTAX OCTET STRING (SIZE (0..64))
			MAX-ACCESS read-only
			STATUS current
			DESCRIPTION
				"Number identifying assembly of this inventory item.
				e.g. 503-xxxx-xxx"
			::= { asCmnAgentInventoryEntry 12 }

		
		-- 1.3.6.1.4.1.989.1.22.1.3.2.1.13
		asCmnAgentInventoryAssemblyRevision OBJECT-TYPE
			SYNTAX OCTET STRING (SIZE (0..64))
			MAX-ACCESS read-only
			STATUS current
			DESCRIPTION
				"Revision of the assembly identified by AssemblyNumber."
			::= { asCmnAgentInventoryEntry 13 }

		
		-- 1.3.6.1.4.1.989.1.22.1.3.2.1.14
		asCmnAgentInventoryCleiCode OBJECT-TYPE
			SYNTAX OCTET STRING (SIZE (0..64))
			MAX-ACCESS read-only
			STATUS current
			DESCRIPTION
				"Common Language Equipment Identification. As defined by OEM / PM."
			::= { asCmnAgentInventoryEntry 14 }

		
		-- 1.3.6.1.4.1.989.1.22.1.3.2.1.15
		asCmnAgentInventoryItemDescription OBJECT-TYPE
			SYNTAX DisplayString
			MAX-ACCESS read-only
			STATUS current
			DESCRIPTION
				"User friendly description about current inventory as entered during manufacturing."
			::= { asCmnAgentInventoryEntry 15 }

		
		-- 1.3.6.1.4.1.989.1.22.1.3.2.1.16
		asCmnAgentInventoryManufDate OBJECT-TYPE
			SYNTAX OCTET STRING (SIZE (0..64))
			MAX-ACCESS read-only
			STATUS current
			DESCRIPTION
				"Date of Manufacture entered as string. Expected format: dd.mm.yyyy"
			::= { asCmnAgentInventoryEntry 16 }

		
		-- 1.3.6.1.4.1.989.1.22.1.3.2.1.17
		asCmnAgentInventoryHardwareMacAddress OBJECT-TYPE
			SYNTAX MacAddress
			MAX-ACCESS read-only
			STATUS current
			DESCRIPTION
				"Mac Address of the Front Panel Ethernet or another Mac Address selected for the purpose 
				of identification of this inventory item."
			::= { asCmnAgentInventoryEntry 17 }

		
		-- 1.3.6.1.4.1.989.1.22.1.3.2.1.18
		asCmnAgentInventoryManufName OBJECT-TYPE
			SYNTAX OCTET STRING (SIZE (0..8))
			MAX-ACCESS read-only
			STATUS current
			DESCRIPTION
				"Name of manufacturer entered as a string.
				Maximum 8 characters."
			::= { asCmnAgentInventoryEntry 18 }

		
		-- 1.3.6.1.4.1.989.1.22.1.3.2.1.19
		asCmnAgentInventoryFactoryCode OBJECT-TYPE
			SYNTAX OCTET STRING (SIZE (0..6))
			MAX-ACCESS read-only
			STATUS current
			DESCRIPTION
				"Factory code of manufacturer entered as a string.
				Maximum 6 characters."
			::= { asCmnAgentInventoryEntry 19 }

		
	
	END

--
-- ASCMN-AGENT-MIB.mib
--
