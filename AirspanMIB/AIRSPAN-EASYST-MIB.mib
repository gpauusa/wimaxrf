--
-- AIRSPAN-EASYST-MIB.mib
-- MIB generated by MG-SOFT Visual MIB Builder Version 5.0  Build 250
-- Thursday, January 17, 2008 at 09:35:27
--

--  *****************************************************************
-- AIRSPAN-EASYST-MIB.txt:  Airspan MIB root tree
-- Copyright (c) 2003 by Airspan Networks, Inc.
-- All rights reserved.
-- 
-- *****************************************************************

	AIRSPAN-EASYST-MIB DEFINITIONS ::= BEGIN
 
		IMPORTS
			airspanProducts			
				FROM AIRSPAN-MIB			
			InetAddressType, InetAddress			
				FROM INET-ADDRESS-MIB			
			OBJECT-GROUP			
				FROM SNMPv2-CONF			
			Integer32, OBJECT-TYPE, MODULE-IDENTITY			
				FROM SNMPv2-SMI			
			DisplayString, TimeStamp, TEXTUAL-CONVENTION			
				FROM SNMPv2-TC;
	
	
		-- 1.3.6.1.4.1.989.1.16.3
		asMaxSS MODULE-IDENTITY 
			LAST-UPDATED "200608021809Z"		-- August 02, 2006 at 18:09 GMT
			ORGANIZATION 
				"Airspan"
			CONTACT-INFO 
				"Contact-info."
			DESCRIPTION 
				"Description."
			REVISION "200512091631Z"		-- December 09, 2005 at 16:31 GMT
			DESCRIPTION 
				"Draft 1
				- initial version
				"
			REVISION "200601121402Z"		-- January 12, 2006 at 14:02 GMT
			DESCRIPTION 
				"Draft 2
				- Added objects:
				  - asMaxSSCmUpgrVersionToActivate
				  - asMaxSSCmUpgrServerAddrType
				  - asMaxSSCmUpgrErrorString
				  - asMaxSSCmUpgrActiveVersion
				  - asMaxSSCmUpgrActiveDetails
				  - asMaxSSCmUpgrStandbyVersion
				  - asMaxSSCmUpgrStandbyDetails
				  - asMaxSSCmUpgrTypeDescription
				  - asMaxSSConformance branch added.
				
				- Removed objects:
				  - asMaxSSCmUpgrIndex
				
				- Modified objects:
				  - asMaxSSCmUpgrType made not accessible.
				"
			REVISION "200602021244Z"		-- February 02, 2006 at 12:44 GMT
			DESCRIPTION 
				"ActiveVersion, ActiveDetails, StandbyVersion and StandbyDetails are moved to a separate table."
			REVISION "200602021421Z"		-- February 02, 2006 at 14:21 GMT
			DESCRIPTION 
				"SR2.0 final.
				Description for asMaxSSCmCfgUpgradeEntry corrected."
			REVISION "200608021809Z"		-- August 02, 2006 at 18:09 GMT
			DESCRIPTION 
				"SR3.0 (draft1)
				Added two actions to object asMaxSSCmUpgrAction:
				  reset, swapAndReset
				Added two columns to table asMaxSSCmVersionTable: 
				  asMaxSSCmRunningVersion, asMaxSSCmRunningDetails"
			REVISION "200801141756Z"		-- January 14, 2008 at 17:56 GMT
			DESCRIPTION 
				"Draft 3:
				EBanks added.
				BankStatus values moved to TextualConvention.
				new value hidden included to BankStatus enumeration.
				Descriptions changed."
			REVISION "200801170934Z"		-- January 17, 2008 at 09:34 GMT
			DESCRIPTION 
				"Draft 4:
				EBankVersion and Status fields set as read-only."
			::= { asMax 3 }

		
	
--
-- Textual conventions
--
	
		BankStatus ::= TEXTUAL-CONVENTION
			STATUS current
			DESCRIPTION 
				"empty - bank does not have code in it.
				active - bank currently used as primary. It will be used to boot up after hard reset.
				standby - bank currently used as standby. It will be used to swap with primary when doing activate(swapToPrimary)
				hidden - bank contains code, but not used as primary or standby."
			SYNTAX INTEGER
				{
				empty(0),
				active(1),
				standby(2),
				hidden(3)
				}

	
--
-- Node definitions
--
	
-- #################################################################
-- 
-- Groups within the WipMax Common MIB (Common)
-- 
-- #################################################################
		-- 1.3.6.1.4.1.989.1.16
		asMax OBJECT IDENTIFIER ::= { airspanProducts 16 }

		
		-- 1.3.6.1.4.1.989.1.16.3.1
		asMaxSSCommon OBJECT IDENTIFIER ::= { asMaxSS 1 }

		
		-- 1.3.6.1.4.1.989.1.16.3.1.1
		asMaxSSCmMonitor OBJECT IDENTIFIER ::= { asMaxSSCommon 1 }

		
-- -----------------------------------------------------------------
-- Common Monitor Group -  asMaxSSCmMonitor
-- -----------------------------------------------------------------
		-- 1.3.6.1.4.1.989.1.16.3.1.1.1
		asMaxSSMonPcToTargetBuff OBJECT-TYPE
			SYNTAX OCTET STRING
			MAX-ACCESS read-write
			STATUS current
			DESCRIPTION
				"The buffer that is received by the PC monitor tool."
			::= { asMaxSSCmMonitor 1 }

		
		-- 1.3.6.1.4.1.989.1.16.3.1.1.2
		asMaxSSMonTargetToPcBuff OBJECT-TYPE
			SYNTAX OCTET STRING
			MAX-ACCESS read-write
			STATUS current
			DESCRIPTION
				"The buffer that is received by the monitor task."
			::= { asMaxSSCmMonitor 2 }

		
		-- 1.3.6.1.4.1.989.1.16.3.1.1.3
		asMaxSSMonSnmpRelayStatus OBJECT-TYPE
			SYNTAX INTEGER
				{
				enable(1),
				disable(2)
				}
			MAX-ACCESS read-write
			STATUS current
			DESCRIPTION
				"This attribute indicates whether the monitor tool
				can query the target via SNMP."
			::= { asMaxSSCmMonitor 3 }

		
		-- 1.3.6.1.4.1.989.1.16.3.1.2
		asMaxSSCmCfg OBJECT IDENTIFIER ::= { asMaxSSCommon 2 }

		
-- -----------------------------------------------------------------
-- Common Configuration Group -  asMaxSSCmCfg
-- -----------------------------------------------------------------
		-- 1.3.6.1.4.1.989.1.16.3.1.2.1
		asMaxSSCmCfgUpgradeTable OBJECT-TYPE
			SYNTAX SEQUENCE OF AsMaxSSCmCfgUpgradeEntry
			MAX-ACCESS not-accessible
			STATUS current
			DESCRIPTION
				"This table contains objects associated with SS software
				upgrades.
				"
			::= { asMaxSSCmCfg 1 }

		
		-- 1.3.6.1.4.1.989.1.16.3.1.2.1.1
		asMaxSSCmCfgUpgradeEntry OBJECT-TYPE
			SYNTAX AsMaxSSCmCfgUpgradeEntry
			MAX-ACCESS not-accessible
			STATUS current
			DESCRIPTION
				"This table may have multiple entries, and is indexed
				by asMaxSSCmUpgrType."
			INDEX { asMaxSSCmUpgrType }
			::= { asMaxSSCmCfgUpgradeTable 1 }

		
		AsMaxSSCmCfgUpgradeEntry ::=
			SEQUENCE { 
				asMaxSSCmUpgrType
					INTEGER,
				asMaxSSCmUpgrFileToInstall
					DisplayString,
				asMaxSSCmUpgrVersionToActivate
					DisplayString,
				asMaxSSCmUpgrServerType
					INTEGER,
				asMaxSSCmUpgrServerAddrType
					InetAddressType,
				asMaxSSCmUpgrServerAddr
					InetAddress,
				asMaxSSCmUpgrServerUser
					DisplayString,
				asMaxSSCmUpgrServerPasswd
					DisplayString,
				asMaxSSCmUpgrAction
					INTEGER,
				asMaxSSCmUpgrProgress
					INTEGER,
				asMaxSSCmUpgrErrorCode
					Integer32,
				asMaxSSCmUpgrErrorString
					DisplayString,
				asMaxSSCmUpgrTimeStamp
					TimeStamp,
				asMaxSSCmUpgrTypeDescription
					DisplayString
			 }

		-- 1.3.6.1.4.1.989.1.16.3.1.2.1.1.1
		asMaxSSCmUpgrType OBJECT-TYPE
			SYNTAX INTEGER
				{
				codeUpgrade(1),
				zipcodeUpgrade(2),
				bootUpgrade(3),
				romParameters(4)
				}
			MAX-ACCESS not-accessible
			STATUS current
			DESCRIPTION
				"The type is used for various types of download. Used as index field."
			::= { asMaxSSCmCfgUpgradeEntry 1 }

		
		-- 1.3.6.1.4.1.989.1.16.3.1.2.1.1.2
		asMaxSSCmUpgrFileToInstall OBJECT-TYPE
			SYNTAX DisplayString
			MAX-ACCESS read-write
			STATUS current
			DESCRIPTION
				"The filename is a fully qualified directory path name,
				indicating where the software is located."
			::= { asMaxSSCmCfgUpgradeEntry 2 }

		
		-- 1.3.6.1.4.1.989.1.16.3.1.2.1.1.3
		asMaxSSCmUpgrVersionToActivate OBJECT-TYPE
			SYNTAX DisplayString
			MAX-ACCESS read-write
			STATUS current
			DESCRIPTION
				"This column is used in conjunction with any of the upgrade action given by column asMaxSSCmUpgrAction.
				This column defines the version of the software to act upon. 
				
				If the version set by this field is not installed, the requested action terminates with an error.
				
				Providing asMaxSSCmUpgrVersionToActivate with asMaxSSCmUpgrAction is mandatory.
				SS would use it to decide 
				 - on which physical bank (bank0, bank1, Ebank0, EBank1) to download.
				 - activate(swapToPrimary) this version only if possible. (ie, in the standby bank), otherwise report error.
				 - reset this version only if possible. (ie, in the primary bank), othrwise report error."
			::= { asMaxSSCmCfgUpgradeEntry 3 }

		
		-- 1.3.6.1.4.1.989.1.16.3.1.2.1.1.4
		asMaxSSCmUpgrServerType OBJECT-TYPE
			SYNTAX INTEGER
				{
				ftp(1),
				tftp(2),
				web(3)
				}
			MAX-ACCESS read-write
			STATUS current
			DESCRIPTION
				"defines 'asMaxSSCmUpgrServerAddr' Type for download. (like ftp, tftp, etc.)"
			::= { asMaxSSCmCfgUpgradeEntry 4 }

		
		-- 1.3.6.1.4.1.989.1.16.3.1.2.1.1.5
		asMaxSSCmUpgrServerAddrType OBJECT-TYPE
			SYNTAX InetAddressType
			MAX-ACCESS read-write
			STATUS current
			DESCRIPTION
				"Defines the type of 'asMaxSSCmUpgrServerAddr'. (like ipv4, ipv6, etc)"
			::= { asMaxSSCmCfgUpgradeEntry 5 }

		
		-- 1.3.6.1.4.1.989.1.16.3.1.2.1.1.6
		asMaxSSCmUpgrServerAddr OBJECT-TYPE
			SYNTAX InetAddress
			MAX-ACCESS read-write
			STATUS current
			DESCRIPTION
				"Defines the inet address of the server the file to install is available to download from."
			::= { asMaxSSCmCfgUpgradeEntry 6 }

		
		-- 1.3.6.1.4.1.989.1.16.3.1.2.1.1.7
		asMaxSSCmUpgrServerUser OBJECT-TYPE
			SYNTAX DisplayString
			MAX-ACCESS read-write
			STATUS current
			DESCRIPTION
				"A user name for a download Server, used for FTP servers."
			::= { asMaxSSCmCfgUpgradeEntry 7 }

		
		-- 1.3.6.1.4.1.989.1.16.3.1.2.1.1.8
		asMaxSSCmUpgrServerPasswd OBJECT-TYPE
			SYNTAX DisplayString
			MAX-ACCESS read-write
			STATUS current
			DESCRIPTION
				"A password for a download Server, used for FTP servers."
			::= { asMaxSSCmCfgUpgradeEntry 8 }

		
		-- 1.3.6.1.4.1.989.1.16.3.1.2.1.1.9
		asMaxSSCmUpgrAction OBJECT-TYPE
			SYNTAX INTEGER
				{
				download(1),
				activate(2),
				abortDownload(3),
				downloadAndActivate(4),
				display(5),
				reset(6),
				swapAndReset(7)
				}
			MAX-ACCESS read-write
			STATUS current
			DESCRIPTION
				"Setting this value will behave as explained below.
				
				download(1) causes the SS to initiate the software download from  a server (e.g. software image server). 
				SS would use the field asMaxSSCmUpgrVersionToActivate to decide which bank (Bank0, Bank1, EBank0, EBank1) to download to.
				
				activate(2) will swap SS software specified by 'asMaxSSCmUpgrVersionToActivate' to the primary bank from the standby bank.
				If the 'asMaxSSCmUpgrVersionToActivate' does not exist in the standby bank, it should report error instead.
				
				abortDownload(3) will abort current upgrade action.
				
				downloadAndActivate(4) will perform both actions. 
				
				reset(6) will force SS to reboot and start running software specified by 'asMaxSSCmUpgrVersionToActivate' from active bank.
				If the 'asMaxSSCmUpgrVersionToActivate' does not exist in the active bank, it should report error instead.
				
				swapAndReset(7) will force SS to perform swap of banks and reset as a single operation. 
				
				Reading this object returns: last operation while not completed , before activation or error occured
				                             display(5) after a success download and activation. "
			::= { asMaxSSCmCfgUpgradeEntry 9 }

		
		-- 1.3.6.1.4.1.989.1.16.3.1.2.1.1.10
		asMaxSSCmUpgrProgress OBJECT-TYPE
			SYNTAX INTEGER (0..100)
			MAX-ACCESS read-only
			STATUS current
			DESCRIPTION
				"This value indicates the progress of software download in
				percentage. For example, 50 means 50% of SS software has
				been downloaded."
			::= { asMaxSSCmCfgUpgradeEntry 10 }

		
		-- 1.3.6.1.4.1.989.1.16.3.1.2.1.1.11
		asMaxSSCmUpgrErrorCode OBJECT-TYPE
			SYNTAX Integer32
			MAX-ACCESS read-only
			STATUS current
			DESCRIPTION
				"Error code during process or 0 for success on last action."
			::= { asMaxSSCmCfgUpgradeEntry 11 }

		
		-- 1.3.6.1.4.1.989.1.16.3.1.2.1.1.12
		asMaxSSCmUpgrErrorString OBJECT-TYPE
			SYNTAX DisplayString
			MAX-ACCESS read-only
			STATUS current
			DESCRIPTION
				"Implementation specific reporting message. If operation is 
				terminated with an error this object will report error details.
				"
			::= { asMaxSSCmCfgUpgradeEntry 12 }

		
		-- 1.3.6.1.4.1.989.1.16.3.1.2.1.1.13
		asMaxSSCmUpgrTimeStamp OBJECT-TYPE
			SYNTAX TimeStamp
			MAX-ACCESS read-only
			STATUS current
			DESCRIPTION
				"This time stamp indicates when the SS software was last
				downloaded or activated."
			::= { asMaxSSCmCfgUpgradeEntry 13 }

		
		-- 1.3.6.1.4.1.989.1.16.3.1.2.1.1.18
		asMaxSSCmUpgrTypeDescription OBJECT-TYPE
			SYNTAX DisplayString
			MAX-ACCESS read-only
			STATUS current
			DESCRIPTION
				"Describes the role of the asMaxSSCmUpgrType."
			::= { asMaxSSCmCfgUpgradeEntry 18 }

		
		-- 1.3.6.1.4.1.989.1.16.3.1.2.2
		asMaxSSCmCfgInfoTable OBJECT-TYPE
			SYNTAX SEQUENCE OF AsMaxSSCmCfgInfoEntry
			MAX-ACCESS not-accessible
			STATUS current
			DESCRIPTION
				"This table contains objects associated with 
				information about both active and standby code banks of SS software.
				First row is a current banks status,
				Second row is a previous banks status and so on."
			::= { asMaxSSCmCfg 2 }

		
		-- 1.3.6.1.4.1.989.1.16.3.1.2.2.1
		asMaxSSCmCfgInfoEntry OBJECT-TYPE
			SYNTAX AsMaxSSCmCfgInfoEntry
			MAX-ACCESS not-accessible
			STATUS current
			DESCRIPTION
				"This table will have multiple entries presenting a few last downloads, and is indexed
				by asMaxSSCmCfgIndex."
			INDEX { asMaxSSCmCfgIndex }
			::= { asMaxSSCmCfgInfoTable 1 }

		
		AsMaxSSCmCfgInfoEntry ::=
			SEQUENCE { 
				asMaxSSCmCfgIndex
					Integer32,
				asMaxSSCmCfgBank0Version
					DisplayString,
				asMaxSSCmCfgBank0Status
					BankStatus,
				asMaxSSCmCfgBank1Version
					DisplayString,
				asMaxSSCmCfgBank1Status
					BankStatus,
				asMaxSSCmCfgEBank0Version
					Integer32,
				asMaxSSCmCfgEBank0Status
					BankStatus,
				asMaxSSCmCfgEBank1Version
					Integer32,
				asMaxSSCmCfgEBank1Status
					BankStatus
			 }

		-- 1.3.6.1.4.1.989.1.16.3.1.2.2.1.1
		asMaxSSCmCfgIndex OBJECT-TYPE
			SYNTAX Integer32 (1..2147483647)
			MAX-ACCESS read-only
			STATUS current
			DESCRIPTION
				"A table index."
			::= { asMaxSSCmCfgInfoEntry 1 }

		
		-- 1.3.6.1.4.1.989.1.16.3.1.2.2.1.2
		asMaxSSCmCfgBank0Version OBJECT-TYPE
			SYNTAX DisplayString
			MAX-ACCESS read-only
			STATUS current
			DESCRIPTION
				"Information about software version in bank 0 ."
			::= { asMaxSSCmCfgInfoEntry 2 }

		
		-- 1.3.6.1.4.1.989.1.16.3.1.2.2.1.3
		asMaxSSCmCfgBank0Status OBJECT-TYPE
			SYNTAX BankStatus
			MAX-ACCESS read-only
			STATUS current
			DESCRIPTION
				"Status of software version in bank 0, active(1) means it will be used to boot up after hard reset."
			::= { asMaxSSCmCfgInfoEntry 3 }

		
		-- 1.3.6.1.4.1.989.1.16.3.1.2.2.1.4
		asMaxSSCmCfgBank1Version OBJECT-TYPE
			SYNTAX DisplayString
			MAX-ACCESS read-only
			STATUS current
			DESCRIPTION
				"Information about software version in bank 1."
			::= { asMaxSSCmCfgInfoEntry 4 }

		
		-- 1.3.6.1.4.1.989.1.16.3.1.2.2.1.5
		asMaxSSCmCfgBank1Status OBJECT-TYPE
			SYNTAX BankStatus
			MAX-ACCESS read-only
			STATUS current
			DESCRIPTION
				"Status of software version in bank 1, active(1) means it will be used to boot up after hard reset."
			::= { asMaxSSCmCfgInfoEntry 5 }

		
		-- 1.3.6.1.4.1.989.1.16.3.1.2.2.1.6
		asMaxSSCmCfgEBank0Version OBJECT-TYPE
			SYNTAX Integer32
			MAX-ACCESS read-only
			STATUS current
			DESCRIPTION
				"Information about software version in E bank 0."
			::= { asMaxSSCmCfgInfoEntry 6 }

		
		-- 1.3.6.1.4.1.989.1.16.3.1.2.2.1.7
		asMaxSSCmCfgEBank0Status OBJECT-TYPE
			SYNTAX BankStatus
			MAX-ACCESS read-only
			STATUS current
			DESCRIPTION
				"Status of software version in E bank 0, active(1) means it will be used to boot up after hard reset."
			::= { asMaxSSCmCfgInfoEntry 7 }

		
		-- 1.3.6.1.4.1.989.1.16.3.1.2.2.1.8
		asMaxSSCmCfgEBank1Version OBJECT-TYPE
			SYNTAX Integer32
			MAX-ACCESS read-only
			STATUS current
			DESCRIPTION
				"Information about software version in E bank 1."
			::= { asMaxSSCmCfgInfoEntry 8 }

		
		-- 1.3.6.1.4.1.989.1.16.3.1.2.2.1.9
		asMaxSSCmCfgEBank1Status OBJECT-TYPE
			SYNTAX BankStatus
			MAX-ACCESS read-only
			STATUS current
			DESCRIPTION
				"Status of software version in E bank 1, active(1) means it will be used to boot up after hard reset."
			::= { asMaxSSCmCfgInfoEntry 9 }

		
		-- 1.3.6.1.4.1.989.1.16.3.1.2.3
		asMaxSSCmCfgSwapBanks OBJECT-TYPE
			SYNTAX INTEGER
				{
				idle(1),
				swap(2),
				error(3)
				}
			MAX-ACCESS read-write
			STATUS current
			DESCRIPTION
				"On write  - swap(2) command will activate stand-by version and 
				the active version will become stand-by after the next reset.
				On read   - idle(1)  reports success on last swap,
				 error(3) reports error."
			::= { asMaxSSCmCfg 3 }

		
		-- 1.3.6.1.4.1.989.1.16.3.1.2.4
		asMaxSSCmCfgDeleteStandbyBank OBJECT-TYPE
			SYNTAX INTEGER
				{
				idle(1),
				delete(2),
				error(3)
				}
			MAX-ACCESS read-write
			STATUS current
			DESCRIPTION
				"On write  - delete(2) command will erase stand-by version.
				On read   - idle(1)  reports success on last delete,
				            error(3) reports error."
			::= { asMaxSSCmCfg 4 }

		
		-- 1.3.6.1.4.1.989.1.16.3.1.2.5
		asMaxSSCmVersionTable OBJECT-TYPE
			SYNTAX SEQUENCE OF AsMaxSSCmVersionEntry
			MAX-ACCESS not-accessible
			STATUS current
			DESCRIPTION
				"Description."
			::= { asMaxSSCmCfg 5 }

		
		-- 1.3.6.1.4.1.989.1.16.3.1.2.5.1
		asMaxSSCmVersionEntry OBJECT-TYPE
			SYNTAX AsMaxSSCmVersionEntry
			MAX-ACCESS not-accessible
			STATUS current
			DESCRIPTION
				"Description."
			INDEX { asMaxSSCmUpgrType }
			::= { asMaxSSCmVersionTable 1 }

		
		AsMaxSSCmVersionEntry ::=
			SEQUENCE { 
				asMaxSSCmActiveVersion
					DisplayString,
				asMaxSSCmActiveDetails
					DisplayString,
				asMaxSSCmStandbyVersion
					DisplayString,
				asMaxSSCmStandbyDetails
					DisplayString,
				asMaxSSCmRunningVersion
					DisplayString,
				asMaxSSCmRunningDetails
					DisplayString
			 }

		-- 1.3.6.1.4.1.989.1.16.3.1.2.5.1.1
		asMaxSSCmActiveVersion OBJECT-TYPE
			SYNTAX DisplayString
			MAX-ACCESS read-only
			STATUS current
			DESCRIPTION
				"The version string of the active (running) software.
				The software from active bank will be running only after SS reset.
				This can be triggered by setting asMaxSSCmUpgrAction to reset(6)."
			::= { asMaxSSCmVersionEntry 1 }

		
		-- 1.3.6.1.4.1.989.1.16.3.1.2.5.1.2
		asMaxSSCmActiveDetails OBJECT-TYPE
			SYNTAX DisplayString
			MAX-ACCESS read-only
			STATUS current
			DESCRIPTION
				"Details of the active (running) software. The contents of 
				this object is implementation specific.
				The software from active bank will be running only after SS reset.
				This can be triggered by setting asMaxSSCmUpgrAction to reset(6)."
			::= { asMaxSSCmVersionEntry 2 }

		
		-- 1.3.6.1.4.1.989.1.16.3.1.2.5.1.3
		asMaxSSCmStandbyVersion OBJECT-TYPE
			SYNTAX DisplayString
			MAX-ACCESS read-only
			STATUS current
			DESCRIPTION
				"The version string of the standby software."
			::= { asMaxSSCmVersionEntry 3 }

		
		-- 1.3.6.1.4.1.989.1.16.3.1.2.5.1.4
		asMaxSSCmStandbyDetails OBJECT-TYPE
			SYNTAX DisplayString
			MAX-ACCESS read-only
			STATUS current
			DESCRIPTION
				"Details of the standby (backup) software. The contents of 
				this object is implementation specific."
			::= { asMaxSSCmVersionEntry 4 }

		
		-- 1.3.6.1.4.1.989.1.16.3.1.2.5.1.5
		asMaxSSCmRunningVersion OBJECT-TYPE
			SYNTAX DisplayString
			MAX-ACCESS read-only
			STATUS current
			DESCRIPTION
				"The version string of the software the target is currently running."
			::= { asMaxSSCmVersionEntry 5 }

		
		-- 1.3.6.1.4.1.989.1.16.3.1.2.5.1.6
		asMaxSSCmRunningDetails OBJECT-TYPE
			SYNTAX DisplayString
			MAX-ACCESS read-only
			STATUS current
			DESCRIPTION
				"Details of the software the target is currently running.
				The contents of this object is implementation specific."
			::= { asMaxSSCmVersionEntry 6 }

		
		-- 1.3.6.1.4.1.989.1.16.3.1.3
		asMaxSSCmTest OBJECT IDENTIFIER ::= { asMaxSSCommon 3 }

		
-- -----------------------------------------------------------------
-- Common Testing -  asMaxSSCmTest
-- -----------------------------------------------------------------
		-- 1.3.6.1.4.1.989.1.16.3.1.3.1
		asMaxSSCmTestTable OBJECT-TYPE
			SYNTAX SEQUENCE OF AsMaxSSCmTestEntry
			MAX-ACCESS not-accessible
			STATUS current
			DESCRIPTION
				"Table used to activate an internal debug procedures."
			::= { asMaxSSCmTest 1 }

		
		-- 1.3.6.1.4.1.989.1.16.3.1.3.1.1
		asMaxSSCmTestEntry OBJECT-TYPE
			SYNTAX AsMaxSSCmTestEntry
			MAX-ACCESS not-accessible
			STATUS current
			DESCRIPTION
				"Description."
			INDEX { asMaxSSCmTestIndex }
			::= { asMaxSSCmTestTable 1 }

		
		AsMaxSSCmTestEntry ::=
			SEQUENCE { 
				asMaxSSCmTestIndex
					Integer32,
				asMaxSSCmTestDescription
					DisplayString,
				asMaxSSCmTestStatus
					INTEGER
			 }

		-- 1.3.6.1.4.1.989.1.16.3.1.3.1.1.1
		asMaxSSCmTestIndex OBJECT-TYPE
			SYNTAX Integer32 (1..2147483647)
			MAX-ACCESS read-only
			STATUS current
			DESCRIPTION
				"Description."
			::= { asMaxSSCmTestEntry 1 }

		
		-- 1.3.6.1.4.1.989.1.16.3.1.3.1.1.2
		asMaxSSCmTestDescription OBJECT-TYPE
			SYNTAX DisplayString
			MAX-ACCESS read-only
			STATUS current
			DESCRIPTION
				"Description."
			::= { asMaxSSCmTestEntry 2 }

		
		-- 1.3.6.1.4.1.989.1.16.3.1.3.1.1.3
		asMaxSSCmTestStatus OBJECT-TYPE
			SYNTAX INTEGER
				{
				start(1),
				proceeding(2),
				finished(3),
				stop(4),
				error(5)
				}
			MAX-ACCESS read-write
			STATUS current
			DESCRIPTION
				"Description."
			::= { asMaxSSCmTestEntry 3 }

		
		-- 1.3.6.1.4.1.989.1.16.3.1.3.2
		asMaxSSCmTestArm0Int OBJECT-TYPE
			SYNTAX Integer32
			MAX-ACCESS read-write
			STATUS current
			DESCRIPTION
				"Description."
			::= { asMaxSSCmTest 2 }

		
		-- 1.3.6.1.4.1.989.1.16.3.1.3.3
		asMaxSSCmTestArm0String OBJECT-TYPE
			SYNTAX DisplayString
			MAX-ACCESS read-write
			STATUS current
			DESCRIPTION
				"Description."
			::= { asMaxSSCmTest 3 }

		
		-- 1.3.6.1.4.1.989.1.16.3.2
		asMaxSSEasyST OBJECT IDENTIFIER ::= { asMaxSS 2 }

		
		-- 1.3.6.1.4.1.989.1.16.3.3
		asMaxSSProST OBJECT IDENTIFIER ::= { asMaxSS 3 }

		
		-- 1.3.6.1.4.1.989.1.16.3.4
		asMaxSSConformance OBJECT IDENTIFIER ::= { asMaxSS 4 }

		
		-- 1.3.6.1.4.1.989.1.16.3.4.1
		asMaxSSCompliances OBJECT IDENTIFIER ::= { asMaxSSConformance 1 }

		
		-- 1.3.6.1.4.1.989.1.16.3.4.2
		asMaxSSGroups OBJECT IDENTIFIER ::= { asMaxSSConformance 2 }

		
		-- 1.3.6.1.4.1.989.1.16.3.4.2.1
		asMaxSSCmMonitorGroup OBJECT-GROUP
			OBJECTS { asMaxSSMonPcToTargetBuff, asMaxSSMonTargetToPcBuff, asMaxSSMonSnmpRelayStatus }
			STATUS current
			DESCRIPTION 
				"Description."
			::= { asMaxSSGroups 1 }

		
		-- 1.3.6.1.4.1.989.1.16.3.4.2.2
		asMaxSSCmCfgGroup OBJECT-GROUP
			OBJECTS { asMaxSSCmUpgrFileToInstall, asMaxSSCmUpgrVersionToActivate, asMaxSSCmUpgrServerType, asMaxSSCmUpgrServerAddrType, asMaxSSCmUpgrServerAddr, 
				asMaxSSCmUpgrServerUser, asMaxSSCmUpgrServerPasswd, asMaxSSCmUpgrAction, asMaxSSCmUpgrProgress, asMaxSSCmUpgrErrorCode, 
				asMaxSSCmUpgrErrorString, asMaxSSCmUpgrTimeStamp, asMaxSSCmUpgrTypeDescription, asMaxSSCmCfgIndex, asMaxSSCmCfgBank0Version, 
				asMaxSSCmCfgBank0Status, asMaxSSCmCfgBank1Version, asMaxSSCmCfgBank1Status, asMaxSSCmCfgSwapBanks, asMaxSSCmCfgDeleteStandbyBank, 
				asMaxSSCmActiveVersion, asMaxSSCmActiveDetails, asMaxSSCmStandbyVersion, asMaxSSCmStandbyDetails, asMaxSSCmRunningVersion, 
				asMaxSSCmRunningDetails, asMaxSSCmCfgEBank0Version, asMaxSSCmCfgEBank0Status, asMaxSSCmCfgEBank1Version, asMaxSSCmCfgEBank1Status
				 }
			STATUS current
			DESCRIPTION 
				"Description."
			::= { asMaxSSGroups 2 }

		
		-- 1.3.6.1.4.1.989.1.16.3.4.2.3
		asMaxSSCmTestGroup OBJECT-GROUP
			OBJECTS { asMaxSSCmTestIndex, asMaxSSCmTestDescription, asMaxSSCmTestStatus, asMaxSSCmTestArm0Int, asMaxSSCmTestArm0String
				 }
			STATUS current
			DESCRIPTION 
				"Description."
			::= { asMaxSSGroups 3 }

		
	
	END

--
-- AIRSPAN-EASYST-MIB.mib
--
