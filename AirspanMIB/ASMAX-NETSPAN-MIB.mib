--
-- ASMAX-NETSPAN-MIB.mib
-- MIB generated by MG-SOFT Visual MIB Builder Version 5.0  Build 250
-- Wednesday, July 16, 2008 at 13:50:22
--

	ASMAX-NETSPAN-MIB DEFINITIONS ::= BEGIN
 
		IMPORTS
			airspanProducts			
				FROM AIRSPAN-MIB			
			asMax, asNet, voiceMax			
				FROM AIRSPAN-PRODUCTS-MIB			
			ItuPerceivedSeverity			
				FROM ITU-ALARM-TC-MIB			
			OBJECT-GROUP, MODULE-COMPLIANCE, NOTIFICATION-GROUP			
				FROM SNMPv2-CONF			
			Integer32, OBJECT-TYPE, MODULE-IDENTITY, NOTIFICATION-TYPE			
				FROM SNMPv2-SMI			
			DateAndTime, TruthValue			
				FROM SNMPv2-TC;
	
	
		-- 1.3.6.1.4.1.989.1.15
		asMaxNetspan MODULE-IDENTITY 
			LAST-UPDATED "200712280941Z"		-- December 28, 2007 at 09:41 GMT
			ORGANIZATION 
				"Airspan"
			CONTACT-INFO 
				"kdudzins@airspan.com"
			DESCRIPTION 
				"MIBs implemented by ASMAX Netspan v.9.00.000 or later.
				Used in Netspan NBIF."
			REVISION "200711231723Z"		-- November 23, 2007 at 17:23 GMT
			DESCRIPTION 
				"Draft 1
				- initial version with starter trap template"
			REVISION "200712100900Z"		-- December 10, 2007 at 09:00 GMT
			DESCRIPTION 
				"Draft 2:
				- Complete Netspan alarm definition"
			REVISION "200712280941Z"		-- December 28, 2007 at 09:41 GMT
			DESCRIPTION 
				"Draft 3:
				--Changed asxNmsInstanceId to a Octet String"
			REVISION "200807161255Z"		-- July 16, 2008 at 12:55 GMT
			DESCRIPTION 
				"Draft 4:
				- Added Critical/Major/Minor/Warning Raise/Clear traps for use with external alarm equipment."
			::= { airspanProducts 15 }

		
	
	
--
-- Node definitions
--
	
		-- 1.3.6.1.4.1.989.1.15.1
		asxNmsConformance OBJECT IDENTIFIER ::= { asMaxNetspan 1 }

		
		-- 1.3.6.1.4.1.989.1.15.1.1
		asxNmsCompliance MODULE-COMPLIANCE
			STATUS current
			DESCRIPTION 
				"Description."
			MODULE -- this module
				MANDATORY-GROUPS { asxNmsNotificationGroup }
			::= { asxNmsConformance 1 }

		
		-- 1.3.6.1.4.1.989.1.15.1.2
		asxNmsNotificationGroup NOTIFICATION-GROUP
			NOTIFICATIONS { asxNmsAlarmTrap, asxNmsCriticalAlarmRaise, asxNmsMajorAlarmRaise, asxNmsMinorlAlarmRaise, asxNmsWarningAlarmRaise, 
				asxNmsCriticalAlarmClear, asxNmsMajorAlarmClear, asxNmsMinorAlarmClear, asxNmsWarningAlarmClear }
			STATUS current
			DESCRIPTION 
				"Description."
			::= { asxNmsConformance 2 }

		
		-- 1.3.6.1.4.1.989.1.15.1.3
		asxNmsObjectGroup OBJECT-GROUP
			OBJECTS { asxNmsAlarmId, asxNmsAlarmType, asxNmsAlarmCategory, asxNmsAlarmSourceId, asxNmsInstanceId, 
				asxNmsSeverity, asxNmsAlarmCount, asxNmsLastReceived, asxNmsAcknowledged, asxNmsLastAcknowledged, 
				asxNmsUserName }
			STATUS current
			DESCRIPTION 
				"Description."
			::= { asxNmsConformance 3 }

		
		-- 1.3.6.1.4.1.989.1.15.2
		asxNmsNotifications OBJECT IDENTIFIER ::= { asMaxNetspan 2 }

		
		-- 1.3.6.1.4.1.989.1.15.2.0
		asxNmsTrapPrefix OBJECT IDENTIFIER ::= { asxNmsNotifications 0 }

		
		-- 1.3.6.1.4.1.989.1.15.2.0.1
		asxNmsAlarmTrap NOTIFICATION-TYPE
			OBJECTS { asxNmsAlarmId, asxNmsAlarmType, asxNmsAlarmCategory, asxNmsAlarmSourceId, asxNmsInstanceId, 
				asxNmsSeverity, asxNmsAlarmCount, asxNmsLastReceived, asxNmsAcknowledged, asxNmsLastAcknowledged, 
				asxNmsUserName }
			STATUS current
			DESCRIPTION 
				"NMS sends the trap to notify the manager about the change in
				an alarm status."
			::= { asxNmsTrapPrefix 1 }

		
		-- 1.3.6.1.4.1.989.1.15.2.0.2
		asxNmsCriticalAlarmRaise NOTIFICATION-TYPE
			OBJECTS { asxNmsAlarmId, asxNmsAlarmType }
			STATUS current
			DESCRIPTION 
				"NMS sends the trap to notify external alarm equipment that a critical alarm has been raised."
			::= { asxNmsTrapPrefix 2 }

		
		-- 1.3.6.1.4.1.989.1.15.2.0.3
		asxNmsMajorAlarmRaise NOTIFICATION-TYPE
			OBJECTS { asxNmsAlarmId, asxNmsAlarmType }
			STATUS current
			DESCRIPTION 
				"NMS sends the trap to notify external alarm equipment that a major alarm has been raised."
			::= { asxNmsTrapPrefix 3 }

		
		-- 1.3.6.1.4.1.989.1.15.2.0.4
		asxNmsMinorlAlarmRaise NOTIFICATION-TYPE
			OBJECTS { asxNmsAlarmId, asxNmsAlarmType }
			STATUS current
			DESCRIPTION 
				"NMS sends the trap to notify external alarm equipment that a minor alarm has been raised."
			::= { asxNmsTrapPrefix 4 }

		
		-- 1.3.6.1.4.1.989.1.15.2.0.5
		asxNmsWarningAlarmRaise NOTIFICATION-TYPE
			OBJECTS { asxNmsAlarmId, asxNmsAlarmType }
			STATUS current
			DESCRIPTION 
				"NMS sends the trap to notify external alarm equipment that a warning alarm has been raised."
			::= { asxNmsTrapPrefix 5 }

		
		-- 1.3.6.1.4.1.989.1.15.2.0.6
		asxNmsCriticalAlarmClear NOTIFICATION-TYPE
			OBJECTS { asxNmsAlarmId, asxNmsAlarmType }
			STATUS current
			DESCRIPTION 
				"NMS sends the trap to notify external alarm equipment that the last remaining critical alarm has cleared."
			::= { asxNmsTrapPrefix 6 }

		
		-- 1.3.6.1.4.1.989.1.15.2.0.7
		asxNmsMajorAlarmClear NOTIFICATION-TYPE
			OBJECTS { asxNmsAlarmId, asxNmsAlarmType }
			STATUS current
			DESCRIPTION 
				"NMS sends the trap to notify external alarm equipment that the last remaining major alarm has cleared."
			::= { asxNmsTrapPrefix 7 }

		
		-- 1.3.6.1.4.1.989.1.15.2.0.8
		asxNmsMinorAlarmClear NOTIFICATION-TYPE
			OBJECTS { asxNmsAlarmId, asxNmsAlarmType }
			STATUS current
			DESCRIPTION 
				"NMS sends the trap to notify external alarm equipment that the last remaining minor alarm has cleared."
			::= { asxNmsTrapPrefix 8 }

		
		-- 1.3.6.1.4.1.989.1.15.2.0.9
		asxNmsWarningAlarmClear NOTIFICATION-TYPE
			OBJECTS { asxNmsAlarmId, asxNmsAlarmType }
			STATUS current
			DESCRIPTION 
				"NMS sends the trap to notify external alarm equipment that the last remaining warning alarm has cleared."
			::= { asxNmsTrapPrefix 9 }

		
		-- 1.3.6.1.4.1.989.1.15.2.1
		asxNmsActiveAlarmTable OBJECT-TYPE
			SYNTAX SEQUENCE OF AsxNmsActiveAlarmEntry
			MAX-ACCESS not-accessible
			STATUS current
			DESCRIPTION
				"Contains status of objects assotiated with NMS alarm status,
				NMS send trap to notify the manager about the change 
				in an alarm status."
			::= { asxNmsNotifications 1 }

		
		-- 1.3.6.1.4.1.989.1.15.2.1.1
		asxNmsActiveAlarmEntry OBJECT-TYPE
			SYNTAX AsxNmsActiveAlarmEntry
			MAX-ACCESS not-accessible
			STATUS current
			DESCRIPTION
				"Defines objects used in traps - no actual data available."
			INDEX { asxNmsAlarmId }
			::= { asxNmsActiveAlarmTable 1 }

		
		AsxNmsActiveAlarmEntry ::=
			SEQUENCE { 
				asxNmsAlarmId
					Integer32,
				asxNmsAlarmType
					OCTET STRING,
				asxNmsAlarmCategory
					OCTET STRING,
				asxNmsAlarmSourceId
					OCTET STRING,
				asxNmsInstanceId
					OCTET STRING,
				asxNmsSeverity
					ItuPerceivedSeverity,
				asxNmsAlarmCount
					Integer32,
				asxNmsLastReceived
					DateAndTime,
				asxNmsAcknowledged
					TruthValue,
				asxNmsLastAcknowledged
					DateAndTime,
				asxNmsUserName
					OCTET STRING
			 }

		-- 1.3.6.1.4.1.989.1.15.2.1.1.1
		asxNmsAlarmId OBJECT-TYPE
			SYNTAX Integer32 (1..2147483647)
			MAX-ACCESS read-only
			STATUS current
			DESCRIPTION
				"An ID uniquely identifying the alarm on the NMS"
			::= { asxNmsActiveAlarmEntry 1 }

		
		-- 1.3.6.1.4.1.989.1.15.2.1.1.2
		asxNmsAlarmType OBJECT-TYPE
			SYNTAX OCTET STRING
			MAX-ACCESS read-only
			STATUS current
			DESCRIPTION
				"A string describing the type of the alarm"
			::= { asxNmsActiveAlarmEntry 2 }

		
		-- 1.3.6.1.4.1.989.1.15.2.1.1.3
		asxNmsAlarmCategory OBJECT-TYPE
			SYNTAX OCTET STRING
			MAX-ACCESS read-only
			STATUS current
			DESCRIPTION
				"The managed object category of the alarm (e.g. BS/GPS/RF)"
			::= { asxNmsActiveAlarmEntry 3 }

		
		-- 1.3.6.1.4.1.989.1.15.2.1.1.4
		asxNmsAlarmSourceId OBJECT-TYPE
			SYNTAX OCTET STRING
			MAX-ACCESS read-only
			STATUS current
			DESCRIPTION
				"An ID uniquely identifying the alarm source.  For BS managed objects this will be the BS ID."
			::= { asxNmsActiveAlarmEntry 4 }

		
		-- 1.3.6.1.4.1.989.1.15.2.1.1.5
		asxNmsInstanceId OBJECT-TYPE
			SYNTAX OCTET STRING
			MAX-ACCESS read-only
			STATUS current
			DESCRIPTION
				"Identifies the instance of the managed object."
			::= { asxNmsActiveAlarmEntry 5 }

		
		-- 1.3.6.1.4.1.989.1.15.2.1.1.6
		asxNmsSeverity OBJECT-TYPE
			SYNTAX ItuPerceivedSeverity
			MAX-ACCESS read-only
			STATUS current
			DESCRIPTION
				"Identifies the severity of the alarm (e.g. Critical, Major, Normal)"
			::= { asxNmsActiveAlarmEntry 6 }

		
		-- 1.3.6.1.4.1.989.1.15.2.1.1.7
		asxNmsAlarmCount OBJECT-TYPE
			SYNTAX Integer32
			MAX-ACCESS read-only
			STATUS current
			DESCRIPTION
				"Number of time the alarm has been raised having been previously cleared."
			::= { asxNmsActiveAlarmEntry 7 }

		
		-- 1.3.6.1.4.1.989.1.15.2.1.1.8
		asxNmsLastReceived OBJECT-TYPE
			SYNTAX DateAndTime
			MAX-ACCESS read-only
			STATUS current
			DESCRIPTION
				"Date and time the alarm was last received by the EMS."
			::= { asxNmsActiveAlarmEntry 8 }

		
		-- 1.3.6.1.4.1.989.1.15.2.1.1.9
		asxNmsAcknowledged OBJECT-TYPE
			SYNTAX TruthValue
			MAX-ACCESS read-only
			STATUS current
			DESCRIPTION
				"Indicates whether the alarm is currently acknowledged or released"
			::= { asxNmsActiveAlarmEntry 9 }

		
		-- 1.3.6.1.4.1.989.1.15.2.1.1.10
		asxNmsLastAcknowledged OBJECT-TYPE
			SYNTAX DateAndTime
			MAX-ACCESS read-only
			STATUS current
			DESCRIPTION
				"Date and time the alarm was last acknowledged by a user."
			::= { asxNmsActiveAlarmEntry 10 }

		
		-- 1.3.6.1.4.1.989.1.15.2.1.1.11
		asxNmsUserName OBJECT-TYPE
			SYNTAX OCTET STRING
			MAX-ACCESS read-only
			STATUS current
			DESCRIPTION
				"The user who last acknowledged the alarm."
			::= { asxNmsActiveAlarmEntry 11 }

		
	
	END

--
-- ASMAX-NETSPAN-MIB.mib
--
