--
-- AIRSPAN-PRODUCTS-MIB.mib
-- MIB generated by MG-SOFT Visual MIB Builder Version 7.0  Build 230
-- Wednesday, September 24, 2008 at 15:27:30
--

	AIRSPAN-PRODUCTS-MIB DEFINITIONS ::= BEGIN
 
		IMPORTS
			airspan			
				FROM AIRSPAN-MIB			
			MODULE-IDENTITY			
				FROM SNMPv2-SMI;
	
	
		-- 1.3.6.1.4.1.989.1
		airspanProducts MODULE-IDENTITY 
			LAST-UPDATED "201103160941Z"		-- March 16, 2011 at 09:41 GMT
			ORGANIZATION 
				"Airspan"
			CONTACT-INFO 
				"kdudzins@airspan.com"
			DESCRIPTION 
				"airspanProducts is the root from which sysObjectID values are assigned."
			REVISION "200809241518Z"		-- September 24, 2008 at 15:18 GMT
			DESCRIPTION 
				"Draft 2: 17.03.2006
				- first draft with revision history
				- added asMaxSoc OID
				Draft 3: 20.03.2006
				- added asMaxMisc, asMaxBridge
				Draft 4: 18.04.2006
				- added asMaxWiFiAp
				Draft 5: 20.11.2006
				- added asNet
				Draft 6: 29.11.2006
				- added asMaxQBridge
				Draft 7: 30.01.2007
				- added asMaxBsStats
				Draft 8: 14.05.2007
				- added voiceMax
				Draft 9: 18.10.2007
				- added mibs for mobile BS: asMaxEbs and asMaxEsvc
				Draft 10: 14.11.2007
				- added mibs for mobile BS: asMaxAdBridge
				Draft 11: 23.11.2007
				- added mib for Netspan NBIF: asMaxNetspan
				Draft 12: 07.04.2008
				- added mib for NBIF for Unified OMC"
			REVISION "200809241526Z"		-- September 24, 2008 at 15:26 GMT
			DESCRIPTION 
				"Draft 13:
				Made ModuleIdentity to preserve revision history."
			REVISION "201103150941Z"		-- March 15, 2011 at 09:41 GMT
			DESCRIPTION 
				"Draft 14:
				Added asLte, asIb, asSyn, asLteStack, asIbStack, asSynAgent and asSynBrd OIDs"
			REVISION "201103150941Z"		-- March 16, 2011 at 09:41 GMT
			DESCRIPTION 
				"Draft 15:
				Restructured to add asCmn subtree and related sub-MIBs"
			::= { airspan 1 }

		
	
--
-- Node definitions
--
	
		-- 1.3.6.1.4.1.989.1.15
		asMaxNetspan OBJECT IDENTIFIER ::= { airspanProducts 15 }

		
		-- 1.3.6.1.4.1.989.1.16
		asMax OBJECT IDENTIFIER ::= { airspanProducts 16 }

		
		-- 1.3.6.1.4.1.989.1.16.1
		asMaxCommon OBJECT IDENTIFIER ::= { asMax 1 }

		
		-- 1.3.6.1.4.1.989.1.16.2
		asMaxBS OBJECT IDENTIFIER ::= { asMax 2 }

		
		-- 1.3.6.1.4.1.989.1.16.2.1
		asMaxBSCommon OBJECT IDENTIFIER ::= { asMaxBS 1 }

		
		-- 1.3.6.1.4.1.989.1.16.2.2
		asMaxBSHiperMax OBJECT IDENTIFIER ::= { asMaxBS 2 }

		
		-- 1.3.6.1.4.1.989.1.16.2.3
		asMaxBSPicoMax OBJECT IDENTIFIER ::= { asMaxBS 3 }

		
		-- 1.3.6.1.4.1.989.1.16.2.4
		asMaxBSDemoMax OBJECT IDENTIFIER ::= { asMaxBS 4 }

		
		-- 1.3.6.1.4.1.989.1.16.2.5
		asMaxBSSoc OBJECT IDENTIFIER ::= { asMaxBS 5 }

		
		-- 1.3.6.1.4.1.989.1.16.2.6
		asMaxBsStats OBJECT IDENTIFIER ::= { asMaxBS 6 }

		
		-- 1.3.6.1.4.1.989.1.16.2.7
		asMaxEbs OBJECT IDENTIFIER ::= { asMaxBS 7 }

		
		-- 1.3.6.1.4.1.989.1.16.2.8
		asMaxEsvc OBJECT IDENTIFIER ::= { asMaxBS 8 }

		
		-- 1.3.6.1.4.1.989.1.16.2.9
		asMaxEstats OBJECT IDENTIFIER ::= { asMaxBS 9 }

		
		-- 1.3.6.1.4.1.989.1.16.3
		asMaxSS OBJECT IDENTIFIER ::= { asMax 3 }

		
		-- 1.3.6.1.4.1.989.1.16.3.1
		asMaxSSCommon OBJECT IDENTIFIER ::= { asMaxSS 1 }

		
		-- 1.3.6.1.4.1.989.1.16.3.2
		asMaxSSEasyST OBJECT IDENTIFIER ::= { asMaxSS 2 }

		
		-- 1.3.6.1.4.1.989.1.16.3.3
		asMaxSSProST OBJECT IDENTIFIER ::= { asMaxSS 3 }

		
		-- 1.3.6.1.4.1.989.1.16.4
		asMaxBSDU OBJECT IDENTIFIER ::= { asMax 4 }

		
		-- 1.3.6.1.4.1.989.1.16.5
		asMaxMisc OBJECT IDENTIFIER ::= { asMax 5 }

		
		-- 1.3.6.1.4.1.989.1.16.5.1
		asMaxBridge OBJECT IDENTIFIER ::= { asMaxMisc 1 }

		
		-- 1.3.6.1.4.1.989.1.16.5.2
		asMaxWiFiAp OBJECT IDENTIFIER ::= { asMaxMisc 2 }

		
		-- 1.3.6.1.4.1.989.1.16.5.3
		asMaxQBridge OBJECT IDENTIFIER ::= { asMaxMisc 3 }

		
		-- 1.3.6.1.4.1.989.1.16.5.4
		asMaxAdBridge OBJECT IDENTIFIER ::= { asMaxMisc 4 }

		
		-- 1.3.6.1.4.1.989.1.17
		asNet OBJECT IDENTIFIER ::= { airspanProducts 17 }

		
		-- 1.3.6.1.4.1.989.1.18
		voiceMax OBJECT IDENTIFIER ::= { airspanProducts 18 }

		
		-- 1.3.6.1.4.1.989.1.19
		asMaxUomc OBJECT IDENTIFIER ::= { airspanProducts 19 }


		-- Branch to include LTE related MIBs
        -- 1.3.6.1.4.1.989.1.20
		asLte OBJECT IDENTIFIER ::= { airspanProducts 20 }


   		-- MIB for general CCPU stack configuration and management
    	-- 1.3.6.1.4.1.989.1.20.1
		asLteStk OBJECT IDENTIFIER ::= { asLte 1 }
        

		-- Branch to include iBridge related MIBs
		-- 1.3.6.1.4.1.989.1.21
		asIb OBJECT IDENTIFIER ::= { airspanProducts 21 }


        -- MIB for Feeder Terminal variant of iBridge
   		-- 1.3.6.1.4.1.989.1.21.1
		asIbFt OBJECT IDENTIFIER ::= { asIb 1 }


        -- Branch to include generally reusable MIBs to cover specific functional areas.
		-- 1.3.6.1.4.1.989.1.22
		asCmn OBJECT IDENTIFIER ::= { airspanProducts 22 }


        -- MIB supported by every SNMP agent in multi-stack architecture.
   		-- 1.3.6.1.4.1.989.1.22.1
		asCmnAgent OBJECT IDENTIFIER ::= { asCmn 1 }


   		-- MIB for software download
        -- 1.3.6.1.4.1.989.1.22.2
		asCmnSw OBJECT IDENTIFIER ::= { asCmn 2 }


   		-- MIB for sensors
        -- 1.3.6.1.4.1.989.1.22.3
		asCmnSensor OBJECT IDENTIFIER ::= { asCmn 3 }


  		-- MIB for feature licensing
        -- 1.3.6.1.4.1.989.1.22.4
		asCmnLic OBJECT IDENTIFIER ::= { asCmn 4 }


  		-- MIB for Airspan Textual Conventions
        -- 1.3.6.1.4.1.989.1.22.4
		asCmnTc OBJECT IDENTIFIER ::= { asCmn 5 }

        

		-- Branch for MIBs specific to the AirSynergy platform
        -- 1.3.6.1.4.1.989.1.23
		asSyn OBJECT IDENTIFIER ::= { airspanProducts 23 }


   		-- AirSynergy hardware-related functionality
        -- 1.3.6.1.4.1.989.1.23.1
		asSynBd OBJECT IDENTIFIER ::= { asSyn 1 }

      		
	
	END

--
-- AIRSPAN-PRODUCTS-MIB.mib
--
