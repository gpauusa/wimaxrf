--
-- AIRSPAN-Q-BRIDGE-MIB.mib
-- MIB generated by MG-SOFT Visual MIB Builder Version 5.0  Build 250
-- Thursday, April 17, 2008 at 10:21:24
--

	AIRSPAN-Q-BRIDGE-MIB DEFINITIONS ::= BEGIN
 
		IMPORTS
			AsmaxBooleanSwitch			
				FROM AIRSPAN-ASMAX-COMMON-MIB			
			asMaxMisc			
				FROM AIRSPAN-PRODUCTS-MIB			
			InterfaceIndex			
				FROM IF-MIB			
			OBJECT-GROUP, MODULE-COMPLIANCE			
				FROM SNMPv2-CONF			
			Integer32, OBJECT-TYPE, MODULE-IDENTITY			
				FROM SNMPv2-SMI			
			MacAddress, RowStatus, TEXTUAL-CONVENTION			
				FROM SNMPv2-TC;
	
	
		-- 1.3.6.1.4.1.989.1.16.5.3
		asMaxQBridge MODULE-IDENTITY 
			LAST-UPDATED "200804171020Z"		-- April 17, 2008 at 10:20 GMT
			ORGANIZATION 
				"Airspan Communications Lt."
			CONTACT-INFO 
				"Krzysztof Dudzinski
				Airspan Communications Ltd.
				email: kdudzins@airspan.com
				http://www.airspan.com"
			DESCRIPTION 
				"The VLAN Bridge MIB module for managing Virtual Bridged
				Local Area Networks, defined based on standard Q-BRIDGE-MIB
				and IEEE 802.1Q-2003 standard, implemented as VLAN bridge over 802.16."
			REVISION "200612111021Z"		-- December 11, 2006 at 10:21 GMT
			DESCRIPTION 
				"Predraft version - everything subject to change.
				29/11 - all OIDs changed
				30/11 - plenty of changes converging towards the first draft:
				  - mgmt vlan allows to configure untagged
				  - split port table into BS port table and SS port table
				  - chorten VLAN name to 8 chars
				  - fixed indexes for port vlan list table
				  - added port mode to port tables
				  - reserved VLAN 1 doesn't allow (0)
				  - bridge mode default changed to transparent
				  - removed bridge status table (BS port table will give BS port Mac Address)
				  - remove filtering database ID
				  - fixed various types and descriptions
				5/12
				  - removed asDot1qVlanProvShortName
				  - defined defaults for columns in asDot1qBridgeTable
				11/12
				  - fixed default value for asDot1qPortVlanListTagging (tagged)
				  - changed AlanId textual convetion names to avoid clash with AIRSPAN-BS-COMMON-MIB"
			REVISION "200701111838Z"		-- January 11, 2007 at 18:38 GMT
			DESCRIPTION 
				"Draft 1
				 - first draft validated by initial integration tests
				 - restricted reserved VLANs to valid IDs only"
			REVISION "200701301122Z"		-- January 30, 2007 at 11:22 GMT
			DESCRIPTION 
				"Draft 2
				 - added admitOnlyUntagged value to asDot1qSsPortProvAllowedFrameTypes and asDot1qBsPortProvAllowedFrameTypes"
			REVISION "200704131100Z"		-- April 13, 2007 at 11:00 GMT
			DESCRIPTION 
				"Draft 3
				- Replaced direct type encoding with usage of textual convention for 
				  port mode and allowed frame types objects (AsDot1qPortMode, AsDot1qAllowedFrameTypes)."
			REVISION "200704171800Z"		-- April 17, 2007 at 18:00 GMT
			DESCRIPTION 
				"Draft 4
				- Added asDot1qBridgeAgeingTime"
			REVISION "200705171800Z"		-- May 17, 2007 at 18:00 GMT
			DESCRIPTION 
				"Draft 5
				- Added asDot1qBsDefaultPriority, asDot1qSsDefaultPriority"
			REVISION "200709051750Z"		-- September 05, 2007 at 17:50 GMT
			DESCRIPTION 
				"Draft 6
				Added objects:
				- Bridge mode bridgeModeProviders
				- asDot1qBridgeSTagEthertype
				- asDot1qSsSTagPvid
				- asDot1qSsSTagPriority"
			REVISION "200709071630Z"		-- September 07, 2007 at 16:30 GMT
			DESCRIPTION 
				"Draft 7:
				- Added more bridge objects for Q-in-Q:
				  asDot1qBridgeSTagConfigMode,
				  asDot1qBridgeSTagPvid,
				  asDot1qBridgeSTagUseSTagPriority,
				  asDot1qBridgeSTagPriority
				- Added and changed SS port objects for Q-in-Q:
				  asDot1qSsSTagPvid,
				  asDot1qSsSTagUseSTagPriority,
				  asDot1qSsSTagPriority"
			REVISION "200709131140Z"		-- September 13, 2007 at 11:40 GMT
			DESCRIPTION 
				"Draft 8:
				- changed asDot1qBridgeSTagPvid to AsDot1qVlanIdOrNone
				- changed asDot1qSsTagPvid to AsDot1qVlanIdOrNone
				- range 0..7, default 0 defined for asDot1qSsSTagPriority"
			REVISION "200710240955Z"		-- October 24, 2007 at 09:55 GMT
			DESCRIPTION 
				"Draft 9:
				- added asDot1qBridgeFloodingEnabled"
			REVISION "200801021127Z"		-- January 02, 2008 at 11:27 GMT
			DESCRIPTION 
				"Draft 10:
				- added description for asDot1qBridgeFloodingEnabled and corrected previous duplicated draft number"
			REVISION "200804171018Z"		-- April 17, 2008 at 10:18 GMT
			DESCRIPTION 
				"Draft 11:
				- added asDot1qBasePortTable"
			::= { asMaxMisc 3 }

		
	
--
-- Textual conventions
--
	
		AsDot1qVlanId ::= TEXTUAL-CONVENTION
			DISPLAY-HINT 
				"d"
			STATUS current
			DESCRIPTION 
				"The VLAN-ID that uniquely identifies a VLAN.  This
				is the 12-bit VLAN-ID used in the VLAN Tag header.
				The range is defined by the REFERENCEd specification."
			REFERENCE 
				"IEEE Std 802.1Q 2003 Edition, Virtual Bridged
				Local Area Networks."
			SYNTAX Integer32 (1..4094)

		AsDot1qVlanIdOrAny ::= TEXTUAL-CONVENTION
			DISPLAY-HINT 
				"d"
			STATUS current
			DESCRIPTION 
				"The VLAN-ID that uniquely identifies a specific VLAN,
				or any VLAN.  The special value of 4095 is used to
				indicate a wildcard, i.e., any VLAN.  This can be used
				in any situation where an object or table entry must
				refer either to a specific VLAN or to any VLAN.
				
				Note that a MIB object that is defined using this
				TEXTUAL-CONVENTION should clarify the meaning of
				'any VLAN' (i.e., the special value 4095)."
			SYNTAX Integer32 (1..4094 | 4095)

		AsDot1qVlanIdOrNone ::= TEXTUAL-CONVENTION
			DISPLAY-HINT 
				"d"
			STATUS current
			DESCRIPTION 
				"The VLAN-ID that uniquely identifies a specific VLAN,
				or no VLAN.  The special value of zero is used to
				indicate that no VLAN-ID is present or used.  This can
				be used in any situation where an object or a table entry
				must refer either to a specific VLAN, or to no VLAN.
				
				Note that a MIB object that is defined using this
				TEXTUAL-CONVENTION should clarify the meaning of
				'no VLAN' (i.e., the special value 0)."
			SYNTAX Integer32 (0 | 1..4094)

		AsDot1qVlanIdOrAnyOrNone ::= TEXTUAL-CONVENTION
			DISPLAY-HINT 
				"d"
			STATUS current
			DESCRIPTION 
				"The VLAN-ID that uniquely identifies a specific VLAN,
				any VLAN, or no VLAN.  The special values 0 and 4095
				have the same meaning as described in the VlanIdOrAny
				and VlanIdOrNone TEXTUAL-CONVENTIONs.
				
				Note that a MIB object that is defined using this
				TEXTUAL-CONVENTION should clarify the meaning of
				'any VLAN' and 'no VLAN' (i.e., the special values
				0 and 4095)."
			SYNTAX Integer32 (0 | 1..4094 | 4095)

		AsDot1qPortMode ::= TEXTUAL-CONVENTION
			STATUS current
			DESCRIPTION 
				"Configures standard (portModeVlan) behaviour or non standard 
				behaviour of the port (portModeRaw).
				In mode portModeRaw all port configuration and port Vlan list 
				are ignored. The traffic is allow to flow in and out unfiltered 
				and without changes to tagging."
			SYNTAX INTEGER
				{
				portModeRaw(1),
				portModeVlan(2)
				}

		AsDot1qAllowedFrameTypes ::= TEXTUAL-CONVENTION
			STATUS current
			DESCRIPTION 
				"When this is admitOnlyVlanTagged, the device will discard 
				untagged frames or Priority-Tagged frames received on this port.
				When admitAll(1), untagged frames or Priority-Tagged frames 
				received on the port will be accepted and assigned to 
				a VID based on the PVID of for this port.
				When admitOnlyUntagged(3), is set the device will discard 
				all VLAN tagged frames."
			SYNTAX INTEGER
				{
				admitAll(1),
				admitOnlyVlanTagged(2),
				admitOnlyUntagged(3)
				}

	
--
-- Node definitions
--
	
		-- 1.3.6.1.4.1.989.1.16.5.3.1
		asqBridgeObjects OBJECT IDENTIFIER ::= { asMaxQBridge 1 }

		
		-- 1.3.6.1.4.1.989.1.16.5.3.1.1
		asDot1qBase OBJECT IDENTIFIER ::= { asqBridgeObjects 1 }

		
		-- 1.3.6.1.4.1.989.1.16.5.3.1.1.1
		asDot1qBridgeTable OBJECT-TYPE
			SYNTAX SEQUENCE OF AsDot1qBridgeEntry
			MAX-ACCESS not-accessible
			STATUS current
			DESCRIPTION
				"A table containing configuration and status information global 
				for the entire bridge implemented on 802.16 BS.
				A row in this table should be created by BS with the default values."
			::= { asDot1qBase 1 }

		
		-- 1.3.6.1.4.1.989.1.16.5.3.1.1.1.1
		asDot1qBridgeEntry OBJECT-TYPE
			SYNTAX AsDot1qBridgeEntry
			MAX-ACCESS not-accessible
			STATUS current
			DESCRIPTION
				"Description."
			INDEX { asDot1qBridgeIndex }
			::= { asDot1qBridgeTable 1 }

		
		AsDot1qBridgeEntry ::=
			SEQUENCE { 
				asDot1qBridgeIndex
					Integer32,
				asDot1qBridgeMode
					INTEGER,
				asDot1qBridgeMgmtVlanId
					AsDot1qVlanIdOrNone,
				asDot1qBridgeReservedVlan1
					AsDot1qVlanId,
				asDot1qBridgeReservedVlan2
					AsDot1qVlanId,
				asDot1qBridgeReservedVlan3
					AsDot1qVlanId,
				asDot1qBridgeAgeingTime
					INTEGER,
				asDot1qBridgeSTagEthertype
					Integer32,
				asDot1qBridgeSTagConfigMode
					INTEGER,
				asDot1qBridgeSTagPvid
					AsDot1qVlanIdOrNone,
				asDot1qBridgeSTagUseSTagPriority
					AsmaxBooleanSwitch,
				asDot1qBridgeSTagPriority
					Integer32,
				asDot1qBridgeFloodingEnabled
					AsmaxBooleanSwitch
			 }

		-- 1.3.6.1.4.1.989.1.16.5.3.1.1.1.1.1
		asDot1qBridgeIndex OBJECT-TYPE
			SYNTAX Integer32 (1)
			MAX-ACCESS not-accessible
			STATUS current
			DESCRIPTION
				"Arbitrary index for single row table - must always be set to 1."
			::= { asDot1qBridgeEntry 1 }

		
		-- 1.3.6.1.4.1.989.1.16.5.3.1.1.1.1.2
		asDot1qBridgeMode OBJECT-TYPE
			SYNTAX INTEGER
				{
				bridgeModeVlan(1),
				bridgeModeTransparent(2),
				bridgeModeProvidersVlan(3)
				}
			MAX-ACCESS read-write
			STATUS current
			DESCRIPTION
				"Defines the general mode of BS bridge.
				In Transparent mode bridge ignores tagging and behaves like a simple L2 bridge.
				In VLAN mode bridge implements 802.1q standard.
				In Providers mode bridge extends 802.1q with the S-TAGging based on 802.1ad standard 
				but is limited to single S-TAG VID per port.
				"
			DEFVAL { bridgeModeTransparent }
			::= { asDot1qBridgeEntry 2 }

		
		-- 1.3.6.1.4.1.989.1.16.5.3.1.1.1.1.3
		asDot1qBridgeMgmtVlanId OBJECT-TYPE
			SYNTAX AsDot1qVlanIdOrNone
			MAX-ACCESS read-write
			STATUS current
			DESCRIPTION
				"Defines VlanId used to tag the management traffic for the bridge 
				hosting 802.16 BS and management trafic routed to all managed SSs 
				using SMC connection. This VLAN must be diffent than all SSs ports'
				PVIDs to avoid management by untagged traffic coming from SSs end user.
				This VLAN should be added explicitely to BS port vlan list if it is different 
				than the PVID of BS port.
				When this VLAN ID is the same as PVID of BS port the management happens 
				via untagged traffic and the VLAN should not be added to BS port VLAN list.
				When this VLAN ID is set to (0) the management traffic is untagged."
			DEFVAL { 4094 }
			::= { asDot1qBridgeEntry 3 }

		
		-- 1.3.6.1.4.1.989.1.16.5.3.1.1.1.1.4
		asDot1qBridgeReservedVlan1 OBJECT-TYPE
			SYNTAX AsDot1qVlanId
			MAX-ACCESS read-write
			STATUS current
			DESCRIPTION
				"Vlan reserved for implementation specific internal purposes.
				The value of this VLAN ID must be always valid 1..4094.
				This VLAN cannot be used for any other configuration defined 
				in this MIB (PVIDs of all ports, management VLAN).
				This VLAN is not defined in asDot1qVlanProvTable."
			DEFVAL { 4093 }
			::= { asDot1qBridgeEntry 4 }

		
		-- 1.3.6.1.4.1.989.1.16.5.3.1.1.1.1.5
		asDot1qBridgeReservedVlan2 OBJECT-TYPE
			SYNTAX AsDot1qVlanId
			MAX-ACCESS read-write
			STATUS current
			DESCRIPTION
				"Vlan reserved for implementation specific internal purposes.
				The value of this VLAN ID can be either valid 1..4094 or (0).
				When it is set to (0) the reserved VLAN 2 is not configured.
				This VLAN cannot be used for any other configuration defined 
				in this MIB (PVIDs of all ports, management VLAN).
				This VLAN is not defined in asDot1qVlanProvTable."
			::= { asDot1qBridgeEntry 5 }

		
		-- 1.3.6.1.4.1.989.1.16.5.3.1.1.1.1.6
		asDot1qBridgeReservedVlan3 OBJECT-TYPE
			SYNTAX AsDot1qVlanId
			MAX-ACCESS read-write
			STATUS current
			DESCRIPTION
				"Vlan reserved for implementation specific internal purposes.
				The value of this VLAN ID can be either valid 1..4094 or (0).
				When it is set to (0) the reserved VLAN 2 is not configured.
				This VLAN cannot be used for any other configuration defined 
				in this MIB (PVIDs of all ports, management VLAN).
				This VLAN is not defined in asDot1qVlanProvTable."
			::= { asDot1qBridgeEntry 6 }

		
		-- 1.3.6.1.4.1.989.1.16.5.3.1.1.1.1.7
		asDot1qBridgeAgeingTime OBJECT-TYPE
			SYNTAX INTEGER (10..1000000)
			UNITS "s"
			MAX-ACCESS read-write
			STATUS current
			DESCRIPTION
				"When the time since the entry in the filtering database 
				(learned source address) was created or last updated, is greater than 
				this ageing time the entry should be automatically removed."
			DEFVAL { 300 }
			::= { asDot1qBridgeEntry 7 }

		
		-- 1.3.6.1.4.1.989.1.16.5.3.1.1.1.1.8
		asDot1qBridgeSTagEthertype OBJECT-TYPE
			SYNTAX Integer32 (0..65535)
			MAX-ACCESS read-write
			STATUS current
			DESCRIPTION
				"The Ethertype of the frame with outer S-TAG for providers VLAN bridge mode.
				The typical values used are:
				0x88A8 (34984),
				0x9100 (37120),
				0x9200 (37376),
				0x9300 (37632)
				The default value is 0x9100 (37120).
				The object is not defined as an enumeration to allow future extensions.
				NMS should show it as an enumeration on GUI."
			DEFVAL { 37120 }
			::= { asDot1qBridgeEntry 8 }

		
		-- 1.3.6.1.4.1.989.1.16.5.3.1.1.1.1.9
		asDot1qBridgeSTagConfigMode OBJECT-TYPE
			SYNTAX INTEGER
				{
				sTagUseSsConfig(1),
				sTagUseBsConfigForAllSsPorts(2)
				}
			MAX-ACCESS read-write
			STATUS current
			DESCRIPTION
				"Instructs to either use SS config (default) for each SS port STagging
				or to use BS config for each SS Port on this BS bridge."
			DEFVAL { sTagUseSsConfig }
			::= { asDot1qBridgeEntry 9 }

		
		-- 1.3.6.1.4.1.989.1.16.5.3.1.1.1.1.10
		asDot1qBridgeSTagPvid OBJECT-TYPE
			SYNTAX AsDot1qVlanIdOrNone
			MAX-ACCESS read-write
			STATUS current
			DESCRIPTION
				"This object is defined using 802.1q and 802.ad terminology.
				The object overwrites the config for all SS ports on this bridge
				and is used when asDot1qBridgeSTagConfigMode is set to sTagUseBsConfigForAllSsPorts.
				Object defines VLAN ID applied to outer tag (S-TAG) of the frame when 
				the bridge works in Providers VLAN mode (as defined by asDot1qBridgeMode). 
				All the packets received from the C-Bridge of this port
				(tagged or untagged with C-TAG i.e. Q-tag) are tagged with this VID."
			DEFVAL { 1 }
			::= { asDot1qBridgeEntry 10 }

		
		-- 1.3.6.1.4.1.989.1.16.5.3.1.1.1.1.11
		asDot1qBridgeSTagUseSTagPriority OBJECT-TYPE
			SYNTAX AsmaxBooleanSwitch
			MAX-ACCESS read-write
			STATUS current
			DESCRIPTION
				"The object overwrite the config for all SS ports on this BS bridge.
				When false (default) the user priority for STag is copied from 
				the inner tag (CTag).
				When true the user priority for STag is taken from 
				the object asDot1qBridgeSTagPriority."
			DEFVAL { booleanFalse }
			::= { asDot1qBridgeEntry 11 }

		
		-- 1.3.6.1.4.1.989.1.16.5.3.1.1.1.1.12
		asDot1qBridgeSTagPriority OBJECT-TYPE
			SYNTAX Integer32 (0..7)
			MAX-ACCESS read-write
			STATUS current
			DESCRIPTION
				"This object is defined using 802.1q and 802.ad terminology.
				The object overwrites the config for all SS ports on this bridge
				when STagConfigMode selects value sTagConfigModeUseBsConfigForAllSsPorts.
				It is only used when instructed by asDot1qBridgeSTagUseSTagPriority.
				Object defines VLAN user priority applied to outer tag (S-TAG) of the frame 
				when the bridge works in Providers mode (as defined in asDot1qBridgeMode). 
				All the packets received from the C-Bridge of this port
				(tagged or untagged with C-TAG i.e Q-tag) are tagged with this VLAN user priority."
			DEFVAL { 0 }
			::= { asDot1qBridgeEntry 12 }

		
		-- 1.3.6.1.4.1.989.1.16.5.3.1.1.1.1.13
		asDot1qBridgeFloodingEnabled OBJECT-TYPE
			SYNTAX AsmaxBooleanSwitch
			MAX-ACCESS read-write
			STATUS current
			DESCRIPTION
				"Flag indicating whether flooding is enabled. Enabled if set to true"
			DEFVAL { booleanFalse }
			::= { asDot1qBridgeEntry 13 }

		
		-- 1.3.6.1.4.1.989.1.16.5.3.1.1.2
		asDot1qBasePortTable OBJECT-TYPE
			SYNTAX SEQUENCE OF AsDot1qBasePortEntry
			MAX-ACCESS not-accessible
			STATUS current
			DESCRIPTION
				"A table that contains generic information about
				every port that is associated with this bridge.
				Transparent, source-route, and srt ports are
				included."
			::= { asDot1qBase 2 }

		
		-- 1.3.6.1.4.1.989.1.16.5.3.1.1.2.1
		asDot1qBasePortEntry OBJECT-TYPE
			SYNTAX AsDot1qBasePortEntry
			MAX-ACCESS not-accessible
			STATUS current
			DESCRIPTION
				"A list of information for each port of the
				bridge."
			REFERENCE
				"IEEE 802.1D-1998"
			INDEX { asDot1qBasePort }
			::= { asDot1qBasePortTable 1 }

		
		AsDot1qBasePortEntry ::=
			SEQUENCE { 
				asDot1qBasePort
					Integer32,
				asDot1qBasePortIfIndex
					InterfaceIndex,
				asDot1qBasePortCircuit
					MacAddress
			 }

		-- 1.3.6.1.4.1.989.1.16.5.3.1.1.2.1.1
		asDot1qBasePort OBJECT-TYPE
			SYNTAX Integer32 (1..65535)
			MAX-ACCESS read-only
			STATUS current
			DESCRIPTION
				"The port number of the port for which this entry
				contains bridge management information."
			::= { asDot1qBasePortEntry 1 }

		
		-- 1.3.6.1.4.1.989.1.16.5.3.1.1.2.1.2
		asDot1qBasePortIfIndex OBJECT-TYPE
			SYNTAX InterfaceIndex
			MAX-ACCESS read-only
			STATUS current
			DESCRIPTION
				"The value of the instance of the ifIndex object,
				defined in MIB-II, for the interface corresponding
				to this port."
			::= { asDot1qBasePortEntry 2 }

		
		-- 1.3.6.1.4.1.989.1.16.5.3.1.1.2.1.3
		asDot1qBasePortCircuit OBJECT-TYPE
			SYNTAX MacAddress
			MAX-ACCESS read-only
			STATUS current
			DESCRIPTION
				"For a port which (potentially) has the same value
				of asDot1qBasePortIfIndex as another port on the
				same bridge, this object contains the name of an
				object instance unique to this port.  For example,
				in the case where multiple ports correspond one-
				to-one with multiple X.25 virtual circuits, this
				value might identify an (e.g., the first) object
				instance associated with the X.25 virtual circuit
				corresponding to this port.
				
				For a port which has a unique value of
				asDot1qBasePortIfIndex, this object can have the
				value { 0 0 }."
			::= { asDot1qBasePortEntry 3 }

		
		-- 1.3.6.1.4.1.989.1.16.5.3.1.2
		asDot1qTp OBJECT IDENTIFIER ::= { asqBridgeObjects 2 }

		
		-- 1.3.6.1.4.1.989.1.16.5.3.1.2.1
		asDot1qTpFdbTable OBJECT-TYPE
			SYNTAX SEQUENCE OF AsDot1qTpFdbEntry
			MAX-ACCESS not-accessible
			STATUS current
			DESCRIPTION
				"A table that contains information about unicast entries
				for which the device has forwarding and/or filtering
				information.  This information is used by the
				transparent bridging function in determining how to
				propagate a received frame."
			REFERENCE
				"IEEE 802.1Q/D11 Section 12.7.7"
			::= { asDot1qTp 1 }

		
		-- 1.3.6.1.4.1.989.1.16.5.3.1.2.1.1
		asDot1qTpFdbEntry OBJECT-TYPE
			SYNTAX AsDot1qTpFdbEntry
			MAX-ACCESS not-accessible
			STATUS current
			DESCRIPTION
				"Information about a specific unicast MAC address for
				which the device has some forwarding and/or filtering
				information."
			INDEX { asDot1qTpFdbAddress }
			::= { asDot1qTpFdbTable 1 }

		
		AsDot1qTpFdbEntry ::=
			SEQUENCE { 
				asDot1qTpFdbAddress
					MacAddress,
				asDot1qTpFdbPortAddress
					MacAddress,
				asDot1qTpFdbStatus
					INTEGER
			 }

		-- 1.3.6.1.4.1.989.1.16.5.3.1.2.1.1.1
		asDot1qTpFdbAddress OBJECT-TYPE
			SYNTAX MacAddress
			MAX-ACCESS not-accessible
			STATUS current
			DESCRIPTION
				"A unicast MAC address for which the device has
				forwarding and/or filtering information."
			::= { asDot1qTpFdbEntry 1 }

		
		-- 1.3.6.1.4.1.989.1.16.5.3.1.2.1.1.2
		asDot1qTpFdbPortAddress OBJECT-TYPE
			SYNTAX MacAddress
			MAX-ACCESS read-only
			STATUS current
			DESCRIPTION
				"Either the value '00:00:00:00:00:00', or the port address
				of the port on which a frame having a source address equal 
				to the value of the corresponding instance of asDot1qTpFdbAddress 
				has been seen.  A value of '00:00:00:00:00:00' indicates 
				that the port address has not been learned but that the device 
				does have some forwarding/filtering information about this
				source address.
				Implementors are encouraged to assign the port value to
				this object whenever it is learned, even for addresses
				for which the corresponding value of asDot1qTpFdbStatus is
				not learned(3)."
			::= { asDot1qTpFdbEntry 2 }

		
		-- 1.3.6.1.4.1.989.1.16.5.3.1.2.1.1.3
		asDot1qTpFdbStatus OBJECT-TYPE
			SYNTAX INTEGER
				{
				other(1),
				invalid(2),
				learned(3),
				self(4),
				mgmt(5)
				}
			MAX-ACCESS read-only
			STATUS current
			DESCRIPTION
				"The status of this entry.  The meanings of the values
				are:
				    other(1) - none of the following.  This may include
				        the case where some other MIB object (not the
				        corresponding instance of asDot1qTpFdbPort, nor an
				        entry in the asDot1qStaticUnicastTable) is being
				        used to determine if and how frames addressed to
				        the value of the corresponding instance of
				        asDot1qTpFdbAddress are being forwarded.
				    invalid(2) - this entry is no longer valid (e.g., it
				        was learned but has since aged out), but has not
				        yet been flushed from the table.
				    learned(3) - the value of the corresponding instance
				        of asDot1qTpFdbPort was learned and is being used.
				    self(4) - the value of the corresponding instance of
				        asDot1qTpFdbAddress represents one of the device's
				        addresses.  The corresponding instance of
				        asDot1qTpFdbPortAddress indicates which of the device's
				        ports has this address.
				    mgmt(5) - the value of the corresponding instance of
				        asDot1qTpFdbAddress is also the value of an
				        existing instance of asDot1qStaticAddress."
			::= { asDot1qTpFdbEntry 3 }

		
		-- 1.3.6.1.4.1.989.1.16.5.3.1.3
		asDot1qVlan OBJECT IDENTIFIER ::= { asqBridgeObjects 3 }

		
		-- 1.3.6.1.4.1.989.1.16.5.3.1.3.1
		asDot1qVlanProvTable OBJECT-TYPE
			SYNTAX SEQUENCE OF AsDot1qVlanProvEntry
			MAX-ACCESS not-accessible
			STATUS current
			DESCRIPTION
				"A table containing static provisioning information for
				each VLAN configured into the device by (local or
				network) management.  All entries are permanent and will
				be restored after the device is reset.
				
				Differs from standard Q-BRIDGE-MIB in that the tagging behaviour is defined
				via mapping table asDot1PortVlanListTable rather than via PortList 
				columns in this table.
				"
			::= { asDot1qVlan 1 }

		
		-- 1.3.6.1.4.1.989.1.16.5.3.1.3.1.1
		asDot1qVlanProvEntry OBJECT-TYPE
			SYNTAX AsDot1qVlanProvEntry
			MAX-ACCESS not-accessible
			STATUS current
			DESCRIPTION
				"One row per VLAN ID."
			INDEX { asDot1qVlanProvId }
			::= { asDot1qVlanProvTable 1 }

		
		AsDot1qVlanProvEntry ::=
			SEQUENCE { 
				asDot1qVlanProvId
					AsDot1qVlanId,
				asDot1qVlanProvRowStatus
					RowStatus
			 }

		-- 1.3.6.1.4.1.989.1.16.5.3.1.3.1.1.1
		asDot1qVlanProvId OBJECT-TYPE
			SYNTAX AsDot1qVlanId
			MAX-ACCESS not-accessible
			STATUS current
			DESCRIPTION
				"VLAN identifier. Only valid VLAN ID can be used i.e. 1 to 4094."
			::= { asDot1qVlanProvEntry 1 }

		
		-- 1.3.6.1.4.1.989.1.16.5.3.1.3.1.1.2
		asDot1qVlanProvRowStatus OBJECT-TYPE
			SYNTAX RowStatus
			MAX-ACCESS read-create
			STATUS current
			DESCRIPTION
				"This object indicates the status of this entry."
			::= { asDot1qVlanProvEntry 2 }

		
		-- 1.3.6.1.4.1.989.1.16.5.3.1.3.2
		asDot1qSsPortProvTable OBJECT-TYPE
			SYNTAX SEQUENCE OF AsDot1qSsPortProvEntry
			MAX-ACCESS not-accessible
			STATUS current
			DESCRIPTION
				"A table containing static per-port provisioning information 
				for all the SS ports allowed on this bridge.
				The table is read-create to allow NMS to provision ports 
				configuration before the first address is learned from the port.
				"
			::= { asDot1qVlan 2 }

		
		-- 1.3.6.1.4.1.989.1.16.5.3.1.3.2.1
		asDot1qSsPortProvEntry OBJECT-TYPE
			SYNTAX AsDot1qSsPortProvEntry
			MAX-ACCESS not-accessible
			STATUS current
			DESCRIPTION
				"One row per port MAC address."
			INDEX { asDot1qSsPortProvAddress }
			::= { asDot1qSsPortProvTable 1 }

		
		AsDot1qSsPortProvEntry ::=
			SEQUENCE { 
				asDot1qSsPortProvAddress
					MacAddress,
				asDot1qSsPortProvMode
					AsDot1qPortMode,
				asDot1qSsPortProvIngressFilterEnabled
					AsmaxBooleanSwitch,
				asDot1qSsPortProvAllowedFrameTypes
					AsDot1qAllowedFrameTypes,
				asDot1qSsPortProvPvid
					AsDot1qVlanId,
				asDot1qSsPortProvRowStatus
					RowStatus,
				asDot1qSsDefaultPriority
					Integer32,
				asDot1qSsSTagPvid
					AsDot1qVlanIdOrNone,
				asDot1qSsSTagUseSTagPriority
					AsmaxBooleanSwitch,
				asDot1qSsSTagPriority
					Integer32
			 }

		-- 1.3.6.1.4.1.989.1.16.5.3.1.3.2.1.1
		asDot1qSsPortProvAddress OBJECT-TYPE
			SYNTAX MacAddress
			MAX-ACCESS not-accessible
			STATUS current
			DESCRIPTION
				"MAC Address identifying the port. The port can be either pyhysical 
				(e.g. BS ethernet port) or virtual (eg. SS air interface port)."
			::= { asDot1qSsPortProvEntry 1 }

		
		-- 1.3.6.1.4.1.989.1.16.5.3.1.3.2.1.2
		asDot1qSsPortProvMode OBJECT-TYPE
			SYNTAX AsDot1qPortMode
			MAX-ACCESS read-create
			STATUS current
			DESCRIPTION
				"Configures standard (portModeVlan) behaviour or non standard 
				behaviour of the port (portModeRaw).
				In mode portModeRaw all port configuration and port Vlan list 
				are ignored. The traffic is allow to flow in and out unfiltered 
				and without changes to tagging."
			DEFVAL { portModeRaw }
			::= { asDot1qSsPortProvEntry 2 }

		
		-- 1.3.6.1.4.1.989.1.16.5.3.1.3.2.1.3
		asDot1qSsPortProvIngressFilterEnabled OBJECT-TYPE
			SYNTAX AsmaxBooleanSwitch
			MAX-ACCESS read-create
			STATUS current
			DESCRIPTION
				"When this is booleanTrue, the device will discard incoming
				frames for VLANs that are not included in this Port
				egress VLAN list as defined by asDot1qPortVlanListTable.
				When booleanFalse, the port will accept all incoming frames."
			REFERENCE
				"IEEE 802.1Q/D11 Section 12.10.1.4"
			DEFVAL { booleanTrue }
			::= { asDot1qSsPortProvEntry 3 }

		
		-- 1.3.6.1.4.1.989.1.16.5.3.1.3.2.1.4
		asDot1qSsPortProvAllowedFrameTypes OBJECT-TYPE
			SYNTAX AsDot1qAllowedFrameTypes
			MAX-ACCESS read-create
			STATUS current
			DESCRIPTION
				"When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitAll }
			::= { asDot1qSsPortProvEntry 4 }

		
		-- 1.3.6.1.4.1.989.1.16.5.3.1.3.2.1.5
		asDot1qSsPortProvPvid OBJECT-TYPE
			SYNTAX AsDot1qVlanId
			MAX-ACCESS read-create
			STATUS current
			DESCRIPTION
				"The PVID, the VLAN-ID assigned to untagged frames or
				Priority-Tagged frames received on this port."
			REFERENCE
				"IEEE 802.1Q/D11 Section 12.10.1.1"
			DEFVAL { 1 }
			::= { asDot1qSsPortProvEntry 5 }

		
		-- 1.3.6.1.4.1.989.1.16.5.3.1.3.2.1.6
		asDot1qSsPortProvRowStatus OBJECT-TYPE
			SYNTAX RowStatus
			MAX-ACCESS read-create
			STATUS current
			DESCRIPTION
				"This object indicates the status of this entry."
			::= { asDot1qSsPortProvEntry 6 }

		
		-- 1.3.6.1.4.1.989.1.16.5.3.1.3.2.1.7
		asDot1qSsDefaultPriority OBJECT-TYPE
			SYNTAX Integer32 (0..7)
			MAX-ACCESS read-create
			STATUS current
			DESCRIPTION
				"Priority applied to VLAN tag for untagged framed 
				where PVID is used."
			DEFVAL { 0 }
			::= { asDot1qSsPortProvEntry 7 }

		
		-- 1.3.6.1.4.1.989.1.16.5.3.1.3.2.1.8
		asDot1qSsSTagPvid OBJECT-TYPE
			SYNTAX AsDot1qVlanIdOrNone
			MAX-ACCESS read-create
			STATUS current
			DESCRIPTION
				"This object is defined using 802.1q and 802.ad terminology.
				The object is used when asDot1qBridgeSTagConfigMode is set to sTagUseSsConfig.
				Object defines VLAN ID applied to outer tag (S-TAG) of the frame when 
				the bridge works in Providers mode (as defined in asDot1qBridgeMode). 
				All the packets received from the C-Bridge of this port
				(tagged or untagged with C-TAG i.e Q-tag) are tagged with this VID."
			DEFVAL { 1 }
			::= { asDot1qSsPortProvEntry 8 }

		
		-- 1.3.6.1.4.1.989.1.16.5.3.1.3.2.1.9
		asDot1qSsSTagUseSTagPriority OBJECT-TYPE
			SYNTAX AsmaxBooleanSwitch
			MAX-ACCESS read-create
			STATUS current
			DESCRIPTION
				"When false (default) the user priority for STag is copied from 
				the inner tag (CTag).
				When true the user priority for STag is taken from 
				the object asDot1qSsSTagPriority."
			DEFVAL { booleanFalse }
			::= { asDot1qSsPortProvEntry 9 }

		
		-- 1.3.6.1.4.1.989.1.16.5.3.1.3.2.1.10
		asDot1qSsSTagPriority OBJECT-TYPE
			SYNTAX Integer32 (0..7)
			MAX-ACCESS read-create
			STATUS current
			DESCRIPTION
				"This object is defined using 802.1q and 802.ad terminology.
				It is only used when instructed by asDot1qSsSTagUseSTagDefaultPriority.
				Object defines VLAN user priority applied to outer tag (S-TAG) of the frame 
				when the bridge works in Providers mode (as defined in asDot1qBridgeMode). 
				All the packets received from the C-Bridge of this port
				(tagged or untagged with C-TAG i.e Q-tag) are tagged with this VLAN user priority."
			DEFVAL { 0 }
			::= { asDot1qSsPortProvEntry 10 }

		
		-- 1.3.6.1.4.1.989.1.16.5.3.1.3.3
		asDot1qBsPortProvTable OBJECT-TYPE
			SYNTAX SEQUENCE OF AsDot1qBsPortProvEntry
			MAX-ACCESS not-accessible
			STATUS current
			DESCRIPTION
				"A table containing static per-port provisioning information 
				for all the BS ports allowed on this bridge. In most cases BS 
				will have only one port but table allows for multiport BSs.
				The table is read-write to allow BS to initialise the row(s) for its port(s).
				The NMS will provision the port properties by updating existing rows."
			::= { asDot1qVlan 3 }

		
		-- 1.3.6.1.4.1.989.1.16.5.3.1.3.3.1
		asDot1qBsPortProvEntry OBJECT-TYPE
			SYNTAX AsDot1qBsPortProvEntry
			MAX-ACCESS not-accessible
			STATUS current
			DESCRIPTION
				"One row per port MAC address."
			INDEX { asDot1qBsPortProvAddress }
			::= { asDot1qBsPortProvTable 1 }

		
		AsDot1qBsPortProvEntry ::=
			SEQUENCE { 
				asDot1qBsPortProvAddress
					MacAddress,
				asDot1qBsPortProvMode
					AsDot1qPortMode,
				asDot1qBsPortProvIngressFilterEnabled
					AsmaxBooleanSwitch,
				asDot1qBsPortProvAllowedFrameTypes
					AsDot1qAllowedFrameTypes,
				asDot1qBsPortProvPvid
					AsDot1qVlanId,
				asDot1qBsDefaultPriority
					Integer32
			 }

		-- 1.3.6.1.4.1.989.1.16.5.3.1.3.3.1.1
		asDot1qBsPortProvAddress OBJECT-TYPE
			SYNTAX MacAddress
			MAX-ACCESS not-accessible
			STATUS current
			DESCRIPTION
				"MAC Address identifying the port. The port can be either pyhysical 
				(e.g. BS ethernet port) or virtual (eg. SS air interface port)."
			::= { asDot1qBsPortProvEntry 1 }

		
		-- 1.3.6.1.4.1.989.1.16.5.3.1.3.3.1.2
		asDot1qBsPortProvMode OBJECT-TYPE
			SYNTAX AsDot1qPortMode
			MAX-ACCESS read-write
			STATUS current
			DESCRIPTION
				"Configures standard (portModeVlan) behaviour or non standard 
				behaviour of the port (portModeRaw).
				In mode portModeRaw all port configuration and port Vlan list 
				are ignored. The traffic is allow to flow in and out unfiltered 
				and without changes to tagging."
			DEFVAL { portModeRaw }
			::= { asDot1qBsPortProvEntry 2 }

		
		-- 1.3.6.1.4.1.989.1.16.5.3.1.3.3.1.3
		asDot1qBsPortProvIngressFilterEnabled OBJECT-TYPE
			SYNTAX AsmaxBooleanSwitch
			MAX-ACCESS read-write
			STATUS current
			DESCRIPTION
				"When this is booleanTrue, the device will discard incoming
				frames for VLANs that are not included in this Port
				egress VLAN list as defined by asDot1qPortVlanListTable.
				When booleanFalse, the port will accept all incoming frames."
			REFERENCE
				"IEEE 802.1Q/D11 Section 12.10.1.4"
			DEFVAL { booleanTrue }
			::= { asDot1qBsPortProvEntry 3 }

		
		-- 1.3.6.1.4.1.989.1.16.5.3.1.3.3.1.4
		asDot1qBsPortProvAllowedFrameTypes OBJECT-TYPE
			SYNTAX AsDot1qAllowedFrameTypes
			MAX-ACCESS read-write
			STATUS current
			DESCRIPTION
				"When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitAll }
			::= { asDot1qBsPortProvEntry 4 }

		
		-- 1.3.6.1.4.1.989.1.16.5.3.1.3.3.1.5
		asDot1qBsPortProvPvid OBJECT-TYPE
			SYNTAX AsDot1qVlanId
			MAX-ACCESS read-write
			STATUS current
			DESCRIPTION
				"The PVID, the VLAN-ID assigned to untagged frames or
				Priority-Tagged frames received on this port."
			REFERENCE
				"IEEE 802.1Q/D11 Section 12.10.1.1"
			DEFVAL { 1 }
			::= { asDot1qBsPortProvEntry 5 }

		
		-- 1.3.6.1.4.1.989.1.16.5.3.1.3.3.1.6
		asDot1qBsDefaultPriority OBJECT-TYPE
			SYNTAX Integer32 (0..7)
			MAX-ACCESS read-write
			STATUS current
			DESCRIPTION
				"Priority applied to VLAN tag for untagged framed 
				where PVID is used."
			DEFVAL { 0 }
			::= { asDot1qBsPortProvEntry 6 }

		
		-- 1.3.6.1.4.1.989.1.16.5.3.1.3.4
		asDot1qPortVlanListTable OBJECT-TYPE
			SYNTAX SEQUENCE OF AsDot1qPortVlanListEntry
			MAX-ACCESS not-accessible
			STATUS current
			DESCRIPTION
				"Combined port egress VLAN lists. It is defined as a map between VLANs 
				and ports with the tagging behaviour additionally defined."
			::= { asDot1qVlan 4 }

		
		-- 1.3.6.1.4.1.989.1.16.5.3.1.3.4.1
		asDot1qPortVlanListEntry OBJECT-TYPE
			SYNTAX AsDot1qPortVlanListEntry
			MAX-ACCESS not-accessible
			STATUS current
			DESCRIPTION
				"Description."
			INDEX { asDot1qPortVlanListPortAddress, asDot1qPortVlanListVlanId }
			::= { asDot1qPortVlanListTable 1 }

		
		AsDot1qPortVlanListEntry ::=
			SEQUENCE { 
				asDot1qPortVlanListPortAddress
					MacAddress,
				asDot1qPortVlanListVlanId
					AsDot1qVlanId,
				asDot1qPortVlanListTagging
					INTEGER,
				asDot1qPortVlanListRowStatus
					RowStatus
			 }

		-- 1.3.6.1.4.1.989.1.16.5.3.1.3.4.1.1
		asDot1qPortVlanListPortAddress OBJECT-TYPE
			SYNTAX MacAddress
			MAX-ACCESS not-accessible
			STATUS current
			DESCRIPTION
				"Mac address of the port this table defines VLAN list for egress
				forwarding and ingress filtering."
			::= { asDot1qPortVlanListEntry 1 }

		
		-- 1.3.6.1.4.1.989.1.16.5.3.1.3.4.1.2
		asDot1qPortVlanListVlanId OBJECT-TYPE
			SYNTAX AsDot1qVlanId
			MAX-ACCESS not-accessible
			STATUS current
			DESCRIPTION
				"ID of the VLAN member of the port vlan list."
			::= { asDot1qPortVlanListEntry 2 }

		
		-- 1.3.6.1.4.1.989.1.16.5.3.1.3.4.1.3
		asDot1qPortVlanListTagging OBJECT-TYPE
			SYNTAX INTEGER
				{
				tagged(1),
				untagged(2)
				}
			MAX-ACCESS read-create
			STATUS current
			DESCRIPTION
				"Tagging behaviour for the given VLAN on a given port in egress."
			DEFVAL { tagged }
			::= { asDot1qPortVlanListEntry 3 }

		
		-- 1.3.6.1.4.1.989.1.16.5.3.1.3.4.1.4
		asDot1qPortVlanListRowStatus OBJECT-TYPE
			SYNTAX RowStatus
			MAX-ACCESS read-create
			STATUS current
			DESCRIPTION
				"This object indicates the status of this entry."
			::= { asDot1qPortVlanListEntry 4 }

		
		-- 1.3.6.1.4.1.989.1.16.5.3.2
		asqBridgeConformance OBJECT IDENTIFIER ::= { asMaxQBridge 2 }

		
		-- 1.3.6.1.4.1.989.1.16.5.3.2.1
		asqBridgeConfigGroup OBJECT-GROUP
			OBJECTS { asDot1qTpFdbPortAddress, asDot1qTpFdbStatus, asDot1qPortVlanListTagging, asDot1qBsPortProvPvid, asDot1qBsPortProvAllowedFrameTypes, 
				asDot1qBsPortProvIngressFilterEnabled, asDot1qBsPortProvMode, asDot1qSsPortProvRowStatus, asDot1qSsPortProvPvid, asDot1qSsPortProvAllowedFrameTypes, 
				asDot1qSsPortProvIngressFilterEnabled, asDot1qSsPortProvMode, asDot1qBridgeAgeingTime, asDot1qSsDefaultPriority, asDot1qBsDefaultPriority, 
				asDot1qBridgeSTagEthertype, asDot1qPortVlanListRowStatus, asDot1qBridgeMode, asDot1qBridgeMgmtVlanId, asDot1qBridgeReservedVlan1, 
				asDot1qBridgeReservedVlan2, asDot1qBridgeReservedVlan3, asDot1qVlanProvRowStatus, asDot1qBridgeSTagConfigMode, asDot1qSsSTagPvid, 
				asDot1qSsSTagUseSTagPriority, asDot1qBridgeFloodingEnabled, asDot1qBasePortCircuit, asDot1qBasePortIfIndex, asDot1qBasePort, 
				asDot1qSsSTagPriority, asDot1qBridgeSTagPvid, asDot1qBridgeSTagUseSTagPriority, asDot1qBridgeSTagPriority }
			STATUS current
			DESCRIPTION 
				"A collection of objects providing device-level control
				and status information for the Virtual LAN bridge
				services."
			::= { asqBridgeConformance 1 }

		
		-- 1.3.6.1.4.1.989.1.16.5.3.2.2
		asqBridgeCompliance MODULE-COMPLIANCE
			STATUS current
			DESCRIPTION 
				"Description."
			MODULE -- this module
				MANDATORY-GROUPS { asqBridgeConfigGroup }
			::= { asqBridgeConformance 2 }

		
	
	END

--
-- AIRSPAN-Q-BRIDGE-MIB.mib
--
