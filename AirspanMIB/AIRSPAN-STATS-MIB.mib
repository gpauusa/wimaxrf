--
-- AIRSPAN-STATS-MIB.mib
-- MIB generated by MG-SOFT Visual MIB Builder Version 5.0  Build 250
-- Wednesday, April 23, 2008 at 15:02:48
--

-- *****************************************************************
-- AIRSPAN-STATS-MIB.mib
-- Copyright (c) 2007 by Airspan Networks, Inc.
-- All rights reserved.
-- *****************************************************************

	AIRSPAN-STATS-MIB DEFINITIONS ::= BEGIN
 
		IMPORTS
			asMaxBS			
				FROM AIRSPAN-PRODUCTS-MIB			
			ifNumber, ifIndex, ifDescr, ifType, ifMtu, 
			ifSpeed, ifPhysAddress, ifAdminStatus, ifOperStatus, ifLastChange, 
			ifInOctets, ifInUcastPkts, ifInNUcastPkts, ifInDiscards, ifInErrors, 
			ifInUnknownProtos, ifOutOctets, ifOutUcastPkts, ifOutNUcastPkts, ifOutDiscards, 
			ifOutErrors, ifOutQLen, ifSpecific			
				FROM IF-MIB			
			OBJECT-GROUP			
				FROM SNMPv2-CONF			
			Integer32, Counter32, Counter64, OBJECT-TYPE, MODULE-IDENTITY			
				FROM SNMPv2-SMI			
			MacAddress, TEXTUAL-CONVENTION			
				FROM SNMPv2-TC;
	
	
		-- 1.3.6.1.4.1.989.1.16.2.6
		asMaxBsStats MODULE-IDENTITY 
			LAST-UPDATED "200804231502Z"		-- April 23, 2008 at 15:02 GMT
			ORGANIZATION 
				"Airspan Communications Ltd."
			CONTACT-INFO 
				"Contact-info."
			DESCRIPTION 
				"Description."
			REVISION "200804231502Z"		-- April 23, 2008 at 15:02 GMT
			DESCRIPTION 
				"Draft 6:
				Extended asMaxBsStatsBsAirInterfaceTable with asMaxBsStatsIfAllocateBwrOpps,
				asMaxBsStatsIfUsedBwrOpps and asMaxBsStatsIfCollidedBwrOpps columns
				Added a new table asMaxBsStatsBsAirInterfaceDynamicTable"
			REVISION "200711291112Z"		-- November 29, 2007 at 11:12 GMT
			DESCRIPTION 
				"Draft 5:
				Unused and duplicated texutal convention AsMaxBooleanSwitch removed."
			REVISION "200704171403Z"		-- April 17, 2007 at 14:03 GMT
			DESCRIPTION 
				"Draft 4:
				Deprecated asMaxBsStatsIfDlFrameContention
				Added asMaxBsStatsIfDlFrameSize"
			REVISION "200703261100Z"		-- March 26, 2007 at 11:00 GMT
			DESCRIPTION 
				"Draft 3:
				Added Uplink/Downlink Sdu/Octet Management/Traffic counters to asMaxBsStatsBsAirInterfaceTable.
				Added asMaxBsStatsSsEthernetTable.
				Added asMaxBsStatsSsAirInterfaceTable
				Changed asMaxBsStatsSsModSubChanMacAddress from read-write to not-accessible.
				Changed asMaxBsStatsSsPacketCounterMacAddress from read-write to not-accessible."
			REVISION "200702071534Z"		-- February 07, 2007 at 15:34 GMT
			DESCRIPTION 
				"Draft 2:
				Corrected Module OID
				from 1.3.6.1.4.1.989.1.16.2.1
				to   1.3.6.1.4.1.989.1.16.2.6"
			REVISION "200701300954Z"		-- January 30, 2007 at 09:54 GMT
			DESCRIPTION 
				"Draft 1
				Initial version based on private statistics tables from AIRSPAN-DEMOMAX-MIB."
			::= { asMaxBS 6 }

		
	
--
-- Textual conventions
--
	
--  Textual conventions
-- 
-- Textual conventions
-- 
		AsmaxExtendedVlanId ::= TEXTUAL-CONVENTION
			DISPLAY-HINT 
				"d"
			STATUS current
			DESCRIPTION 
				"Defines VLAN ID for use in Airspan specifc 
				implementation of VLAN bridge.
				Range 1.4094 is reserved for standard (802.1Q) VLAN IDs.
				Value of 4096 is used for untagged traffic."
			REFERENCE 
				"RFC2674, IEEE802.1Q, IEEE801.3"
			SYNTAX INTEGER (1..4094 | 4096)

		AsmaxPollGroupIdOrNone ::= TEXTUAL-CONVENTION
			DISPLAY-HINT 
				"d"
			STATUS current
			DESCRIPTION 
				"The polling group IDs are subject to custom implementation 
				This ID should be unique withing the BS domain.
				The value of 0 means none."
			SYNTAX INTEGER (0 | 1..253)

		AsmaxTrafficPortVlanMode ::= TEXTUAL-CONVENTION
			STATUS current
			DESCRIPTION 
				"Defines how the Ethernet frames are encoded 
				on local traffic Ethernet port.
				vlanModeRaw - Vlan tags are not checked
				vlanCheckAndTag - Vlan tags are checked 
				(invalid discarded) and frames are tagged
				vlanCheckAndUntag - Vlan tags are checked 
				and frames are not tagged (tags are stripped).
				"
			SYNTAX INTEGER
				{
				vlanModeRaw(0),
				vlanModeCheckAndTag(1),
				vlanModeCheckAndUntag(2)
				}

		AsmaxConnectionId ::= TEXTUAL-CONVENTION
			DISPLAY-HINT 
				"d"
			STATUS current
			DESCRIPTION 
				"Connection Identifier defined temporarly in absence of 
				the textual convention defined in later drafts of the standard MIB."
			SYNTAX INTEGER (0..65535)

		AsmaxPollGroupId ::= TEXTUAL-CONVENTION
			DISPLAY-HINT 
				"d"
			STATUS current
			DESCRIPTION 
				"The polling group IDs are subject to custom implementation 
				This ID should be unique withing the BS domain."
			SYNTAX INTEGER (1..253)

		AsmaxDSFieldValue ::= TEXTUAL-CONVENTION
			DISPLAY-HINT 
				"d"
			STATUS current
			DESCRIPTION 
				"Differential service field value used in the TOS field of the IP header."
			SYNTAX INTEGER (0..63)

		AsmaxWmanIfChannelNumber ::= TEXTUAL-CONVENTION
			STATUS current
			DESCRIPTION 
				"Physical channel number.
				This object is defined in Draft6 of WMAN-IF-MIB."
			SYNTAX INTEGER (0..199)

		AsmaxWmanIfCidType ::= TEXTUAL-CONVENTION
			STATUS current
			DESCRIPTION 
				"Type of CID.
				This object is defined in Draft6 of WMAN-IF-MIB."
			SYNTAX INTEGER (0..65535)

		AsmaxWmanIfSfState ::= TEXTUAL-CONVENTION
			STATUS current
			DESCRIPTION 
				"Defines the state of a service flow.
				This object is defined in Draft6 of WMAN-IF-MIB."
			SYNTAX INTEGER
				{
				authorized(1),
				admitted(2),
				active(3)
				}

		AsmaxWmanIfCsSpecification ::= TEXTUAL-CONVENTION
			STATUS current
			DESCRIPTION 
				"Defines the types of convergence sublayer.
				This object is defined in Draft6 of WMAN-IF-MIB."
			SYNTAX INTEGER
				{
				noCs(0),
				packetIpV4(1),
				packetIpV6(2),
				packet802dot3Ethernet(3),
				packet802dot1QVlan(4),
				packetIpV4Over802dot3(5),
				packetIpV6Over802dot3(6),
				packetIpV4Over802dot1Q(7),
				packetIpV6Over802dot1Q(8),
				atm(9)
				}

		AsmaxAction ::= TEXTUAL-CONVENTION
			STATUS current
			DESCRIPTION 
				"Universal encoding for Asmax Actions.
				The object of this type should be implemented as follows:
				- When value set to actionExecute value, 
				  instructs the agent to execute the action
				- When set to value different than actionExecute it
				  should be ignored
				- When read it should return actionIgnore"
			SYNTAX INTEGER
				{
				actionIgnore(0),
				actionApply(1)
				}

	
--
-- Node definitions
--
	
		-- 1.3.6.1.4.1.989.1.16.2.6.1
		asMaxBsStatsConformance OBJECT IDENTIFIER ::= { asMaxBsStats 1 }

		
		-- 1.3.6.1.4.1.989.1.16.2.6.1.1
		asMaxBsStatsConfigurationGroup OBJECT-GROUP
			OBJECTS { asMaxBsStatsIfDlFrameOverhead, asMaxBsStatsIfDlFrameDataModBpsk, asMaxBsStatsIfDlFrameDataModQpsk12, asMaxBsStatsIfDlFrameDataModQpsk34, asMaxBsStatsIfDlFrameDataMod16Qam12, 
				asMaxBsStatsIfDlFrameDataMod16Qam34, asMaxBsStatsIfDlFrameDataMod64Qam23, asMaxBsStatsIfDlFrameDataMod64Qam34, asMaxBsStatsIfDlFrameAvailable, asMaxBsStatsIfUlFrameOverhead, 
				asMaxBsStatsIfUlFrameDataModBpsk, asMaxBsStatsIfUlFrameDataModQpsk12, asMaxBsStatsIfUlFrameDataModQpsk34, asMaxBsStatsIfUlFrameDataMod16Qam12, asMaxBsStatsIfUlFrameDataMod16Qam34, 
				asMaxBsStatsIfUlFrameDataMod64Qam23, asMaxBsStatsIfUlFrameDataMod64Qam34, asMaxBsStatsIfUlFrameAvailable, asMaxBsStatsIfUlFrameContention, asMaxBsStatsIfUlFrameSize, 
				asMaxBsStatsIfBroadcastSduCount, asMaxBsStatsIfBroadcastOctetCount, asMaxBsStatsSsModSubChanDlModBpsk, asMaxBsStatsSsModSubChanDlModQpsk12, asMaxBsStatsSsModSubChanDlModQpsk34, 
				asMaxBsStatsSsModSubChanDlMod16Qam12, asMaxBsStatsSsModSubChanDlMod16Qam34, asMaxBsStatsSsModSubChanDlMod64Qam23, asMaxBsStatsSsModSubChanDlMod64Qam34, asMaxBsStatsSsModSubChanUlModBpsk, 
				asMaxBsStatsSsModSubChanUlModQpsk12, asMaxBsStatsSsModSubChanUlModQpsk34, asMaxBsStatsSsModSubChanUlMod16Qam12, asMaxBsStatsSsModSubChanUlMod16Qam34, asMaxBsStatsSsModSubChanUlMod64Qam23, 
				asMaxBsStatsSsModSubChanUlMod64Qam34, asMaxBsStatsSsModSubChanUlScwSixteenth, asMaxBsStatsSsModSubChanUlScwEighth, asMaxBsStatsSsModSubChanUlScwQuarter, asMaxBsStatsSsModSubChanUlScwHalf, 
				asMaxBsStatsSsModSubChanUlScwFull, asMaxBsStatsSsUlBasicSduCount, asMaxBsStatsSsDlBasicSduCount, asMaxBsStatsSsUlPrimarySduCount, asMaxBsStatsSsDlPrimarySduCount, 
				asMaxBsStatsSsUlSecondarySduCount, asMaxBsStatsSsDlSecondarySduCount, asMaxBsStatsSsUplinkSduCount, asMaxBsStatsSsDownlinkSduCount, asMaxBsStatsSsUlBasicOctetCount, 
				asMaxBsStatsSsDlBasicOctetCount, asMaxBsStatsSsUlPrimaryOctetCount, asMaxBsStatsSsDlPrimaryOctetCount, asMaxBsStatsSsUlSecondaryOctetCount, asMaxBsStatsSsDlSecondaryOctetCount, 
				asMaxBsStatsSsUplinkOctetCount, asMaxBsStatsIfUlMgmtSduCount, asMaxBsStatsIfDlMgmtSduCount, asMaxBsStatsIfUlMgmtOctetCount, asMaxBsStatsIfDlMgmtOctetCount, 
				asMaxBsStatsIfUlTrafficSduCount, asMaxBsStatsIfDlTrafficSduCount, asMaxBsStatsIfUlTrafficOctetCount, asMaxBsStatsIfDlTrafficOctetCount, asMaxBsStatsSsEthernetInOctets, 
				asMaxBsStatsSsEthernetInUcastPkts, asMaxBsStatsSsEthernetInDiscards, asMaxBsStatsSsEthernetOutOctets, asMaxBsStatsSsEthernetOutUcastPkts, asMaxBsStatsSsAirIfUlMgmtSduCount, 
				asMaxBsStatsSsAirIfDlMgmtSduCount, asMaxBsStatsSsAirIfUlMgmtOctetCount, asMaxBsStatsSsAirIfDlMgmtOctetCount, asMaxBsStatsSsAirIfUlTrafficSduCount, asMaxBsStatsSsAirIfDlTrafficSduCount, 
				asMaxBsStatsSsAirIfUlTrafficOctetCount, asMaxBsStatsSsAirIfDlTrafficOctetCount, asMaxBsStatsIfUsedBwrOpps, asMaxBsStatsIfCollidedBwrOpps, asMaxBsStatsIfAllocateBwrOpps, 
				asMaxBsStatsObservationPeriod, asMaxBsStatsIfDlPacketsPerSec, asMaxBsStatsIfDlBytesPerSec, asMaxBsStatsIfUlPacketsPerSec, asMaxBsStatsIfUlBytesPerSec, 
				asMaxBsStatsIfUlFrameAvailableDynamic, asMaxBsStatsIfDlFrameAvailableDynamic, asMaxBsStatsSsEthernetOutDiscards, asMaxBsStatsIfDlFrameSize, asMaxBsStatsSsDownlinkOctetCount
				 }
			STATUS current
			DESCRIPTION 
				"Description."
			::= { asMaxBsStatsConformance 1 }

		
		-- 1.3.6.1.4.1.989.1.16.2.6.1.2
		asMaxBsStatsDeprecatedGroup OBJECT-GROUP
			OBJECTS { asMaxBsStatsIfDlFrameContention }
			STATUS deprecated
			DESCRIPTION 
				"Description."
			::= { asMaxBsStatsConformance 2 }

		
		-- 1.3.6.1.4.1.989.1.16.2.6.2
		asMaxBsStatsNotifications OBJECT IDENTIFIER ::= { asMaxBsStats 2 }

		
		-- 1.3.6.1.4.1.989.1.16.2.6.3
		asMaxBsStatsData OBJECT IDENTIFIER ::= { asMaxBsStats 3 }

		
		-- 1.3.6.1.4.1.989.1.16.2.6.3.1
		asMaxBsStatsBsAirInterfaceTable OBJECT-TYPE
			SYNTAX SEQUENCE OF AsMaxBsStatsBsAirInterfaceEntry
			MAX-ACCESS not-accessible
			STATUS current
			DESCRIPTION
				"This table contains uplink and downlink frame usage per interface.
				It contains downlink broadcast SDU and Octet counts as well.
				
				The counters are reset to zero when the base station is reset."
			::= { asMaxBsStatsData 1 }

		
		-- 1.3.6.1.4.1.989.1.16.2.6.3.1.1
		asMaxBsStatsBsAirInterfaceEntry OBJECT-TYPE
			SYNTAX AsMaxBsStatsBsAirInterfaceEntry
			MAX-ACCESS not-accessible
			STATUS current
			DESCRIPTION
				"This table contains uplink and downlink frame usage per interface.
				It contains downlink broadcast SDU and Octet counts as well.
				
				It is indexed by ifIndex."
			INDEX { ifIndex }
			::= { asMaxBsStatsBsAirInterfaceTable 1 }

		
		AsMaxBsStatsBsAirInterfaceEntry ::=
			SEQUENCE { 
				asMaxBsStatsIfDlFrameOverhead
					Integer32,
				asMaxBsStatsIfDlFrameDataModBpsk
					Integer32,
				asMaxBsStatsIfDlFrameDataModQpsk12
					Integer32,
				asMaxBsStatsIfDlFrameDataModQpsk34
					Integer32,
				asMaxBsStatsIfDlFrameDataMod16Qam12
					Integer32,
				asMaxBsStatsIfDlFrameDataMod16Qam34
					Integer32,
				asMaxBsStatsIfDlFrameDataMod64Qam23
					Integer32,
				asMaxBsStatsIfDlFrameDataMod64Qam34
					Integer32,
				asMaxBsStatsIfDlFrameAvailable
					Integer32,
				asMaxBsStatsIfDlFrameContention
					Integer32,
				asMaxBsStatsIfUlFrameOverhead
					Integer32,
				asMaxBsStatsIfUlFrameDataModBpsk
					Integer32,
				asMaxBsStatsIfUlFrameDataModQpsk12
					Integer32,
				asMaxBsStatsIfUlFrameDataModQpsk34
					Integer32,
				asMaxBsStatsIfUlFrameDataMod16Qam12
					Integer32,
				asMaxBsStatsIfUlFrameDataMod16Qam34
					Integer32,
				asMaxBsStatsIfUlFrameDataMod64Qam23
					Integer32,
				asMaxBsStatsIfUlFrameDataMod64Qam34
					Integer32,
				asMaxBsStatsIfUlFrameAvailable
					Integer32,
				asMaxBsStatsIfUlFrameContention
					Integer32,
				asMaxBsStatsIfUlFrameSize
					Integer32,
				asMaxBsStatsIfBroadcastSduCount
					Counter64,
				asMaxBsStatsIfBroadcastOctetCount
					Counter64,
				asMaxBsStatsIfUlMgmtSduCount
					Counter64,
				asMaxBsStatsIfDlMgmtSduCount
					Counter64,
				asMaxBsStatsIfUlMgmtOctetCount
					Counter64,
				asMaxBsStatsIfDlMgmtOctetCount
					Counter64,
				asMaxBsStatsIfUlTrafficSduCount
					Counter64,
				asMaxBsStatsIfDlTrafficSduCount
					Counter64,
				asMaxBsStatsIfUlTrafficOctetCount
					Counter64,
				asMaxBsStatsIfDlTrafficOctetCount
					Counter64,
				asMaxBsStatsIfDlFrameSize
					Integer32,
				asMaxBsStatsIfAllocateBwrOpps
					Counter64,
				asMaxBsStatsIfUsedBwrOpps
					Counter64,
				asMaxBsStatsIfCollidedBwrOpps
					Counter64
			 }

		-- 1.3.6.1.4.1.989.1.16.2.6.3.1.1.1
		asMaxBsStatsIfDlFrameOverhead OBJECT-TYPE
			SYNTAX Integer32 (0..100)
			MAX-ACCESS read-only
			STATUS current
			DESCRIPTION
				"The proportion of the downlink subframe that is used but does not carry user data
				- this includes the FCH, DLMAP, ULMAP, DCD, UCD, any preambles used on the downlink bursts, and any frame gaps.
				Note that it does not include PDUs that contain management messages
				- these are considered to be user data for frame usage purposes."
			::= { asMaxBsStatsBsAirInterfaceEntry 1 }

		
		-- 1.3.6.1.4.1.989.1.16.2.6.3.1.1.2
		asMaxBsStatsIfDlFrameDataModBpsk OBJECT-TYPE
			SYNTAX Integer32 (0..100)
			MAX-ACCESS read-only
			STATUS current
			DESCRIPTION
				"Percentage of downlink frames using BPSK modulation."
			::= { asMaxBsStatsBsAirInterfaceEntry 2 }

		
		-- 1.3.6.1.4.1.989.1.16.2.6.3.1.1.3
		asMaxBsStatsIfDlFrameDataModQpsk12 OBJECT-TYPE
			SYNTAX Integer32 (0..100)
			MAX-ACCESS read-only
			STATUS current
			DESCRIPTION
				"Percentage of downlink frames using QPSK 1/2 modulation."
			::= { asMaxBsStatsBsAirInterfaceEntry 3 }

		
		-- 1.3.6.1.4.1.989.1.16.2.6.3.1.1.4
		asMaxBsStatsIfDlFrameDataModQpsk34 OBJECT-TYPE
			SYNTAX Integer32 (0..100)
			MAX-ACCESS read-only
			STATUS current
			DESCRIPTION
				"Percentage of downlink frames using QPSK 3/4 modulation."
			::= { asMaxBsStatsBsAirInterfaceEntry 4 }

		
		-- 1.3.6.1.4.1.989.1.16.2.6.3.1.1.5
		asMaxBsStatsIfDlFrameDataMod16Qam12 OBJECT-TYPE
			SYNTAX Integer32 (0..100)
			MAX-ACCESS read-only
			STATUS current
			DESCRIPTION
				"Percentage of downlink frames using 16 QAM 1/2 modulation."
			::= { asMaxBsStatsBsAirInterfaceEntry 5 }

		
		-- 1.3.6.1.4.1.989.1.16.2.6.3.1.1.6
		asMaxBsStatsIfDlFrameDataMod16Qam34 OBJECT-TYPE
			SYNTAX Integer32 (0..100)
			MAX-ACCESS read-only
			STATUS current
			DESCRIPTION
				"Percentage of downlink frames using 16 QAM 3/4 modulation."
			::= { asMaxBsStatsBsAirInterfaceEntry 6 }

		
		-- 1.3.6.1.4.1.989.1.16.2.6.3.1.1.7
		asMaxBsStatsIfDlFrameDataMod64Qam23 OBJECT-TYPE
			SYNTAX Integer32 (0..100)
			MAX-ACCESS read-only
			STATUS current
			DESCRIPTION
				"Percentage of downlink frames using 64 QAM 2/3 modulation."
			::= { asMaxBsStatsBsAirInterfaceEntry 7 }

		
		-- 1.3.6.1.4.1.989.1.16.2.6.3.1.1.8
		asMaxBsStatsIfDlFrameDataMod64Qam34 OBJECT-TYPE
			SYNTAX Integer32 (0..100)
			MAX-ACCESS read-only
			STATUS current
			DESCRIPTION
				"Percentage of downlink frames using 64 QAM 3/4 modulation."
			::= { asMaxBsStatsBsAirInterfaceEntry 8 }

		
		-- 1.3.6.1.4.1.989.1.16.2.6.3.1.1.9
		asMaxBsStatsIfDlFrameAvailable OBJECT-TYPE
			SYNTAX Integer32 (0..100)
			MAX-ACCESS read-only
			STATUS current
			DESCRIPTION
				"The proportion of the downlink subframe that is unused (empty).
				"
			::= { asMaxBsStatsBsAirInterfaceEntry 9 }

		
		-- 1.3.6.1.4.1.989.1.16.2.6.3.1.1.10
		asMaxBsStatsIfDlFrameContention OBJECT-TYPE
			SYNTAX Integer32 (0..100)
			MAX-ACCESS read-only
			STATUS deprecated
			DESCRIPTION
				"The proportion of the downlink subframe that coincides with the uplink contention regions.
				The BS does not transmit in these regions so they are effectively occupied for downlink purposes.
				"
			::= { asMaxBsStatsBsAirInterfaceEntry 10 }

		
		-- 1.3.6.1.4.1.989.1.16.2.6.3.1.1.11
		asMaxBsStatsIfUlFrameOverhead OBJECT-TYPE
			SYNTAX Integer32 (0..100)
			MAX-ACCESS read-only
			STATUS current
			DESCRIPTION
				"The proportion of the uplink subframe that is used but does not carry any data.
				- this is total of all preambles used on the uplink SS transmissions bursts, 
				plus any allocations made for non-data purposes (e.g. ranging).
				"
			::= { asMaxBsStatsBsAirInterfaceEntry 11 }

		
		-- 1.3.6.1.4.1.989.1.16.2.6.3.1.1.12
		asMaxBsStatsIfUlFrameDataModBpsk OBJECT-TYPE
			SYNTAX Integer32 (0..100)
			MAX-ACCESS read-only
			STATUS current
			DESCRIPTION
				"Percentage of uplink frames using BPSK modulation.
				"
			::= { asMaxBsStatsBsAirInterfaceEntry 12 }

		
		-- 1.3.6.1.4.1.989.1.16.2.6.3.1.1.13
		asMaxBsStatsIfUlFrameDataModQpsk12 OBJECT-TYPE
			SYNTAX Integer32 (0..100)
			MAX-ACCESS read-only
			STATUS current
			DESCRIPTION
				"Percentage of uplink frames using QPSK 1/2 modulation."
			::= { asMaxBsStatsBsAirInterfaceEntry 13 }

		
		-- 1.3.6.1.4.1.989.1.16.2.6.3.1.1.14
		asMaxBsStatsIfUlFrameDataModQpsk34 OBJECT-TYPE
			SYNTAX Integer32 (0..100)
			MAX-ACCESS read-only
			STATUS current
			DESCRIPTION
				"Percentage of uplink frames using QPSK 3/4 modulation."
			::= { asMaxBsStatsBsAirInterfaceEntry 14 }

		
		-- 1.3.6.1.4.1.989.1.16.2.6.3.1.1.15
		asMaxBsStatsIfUlFrameDataMod16Qam12 OBJECT-TYPE
			SYNTAX Integer32 (0..100)
			MAX-ACCESS read-only
			STATUS current
			DESCRIPTION
				"Percentage of uplink frames using 16 QAM 1/2 modulation."
			::= { asMaxBsStatsBsAirInterfaceEntry 15 }

		
		-- 1.3.6.1.4.1.989.1.16.2.6.3.1.1.16
		asMaxBsStatsIfUlFrameDataMod16Qam34 OBJECT-TYPE
			SYNTAX Integer32 (0..100)
			MAX-ACCESS read-only
			STATUS current
			DESCRIPTION
				"Percentage of uplink frames using 16 QAM 3/4 modulation."
			::= { asMaxBsStatsBsAirInterfaceEntry 16 }

		
		-- 1.3.6.1.4.1.989.1.16.2.6.3.1.1.17
		asMaxBsStatsIfUlFrameDataMod64Qam23 OBJECT-TYPE
			SYNTAX Integer32 (0..100)
			MAX-ACCESS read-only
			STATUS current
			DESCRIPTION
				"Percentage of uplink frames using 64 QAM 2/3 modulation."
			::= { asMaxBsStatsBsAirInterfaceEntry 17 }

		
		-- 1.3.6.1.4.1.989.1.16.2.6.3.1.1.18
		asMaxBsStatsIfUlFrameDataMod64Qam34 OBJECT-TYPE
			SYNTAX Integer32 (0..100)
			MAX-ACCESS read-only
			STATUS current
			DESCRIPTION
				"Percentage of uplink frames using 64 QAM 3/4 modulation."
			::= { asMaxBsStatsBsAirInterfaceEntry 18 }

		
		-- 1.3.6.1.4.1.989.1.16.2.6.3.1.1.19
		asMaxBsStatsIfUlFrameAvailable OBJECT-TYPE
			SYNTAX Integer32 (0..100)
			MAX-ACCESS read-only
			STATUS current
			DESCRIPTION
				"The proportion of the uplink subframe that is unused (empty).
				
				
				"
			::= { asMaxBsStatsBsAirInterfaceEntry 19 }

		
		-- 1.3.6.1.4.1.989.1.16.2.6.3.1.1.20
		asMaxBsStatsIfUlFrameContention OBJECT-TYPE
			SYNTAX Integer32 (0..100)
			MAX-ACCESS read-only
			STATUS current
			DESCRIPTION
				"The proportion of the uplink subframe that is used for contention regions.
				"
			::= { asMaxBsStatsBsAirInterfaceEntry 20 }

		
		-- 1.3.6.1.4.1.989.1.16.2.6.3.1.1.21
		asMaxBsStatsIfUlFrameSize OBJECT-TYPE
			SYNTAX Integer32 (0..100)
			MAX-ACCESS read-only
			STATUS current
			DESCRIPTION
				"The proportion of the whole frame period that the uplink subframe occupies.
				"
			::= { asMaxBsStatsBsAirInterfaceEntry 21 }

		
		-- 1.3.6.1.4.1.989.1.16.2.6.3.1.1.22
		asMaxBsStatsIfBroadcastSduCount OBJECT-TYPE
			SYNTAX Counter64
			MAX-ACCESS read-only
			STATUS current
			DESCRIPTION
				"Downlink broadcast SDU count."
			::= { asMaxBsStatsBsAirInterfaceEntry 22 }

		
		-- 1.3.6.1.4.1.989.1.16.2.6.3.1.1.23
		asMaxBsStatsIfBroadcastOctetCount OBJECT-TYPE
			SYNTAX Counter64
			MAX-ACCESS read-only
			STATUS current
			DESCRIPTION
				"Downlink broadcast octet count."
			::= { asMaxBsStatsBsAirInterfaceEntry 23 }

		
		-- 1.3.6.1.4.1.989.1.16.2.6.3.1.1.24
		asMaxBsStatsIfUlMgmtSduCount OBJECT-TYPE
			SYNTAX Counter64
			MAX-ACCESS read-only
			STATUS current
			DESCRIPTION
				"Uplink management SDU count.
				This includes Basic, Primary, Secondary management traffic."
			::= { asMaxBsStatsBsAirInterfaceEntry 24 }

		
		-- 1.3.6.1.4.1.989.1.16.2.6.3.1.1.25
		asMaxBsStatsIfDlMgmtSduCount OBJECT-TYPE
			SYNTAX Counter64
			MAX-ACCESS read-only
			STATUS current
			DESCRIPTION
				"Downlink management SDU count.
				This includes Basic, Primary, Secondary management traffic."
			::= { asMaxBsStatsBsAirInterfaceEntry 25 }

		
		-- 1.3.6.1.4.1.989.1.16.2.6.3.1.1.26
		asMaxBsStatsIfUlMgmtOctetCount OBJECT-TYPE
			SYNTAX Counter64
			MAX-ACCESS read-only
			STATUS current
			DESCRIPTION
				"Uplink management octet count.
				This includes Basic, Primary, Secondary management traffic."
			::= { asMaxBsStatsBsAirInterfaceEntry 26 }

		
		-- 1.3.6.1.4.1.989.1.16.2.6.3.1.1.27
		asMaxBsStatsIfDlMgmtOctetCount OBJECT-TYPE
			SYNTAX Counter64
			MAX-ACCESS read-only
			STATUS current
			DESCRIPTION
				"Downlink management octet count.
				This includes Basic, Primary, Secondary management traffic."
			::= { asMaxBsStatsBsAirInterfaceEntry 27 }

		
		-- 1.3.6.1.4.1.989.1.16.2.6.3.1.1.28
		asMaxBsStatsIfUlTrafficSduCount OBJECT-TYPE
			SYNTAX Counter64
			MAX-ACCESS read-only
			STATUS current
			DESCRIPTION
				"Uplink traffic SDU count.
				This does not include the Basic, Primary or Secondary management traffic."
			::= { asMaxBsStatsBsAirInterfaceEntry 28 }

		
		-- 1.3.6.1.4.1.989.1.16.2.6.3.1.1.29
		asMaxBsStatsIfDlTrafficSduCount OBJECT-TYPE
			SYNTAX Counter64
			MAX-ACCESS read-only
			STATUS current
			DESCRIPTION
				"Downlink traffic SDU count.
				This does not include the Basic, Primary or Secondary management traffic.
				This does not include broadcast traffic."
			::= { asMaxBsStatsBsAirInterfaceEntry 29 }

		
		-- 1.3.6.1.4.1.989.1.16.2.6.3.1.1.30
		asMaxBsStatsIfUlTrafficOctetCount OBJECT-TYPE
			SYNTAX Counter64
			MAX-ACCESS read-only
			STATUS current
			DESCRIPTION
				"Uplink traffic octet count.
				This does not include the Basic, Primary or Secondary management traffic."
			::= { asMaxBsStatsBsAirInterfaceEntry 30 }

		
		-- 1.3.6.1.4.1.989.1.16.2.6.3.1.1.31
		asMaxBsStatsIfDlTrafficOctetCount OBJECT-TYPE
			SYNTAX Counter64
			MAX-ACCESS read-only
			STATUS current
			DESCRIPTION
				"Downlink traffic octet count.
				This does not include the Basic, Primary or Secondary management traffic.
				This does not include broadcast traffic."
			::= { asMaxBsStatsBsAirInterfaceEntry 31 }

		
		-- 1.3.6.1.4.1.989.1.16.2.6.3.1.1.32
		asMaxBsStatsIfDlFrameSize OBJECT-TYPE
			SYNTAX Integer32 (0..100)
			MAX-ACCESS read-only
			STATUS current
			DESCRIPTION
				"The proportion of the whole frame period that the downlink subframe occupies.
				"
			::= { asMaxBsStatsBsAirInterfaceEntry 32 }

		
		-- 1.3.6.1.4.1.989.1.16.2.6.3.1.1.33
		asMaxBsStatsIfAllocateBwrOpps OBJECT-TYPE
			SYNTAX Counter64
			MAX-ACCESS read-only
			STATUS current
			DESCRIPTION
				"The total number of allocated bandwidth request opportunities."
			::= { asMaxBsStatsBsAirInterfaceEntry 33 }

		
		-- 1.3.6.1.4.1.989.1.16.2.6.3.1.1.34
		asMaxBsStatsIfUsedBwrOpps OBJECT-TYPE
			SYNTAX Counter64
			MAX-ACCESS read-only
			STATUS current
			DESCRIPTION
				"The total number of used bandwidth request opportunities."
			::= { asMaxBsStatsBsAirInterfaceEntry 34 }

		
		-- 1.3.6.1.4.1.989.1.16.2.6.3.1.1.35
		asMaxBsStatsIfCollidedBwrOpps OBJECT-TYPE
			SYNTAX Counter64
			MAX-ACCESS read-only
			STATUS current
			DESCRIPTION
				"The total number of colliede bandwidth request opportunities."
			::= { asMaxBsStatsBsAirInterfaceEntry 35 }

		
		-- 1.3.6.1.4.1.989.1.16.2.6.3.2
		asMaxBsStatsSsModSubChanTable OBJECT-TYPE
			SYNTAX SEQUENCE OF AsMaxBsStatsSsModSubChanEntry
			MAX-ACCESS not-accessible
			STATUS current
			DESCRIPTION
				"This table contains modulation and sub-channelisation information per SS per Sector.
				It shows distribution of uplink and downlink modulation and uplink sub-channelisation widths.
				Each measurement gives the percentage of recent frames using the particular modulation or 
				sub-channelisation width."
			::= { asMaxBsStatsData 2 }

		
		-- 1.3.6.1.4.1.989.1.16.2.6.3.2.1
		asMaxBsStatsSsModSubChanEntry OBJECT-TYPE
			SYNTAX AsMaxBsStatsSsModSubChanEntry
			MAX-ACCESS not-accessible
			STATUS current
			DESCRIPTION
				"This table contains modulation and sub-channelisation information per SS per Sector.
				It shows distribution of uplink and downlink modulation and uplink sub-channelisation widths.
				Each measurement gives the percentage of recent frames using the particular modulation or 
				sub-channelisation width.
				
				It is indexed by ifIndex and SS MAC Address."
			INDEX { ifIndex, asMaxBsStatsSsModSubChanMacAddress }
			::= { asMaxBsStatsSsModSubChanTable 1 }

		
		AsMaxBsStatsSsModSubChanEntry ::=
			SEQUENCE { 
				asMaxBsStatsSsModSubChanMacAddress
					MacAddress,
				asMaxBsStatsSsModSubChanDlModBpsk
					Integer32,
				asMaxBsStatsSsModSubChanDlModQpsk12
					Integer32,
				asMaxBsStatsSsModSubChanDlModQpsk34
					Integer32,
				asMaxBsStatsSsModSubChanDlMod16Qam12
					Integer32,
				asMaxBsStatsSsModSubChanDlMod16Qam34
					Integer32,
				asMaxBsStatsSsModSubChanDlMod64Qam23
					Integer32,
				asMaxBsStatsSsModSubChanDlMod64Qam34
					Integer32,
				asMaxBsStatsSsModSubChanUlModBpsk
					Integer32,
				asMaxBsStatsSsModSubChanUlModQpsk12
					Integer32,
				asMaxBsStatsSsModSubChanUlModQpsk34
					Integer32,
				asMaxBsStatsSsModSubChanUlMod16Qam12
					Integer32,
				asMaxBsStatsSsModSubChanUlMod16Qam34
					Integer32,
				asMaxBsStatsSsModSubChanUlMod64Qam23
					Integer32,
				asMaxBsStatsSsModSubChanUlMod64Qam34
					Integer32,
				asMaxBsStatsSsModSubChanUlScwSixteenth
					Integer32,
				asMaxBsStatsSsModSubChanUlScwEighth
					Integer32,
				asMaxBsStatsSsModSubChanUlScwQuarter
					Integer32,
				asMaxBsStatsSsModSubChanUlScwHalf
					Integer32,
				asMaxBsStatsSsModSubChanUlScwFull
					Integer32
			 }

		-- 1.3.6.1.4.1.989.1.16.2.6.3.2.1.1
		asMaxBsStatsSsModSubChanMacAddress OBJECT-TYPE
			SYNTAX MacAddress
			MAX-ACCESS not-accessible
			STATUS current
			DESCRIPTION
				"SS MAC Address"
			::= { asMaxBsStatsSsModSubChanEntry 1 }

		
		-- 1.3.6.1.4.1.989.1.16.2.6.3.2.1.2
		asMaxBsStatsSsModSubChanDlModBpsk OBJECT-TYPE
			SYNTAX Integer32 (0..100)
			MAX-ACCESS read-only
			STATUS current
			DESCRIPTION
				"Percentage of downlink frames using BPSK modulation.
				"
			::= { asMaxBsStatsSsModSubChanEntry 2 }

		
		-- 1.3.6.1.4.1.989.1.16.2.6.3.2.1.3
		asMaxBsStatsSsModSubChanDlModQpsk12 OBJECT-TYPE
			SYNTAX Integer32 (0..100)
			MAX-ACCESS read-only
			STATUS current
			DESCRIPTION
				"Percentage of downlink frames using QPSK 1/2 modulation."
			::= { asMaxBsStatsSsModSubChanEntry 3 }

		
		-- 1.3.6.1.4.1.989.1.16.2.6.3.2.1.4
		asMaxBsStatsSsModSubChanDlModQpsk34 OBJECT-TYPE
			SYNTAX Integer32 (0..100)
			MAX-ACCESS read-only
			STATUS current
			DESCRIPTION
				"Percentage of downlink frames using QPSK 3/4 modulation."
			::= { asMaxBsStatsSsModSubChanEntry 4 }

		
		-- 1.3.6.1.4.1.989.1.16.2.6.3.2.1.5
		asMaxBsStatsSsModSubChanDlMod16Qam12 OBJECT-TYPE
			SYNTAX Integer32 (0..100)
			MAX-ACCESS read-only
			STATUS current
			DESCRIPTION
				"Percentage of downlink frames using 16 QAM 1/2 modulation."
			::= { asMaxBsStatsSsModSubChanEntry 5 }

		
		-- 1.3.6.1.4.1.989.1.16.2.6.3.2.1.6
		asMaxBsStatsSsModSubChanDlMod16Qam34 OBJECT-TYPE
			SYNTAX Integer32 (0..100)
			MAX-ACCESS read-only
			STATUS current
			DESCRIPTION
				"Percentage of downlink frames using 16 QAM 3/4 modulation."
			::= { asMaxBsStatsSsModSubChanEntry 6 }

		
		-- 1.3.6.1.4.1.989.1.16.2.6.3.2.1.7
		asMaxBsStatsSsModSubChanDlMod64Qam23 OBJECT-TYPE
			SYNTAX Integer32 (0..100)
			MAX-ACCESS read-only
			STATUS current
			DESCRIPTION
				"Percentage of downlink frames using 64 QAM 2/3 modulation."
			::= { asMaxBsStatsSsModSubChanEntry 7 }

		
		-- 1.3.6.1.4.1.989.1.16.2.6.3.2.1.8
		asMaxBsStatsSsModSubChanDlMod64Qam34 OBJECT-TYPE
			SYNTAX Integer32 (0..100)
			MAX-ACCESS read-only
			STATUS current
			DESCRIPTION
				"Percentage of downlink frames using 64 QAM 3/4 modulation."
			::= { asMaxBsStatsSsModSubChanEntry 8 }

		
		-- 1.3.6.1.4.1.989.1.16.2.6.3.2.1.9
		asMaxBsStatsSsModSubChanUlModBpsk OBJECT-TYPE
			SYNTAX Integer32 (0..100)
			MAX-ACCESS read-only
			STATUS current
			DESCRIPTION
				"Percentage of uplink frames using BPSK modulation.
				"
			::= { asMaxBsStatsSsModSubChanEntry 9 }

		
		-- 1.3.6.1.4.1.989.1.16.2.6.3.2.1.10
		asMaxBsStatsSsModSubChanUlModQpsk12 OBJECT-TYPE
			SYNTAX Integer32 (0..100)
			MAX-ACCESS read-only
			STATUS current
			DESCRIPTION
				"Percentage of uplink frames using QPSK 1/2 modulation."
			::= { asMaxBsStatsSsModSubChanEntry 10 }

		
		-- 1.3.6.1.4.1.989.1.16.2.6.3.2.1.11
		asMaxBsStatsSsModSubChanUlModQpsk34 OBJECT-TYPE
			SYNTAX Integer32 (0..100)
			MAX-ACCESS read-only
			STATUS current
			DESCRIPTION
				"Percentage of uplink frames using QPSK 3/4 modulation."
			::= { asMaxBsStatsSsModSubChanEntry 11 }

		
		-- 1.3.6.1.4.1.989.1.16.2.6.3.2.1.12
		asMaxBsStatsSsModSubChanUlMod16Qam12 OBJECT-TYPE
			SYNTAX Integer32 (0..100)
			MAX-ACCESS read-only
			STATUS current
			DESCRIPTION
				"Percentage of uplink frames using 16 QAM 1/2 modulation."
			::= { asMaxBsStatsSsModSubChanEntry 12 }

		
		-- 1.3.6.1.4.1.989.1.16.2.6.3.2.1.13
		asMaxBsStatsSsModSubChanUlMod16Qam34 OBJECT-TYPE
			SYNTAX Integer32 (0..100)
			MAX-ACCESS read-only
			STATUS current
			DESCRIPTION
				"Percentage of uplink frames using 16 QAM 3/4 modulation."
			::= { asMaxBsStatsSsModSubChanEntry 13 }

		
		-- 1.3.6.1.4.1.989.1.16.2.6.3.2.1.14
		asMaxBsStatsSsModSubChanUlMod64Qam23 OBJECT-TYPE
			SYNTAX Integer32 (0..100)
			MAX-ACCESS read-only
			STATUS current
			DESCRIPTION
				"Percentage of uplink frames using 64 QAM 2/3 modulation."
			::= { asMaxBsStatsSsModSubChanEntry 14 }

		
		-- 1.3.6.1.4.1.989.1.16.2.6.3.2.1.15
		asMaxBsStatsSsModSubChanUlMod64Qam34 OBJECT-TYPE
			SYNTAX Integer32 (0..100)
			MAX-ACCESS read-only
			STATUS current
			DESCRIPTION
				"Percentage of uplink frames using 64 QAM 3/4 modulation."
			::= { asMaxBsStatsSsModSubChanEntry 15 }

		
		-- 1.3.6.1.4.1.989.1.16.2.6.3.2.1.16
		asMaxBsStatsSsModSubChanUlScwSixteenth OBJECT-TYPE
			SYNTAX Integer32 (0..100)
			MAX-ACCESS read-only
			STATUS current
			DESCRIPTION
				"Percentage of uplink frames using 1/16 sub-channelisation width."
			::= { asMaxBsStatsSsModSubChanEntry 16 }

		
		-- 1.3.6.1.4.1.989.1.16.2.6.3.2.1.17
		asMaxBsStatsSsModSubChanUlScwEighth OBJECT-TYPE
			SYNTAX Integer32 (0..100)
			MAX-ACCESS read-only
			STATUS current
			DESCRIPTION
				"Percentage of uplink frames using 1/8 sub-channelisation width."
			::= { asMaxBsStatsSsModSubChanEntry 17 }

		
		-- 1.3.6.1.4.1.989.1.16.2.6.3.2.1.18
		asMaxBsStatsSsModSubChanUlScwQuarter OBJECT-TYPE
			SYNTAX Integer32 (0..100)
			MAX-ACCESS read-only
			STATUS current
			DESCRIPTION
				"Percentage of uplink frames using 1/4 sub-channelisation width."
			::= { asMaxBsStatsSsModSubChanEntry 18 }

		
		-- 1.3.6.1.4.1.989.1.16.2.6.3.2.1.19
		asMaxBsStatsSsModSubChanUlScwHalf OBJECT-TYPE
			SYNTAX Integer32 (0..100)
			MAX-ACCESS read-only
			STATUS current
			DESCRIPTION
				"Percentage of uplink frames using 1/2 sub-channelisation width."
			::= { asMaxBsStatsSsModSubChanEntry 19 }

		
		-- 1.3.6.1.4.1.989.1.16.2.6.3.2.1.20
		asMaxBsStatsSsModSubChanUlScwFull OBJECT-TYPE
			SYNTAX Integer32 (0..100)
			MAX-ACCESS read-only
			STATUS current
			DESCRIPTION
				"Percentage of uplink frames using no sub-channelisation."
			::= { asMaxBsStatsSsModSubChanEntry 20 }

		
		-- 1.3.6.1.4.1.989.1.16.2.6.3.3
		asMaxBsStatsSsPacketCounterTable OBJECT-TYPE
			SYNTAX SEQUENCE OF AsMaxBsStatsSsPacketCounterEntry
			MAX-ACCESS not-accessible
			STATUS current
			DESCRIPTION
				"This table contains SS traffic count information.
				There is one row for every SS registered with BS.
				This table effectively extends the table wmanIfBsRegisteredSsTable.
				The objects in this table are for statistical purposes.
				
				The counters are reset when the base station is reset.
				The counters are created on SS registration and kept for 3 days after an SS has deregistered (unless BS is reset)."
			::= { asMaxBsStatsData 3 }

		
		-- 1.3.6.1.4.1.989.1.16.2.6.3.3.1
		asMaxBsStatsSsPacketCounterEntry OBJECT-TYPE
			SYNTAX AsMaxBsStatsSsPacketCounterEntry
			MAX-ACCESS not-accessible
			STATUS current
			DESCRIPTION
				"This table contains SS traffic count information.
				There is one row for every SS registered with BS.
				This table effectively extends the table wmanIfBsRegisteredSsTable.
				The objects in this table are for statistical purposes.
				
				It is indexed by SS MAC Address."
			INDEX { asMaxBsStatsSsPacketCounterMacAddress }
			::= { asMaxBsStatsSsPacketCounterTable 1 }

		
		AsMaxBsStatsSsPacketCounterEntry ::=
			SEQUENCE { 
				asMaxBsStatsSsPacketCounterMacAddress
					MacAddress,
				asMaxBsStatsSsUlBasicSduCount
					Counter64,
				asMaxBsStatsSsDlBasicSduCount
					Counter64,
				asMaxBsStatsSsUlPrimarySduCount
					Counter64,
				asMaxBsStatsSsDlPrimarySduCount
					Counter64,
				asMaxBsStatsSsUlSecondarySduCount
					Counter64,
				asMaxBsStatsSsDlSecondarySduCount
					Counter64,
				asMaxBsStatsSsUplinkSduCount
					Counter64,
				asMaxBsStatsSsDownlinkSduCount
					Counter64,
				asMaxBsStatsSsUlBasicOctetCount
					Counter64,
				asMaxBsStatsSsDlBasicOctetCount
					Counter64,
				asMaxBsStatsSsUlPrimaryOctetCount
					Counter64,
				asMaxBsStatsSsDlPrimaryOctetCount
					Counter64,
				asMaxBsStatsSsUlSecondaryOctetCount
					Counter64,
				asMaxBsStatsSsDlSecondaryOctetCount
					Counter64,
				asMaxBsStatsSsUplinkOctetCount
					Counter64,
				asMaxBsStatsSsDownlinkOctetCount
					Counter64
			 }

		-- 1.3.6.1.4.1.989.1.16.2.6.3.3.1.1
		asMaxBsStatsSsPacketCounterMacAddress OBJECT-TYPE
			SYNTAX MacAddress
			MAX-ACCESS not-accessible
			STATUS current
			DESCRIPTION
				"SS MAC Address"
			::= { asMaxBsStatsSsPacketCounterEntry 1 }

		
		-- 1.3.6.1.4.1.989.1.16.2.6.3.3.1.2
		asMaxBsStatsSsUlBasicSduCount OBJECT-TYPE
			SYNTAX Counter64
			MAX-ACCESS read-only
			STATUS current
			DESCRIPTION
				"SDU count on SS basic management uplink (to BS) connection."
			::= { asMaxBsStatsSsPacketCounterEntry 2 }

		
		-- 1.3.6.1.4.1.989.1.16.2.6.3.3.1.3
		asMaxBsStatsSsDlBasicSduCount OBJECT-TYPE
			SYNTAX Counter64
			MAX-ACCESS read-only
			STATUS current
			DESCRIPTION
				"SDU count on SS basic management downlink (from BS) connection."
			::= { asMaxBsStatsSsPacketCounterEntry 3 }

		
		-- 1.3.6.1.4.1.989.1.16.2.6.3.3.1.4
		asMaxBsStatsSsUlPrimarySduCount OBJECT-TYPE
			SYNTAX Counter64
			MAX-ACCESS read-only
			STATUS current
			DESCRIPTION
				"SDU count on SS primary management uplink (to BS) connection."
			::= { asMaxBsStatsSsPacketCounterEntry 4 }

		
		-- 1.3.6.1.4.1.989.1.16.2.6.3.3.1.5
		asMaxBsStatsSsDlPrimarySduCount OBJECT-TYPE
			SYNTAX Counter64
			MAX-ACCESS read-only
			STATUS current
			DESCRIPTION
				"SDU count on SS primary management downlink (from BS) connection."
			::= { asMaxBsStatsSsPacketCounterEntry 5 }

		
		-- 1.3.6.1.4.1.989.1.16.2.6.3.3.1.6
		asMaxBsStatsSsUlSecondarySduCount OBJECT-TYPE
			SYNTAX Counter64
			MAX-ACCESS read-only
			STATUS current
			DESCRIPTION
				"SDU count on SS secondary management uplink (to BS) connection."
			::= { asMaxBsStatsSsPacketCounterEntry 6 }

		
		-- 1.3.6.1.4.1.989.1.16.2.6.3.3.1.7
		asMaxBsStatsSsDlSecondarySduCount OBJECT-TYPE
			SYNTAX Counter64
			MAX-ACCESS read-only
			STATUS current
			DESCRIPTION
				"SDU count on SS secondary management downlink (from BS) connection."
			::= { asMaxBsStatsSsPacketCounterEntry 7 }

		
		-- 1.3.6.1.4.1.989.1.16.2.6.3.3.1.8
		asMaxBsStatsSsUplinkSduCount OBJECT-TYPE
			SYNTAX Counter64
			MAX-ACCESS read-only
			STATUS current
			DESCRIPTION
				"SDU count on SS uplink (to BS) connection.
				This does not include management traffic."
			::= { asMaxBsStatsSsPacketCounterEntry 8 }

		
		-- 1.3.6.1.4.1.989.1.16.2.6.3.3.1.9
		asMaxBsStatsSsDownlinkSduCount OBJECT-TYPE
			SYNTAX Counter64
			MAX-ACCESS read-only
			STATUS current
			DESCRIPTION
				"SDU count on SS downlink (from BS) connection.
				This reports only unicast and not broadcast/multicast or management traffic."
			::= { asMaxBsStatsSsPacketCounterEntry 9 }

		
		-- 1.3.6.1.4.1.989.1.16.2.6.3.3.1.10
		asMaxBsStatsSsUlBasicOctetCount OBJECT-TYPE
			SYNTAX Counter64
			MAX-ACCESS read-only
			STATUS current
			DESCRIPTION
				"Octet count on SS basic management uplink (to BS) connection."
			::= { asMaxBsStatsSsPacketCounterEntry 10 }

		
		-- 1.3.6.1.4.1.989.1.16.2.6.3.3.1.11
		asMaxBsStatsSsDlBasicOctetCount OBJECT-TYPE
			SYNTAX Counter64
			MAX-ACCESS read-only
			STATUS current
			DESCRIPTION
				"Octet count on SS basic management downlink (from BS) connection."
			::= { asMaxBsStatsSsPacketCounterEntry 11 }

		
		-- 1.3.6.1.4.1.989.1.16.2.6.3.3.1.12
		asMaxBsStatsSsUlPrimaryOctetCount OBJECT-TYPE
			SYNTAX Counter64
			MAX-ACCESS read-only
			STATUS current
			DESCRIPTION
				"Octet count on SS primary management uplink (to BS) connection."
			::= { asMaxBsStatsSsPacketCounterEntry 12 }

		
		-- 1.3.6.1.4.1.989.1.16.2.6.3.3.1.13
		asMaxBsStatsSsDlPrimaryOctetCount OBJECT-TYPE
			SYNTAX Counter64
			MAX-ACCESS read-only
			STATUS current
			DESCRIPTION
				"Octet count on SS primary management downlink (from BS) connection."
			::= { asMaxBsStatsSsPacketCounterEntry 13 }

		
		-- 1.3.6.1.4.1.989.1.16.2.6.3.3.1.14
		asMaxBsStatsSsUlSecondaryOctetCount OBJECT-TYPE
			SYNTAX Counter64
			MAX-ACCESS read-only
			STATUS current
			DESCRIPTION
				"Octet count on SS secondary management uplink (to BS) connection."
			::= { asMaxBsStatsSsPacketCounterEntry 14 }

		
		-- 1.3.6.1.4.1.989.1.16.2.6.3.3.1.15
		asMaxBsStatsSsDlSecondaryOctetCount OBJECT-TYPE
			SYNTAX Counter64
			MAX-ACCESS read-only
			STATUS current
			DESCRIPTION
				"Octet count on SS secondary management downlink (from BS) connection."
			::= { asMaxBsStatsSsPacketCounterEntry 15 }

		
		-- 1.3.6.1.4.1.989.1.16.2.6.3.3.1.16
		asMaxBsStatsSsUplinkOctetCount OBJECT-TYPE
			SYNTAX Counter64
			MAX-ACCESS read-only
			STATUS current
			DESCRIPTION
				"Octet count on SS uplink (to BS) connection.
				This does not include management traffic."
			::= { asMaxBsStatsSsPacketCounterEntry 16 }

		
		-- 1.3.6.1.4.1.989.1.16.2.6.3.3.1.17
		asMaxBsStatsSsDownlinkOctetCount OBJECT-TYPE
			SYNTAX Counter64
			MAX-ACCESS read-only
			STATUS current
			DESCRIPTION
				"Octet count on SS downlink (from BS) connection.
				This reports only unicast and not broadcast/multicast or management traffic."
			::= { asMaxBsStatsSsPacketCounterEntry 17 }

		
		-- 1.3.6.1.4.1.989.1.16.2.6.3.4
		asMaxBsStatsSsEthernetTable OBJECT-TYPE
			SYNTAX SEQUENCE OF AsMaxBsStatsSsEthernetEntry
			MAX-ACCESS not-accessible
			STATUS current
			DESCRIPTION
				"Description."
			::= { asMaxBsStatsData 4 }

		
		-- 1.3.6.1.4.1.989.1.16.2.6.3.4.1
		asMaxBsStatsSsEthernetEntry OBJECT-TYPE
			SYNTAX AsMaxBsStatsSsEthernetEntry
			MAX-ACCESS not-accessible
			STATUS current
			DESCRIPTION
				"Description."
			INDEX { asMaxBsStatsSsEthernetMacAddress }
			::= { asMaxBsStatsSsEthernetTable 1 }

		
		AsMaxBsStatsSsEthernetEntry ::=
			SEQUENCE { 
				asMaxBsStatsSsEthernetMacAddress
					MacAddress,
				asMaxBsStatsSsEthernetInOctets
					Counter32,
				asMaxBsStatsSsEthernetInUcastPkts
					Counter32,
				asMaxBsStatsSsEthernetInDiscards
					Counter32,
				asMaxBsStatsSsEthernetOutOctets
					Counter32,
				asMaxBsStatsSsEthernetOutUcastPkts
					Counter32,
				asMaxBsStatsSsEthernetOutDiscards
					Counter32
			 }

		-- 1.3.6.1.4.1.989.1.16.2.6.3.4.1.1
		asMaxBsStatsSsEthernetMacAddress OBJECT-TYPE
			SYNTAX MacAddress
			MAX-ACCESS not-accessible
			STATUS current
			DESCRIPTION
				"SS MAC Address"
			::= { asMaxBsStatsSsEthernetEntry 1 }

		
		-- 1.3.6.1.4.1.989.1.16.2.6.3.4.1.2
		asMaxBsStatsSsEthernetInOctets OBJECT-TYPE
			SYNTAX Counter32
			MAX-ACCESS read-only
			STATUS current
			DESCRIPTION
				"Number of octets that were received on the Ethernet port of the SS."
			::= { asMaxBsStatsSsEthernetEntry 2 }

		
		-- 1.3.6.1.4.1.989.1.16.2.6.3.4.1.3
		asMaxBsStatsSsEthernetInUcastPkts OBJECT-TYPE
			SYNTAX Counter32
			MAX-ACCESS read-only
			STATUS current
			DESCRIPTION
				"Number of unicast packets that were received on the Ethernet port of the SS."
			::= { asMaxBsStatsSsEthernetEntry 3 }

		
		-- 1.3.6.1.4.1.989.1.16.2.6.3.4.1.4
		asMaxBsStatsSsEthernetInDiscards OBJECT-TYPE
			SYNTAX Counter32
			MAX-ACCESS read-only
			STATUS current
			DESCRIPTION
				"Number of discarded packets that were received on the Ethernet port of the SS."
			::= { asMaxBsStatsSsEthernetEntry 4 }

		
		-- 1.3.6.1.4.1.989.1.16.2.6.3.4.1.5
		asMaxBsStatsSsEthernetOutOctets OBJECT-TYPE
			SYNTAX Counter32
			MAX-ACCESS read-only
			STATUS current
			DESCRIPTION
				"Number of octets that were transmitted to the Ethernet port of the SS."
			::= { asMaxBsStatsSsEthernetEntry 5 }

		
		-- 1.3.6.1.4.1.989.1.16.2.6.3.4.1.6
		asMaxBsStatsSsEthernetOutUcastPkts OBJECT-TYPE
			SYNTAX Counter32
			MAX-ACCESS read-only
			STATUS current
			DESCRIPTION
				"Number of unicast packets that were transmitted to the Ethernet port of the SS."
			::= { asMaxBsStatsSsEthernetEntry 6 }

		
		-- 1.3.6.1.4.1.989.1.16.2.6.3.4.1.7
		asMaxBsStatsSsEthernetOutDiscards OBJECT-TYPE
			SYNTAX Counter32
			MAX-ACCESS read-only
			STATUS current
			DESCRIPTION
				"Number of discarded packets that were not transmitted to the Ethernet port of the SS."
			::= { asMaxBsStatsSsEthernetEntry 7 }

		
		-- 1.3.6.1.4.1.989.1.16.2.6.3.5
		asMaxBsStatsSsAirInterfaceTable OBJECT-TYPE
			SYNTAX SEQUENCE OF AsMaxBsStatsSsAirInterfaceEntry
			MAX-ACCESS not-accessible
			STATUS current
			DESCRIPTION
				"Description."
			::= { asMaxBsStatsData 5 }

		
		-- 1.3.6.1.4.1.989.1.16.2.6.3.5.1
		asMaxBsStatsSsAirInterfaceEntry OBJECT-TYPE
			SYNTAX AsMaxBsStatsSsAirInterfaceEntry
			MAX-ACCESS not-accessible
			STATUS current
			DESCRIPTION
				"Description."
			INDEX { asMaxBsStatsSsAirIfMacAddress }
			::= { asMaxBsStatsSsAirInterfaceTable 1 }

		
		AsMaxBsStatsSsAirInterfaceEntry ::=
			SEQUENCE { 
				asMaxBsStatsSsAirIfMacAddress
					MacAddress,
				asMaxBsStatsSsAirIfUlMgmtSduCount
					Counter64,
				asMaxBsStatsSsAirIfDlMgmtSduCount
					Counter64,
				asMaxBsStatsSsAirIfUlMgmtOctetCount
					Counter64,
				asMaxBsStatsSsAirIfDlMgmtOctetCount
					Counter64,
				asMaxBsStatsSsAirIfUlTrafficSduCount
					Counter64,
				asMaxBsStatsSsAirIfDlTrafficSduCount
					Counter64,
				asMaxBsStatsSsAirIfUlTrafficOctetCount
					Counter64,
				asMaxBsStatsSsAirIfDlTrafficOctetCount
					Counter64
			 }

		-- 1.3.6.1.4.1.989.1.16.2.6.3.5.1.2
		asMaxBsStatsSsAirIfMacAddress OBJECT-TYPE
			SYNTAX MacAddress
			MAX-ACCESS not-accessible
			STATUS current
			DESCRIPTION
				"Description."
			::= { asMaxBsStatsSsAirInterfaceEntry 2 }

		
		-- 1.3.6.1.4.1.989.1.16.2.6.3.5.1.3
		asMaxBsStatsSsAirIfUlMgmtSduCount OBJECT-TYPE
			SYNTAX Counter64
			MAX-ACCESS read-only
			STATUS current
			DESCRIPTION
				"Description."
			::= { asMaxBsStatsSsAirInterfaceEntry 3 }

		
		-- 1.3.6.1.4.1.989.1.16.2.6.3.5.1.4
		asMaxBsStatsSsAirIfDlMgmtSduCount OBJECT-TYPE
			SYNTAX Counter64
			MAX-ACCESS read-only
			STATUS current
			DESCRIPTION
				"Description."
			::= { asMaxBsStatsSsAirInterfaceEntry 4 }

		
		-- 1.3.6.1.4.1.989.1.16.2.6.3.5.1.5
		asMaxBsStatsSsAirIfUlMgmtOctetCount OBJECT-TYPE
			SYNTAX Counter64
			MAX-ACCESS read-only
			STATUS current
			DESCRIPTION
				"Description."
			::= { asMaxBsStatsSsAirInterfaceEntry 5 }

		
		-- 1.3.6.1.4.1.989.1.16.2.6.3.5.1.6
		asMaxBsStatsSsAirIfDlMgmtOctetCount OBJECT-TYPE
			SYNTAX Counter64
			MAX-ACCESS read-only
			STATUS current
			DESCRIPTION
				"Description."
			::= { asMaxBsStatsSsAirInterfaceEntry 6 }

		
		-- 1.3.6.1.4.1.989.1.16.2.6.3.5.1.7
		asMaxBsStatsSsAirIfUlTrafficSduCount OBJECT-TYPE
			SYNTAX Counter64
			MAX-ACCESS read-only
			STATUS current
			DESCRIPTION
				"Description."
			::= { asMaxBsStatsSsAirInterfaceEntry 7 }

		
		-- 1.3.6.1.4.1.989.1.16.2.6.3.5.1.8
		asMaxBsStatsSsAirIfDlTrafficSduCount OBJECT-TYPE
			SYNTAX Counter64
			MAX-ACCESS read-only
			STATUS current
			DESCRIPTION
				"Description."
			::= { asMaxBsStatsSsAirInterfaceEntry 8 }

		
		-- 1.3.6.1.4.1.989.1.16.2.6.3.5.1.9
		asMaxBsStatsSsAirIfUlTrafficOctetCount OBJECT-TYPE
			SYNTAX Counter64
			MAX-ACCESS read-only
			STATUS current
			DESCRIPTION
				"Description."
			::= { asMaxBsStatsSsAirInterfaceEntry 9 }

		
		-- 1.3.6.1.4.1.989.1.16.2.6.3.5.1.10
		asMaxBsStatsSsAirIfDlTrafficOctetCount OBJECT-TYPE
			SYNTAX Counter64
			MAX-ACCESS read-only
			STATUS current
			DESCRIPTION
				"Description."
			::= { asMaxBsStatsSsAirInterfaceEntry 10 }

		
		-- 1.3.6.1.4.1.989.1.16.2.6.3.6
		asMaxBsStatsBsAirInterfaceDynamicTable OBJECT-TYPE
			SYNTAX SEQUENCE OF AsMaxBsStatsBsAirInterfaceDynamicEntry
			MAX-ACCESS not-accessible
			STATUS current
			DESCRIPTION
				"This table contains uplink and downlink rate and frame usage per interface
				in last time period. 
								
				The counters are reset to zero when the base station is reset."
			::= { asMaxBsStatsData 6 }

		
		-- 1.3.6.1.4.1.989.1.16.2.6.3.6.1
		asMaxBsStatsBsAirInterfaceDynamicEntry OBJECT-TYPE
			SYNTAX AsMaxBsStatsBsAirInterfaceDynamicEntry
			MAX-ACCESS not-accessible
			STATUS current
			DESCRIPTION
				"This table contains uplink and downlink rate and frame usage per interface
				in last time period. 
				
				It is indexed by ifIndex."
			INDEX { ifIndex }
			::= { asMaxBsStatsBsAirInterfaceDynamicTable 1 }

		
		AsMaxBsStatsBsAirInterfaceDynamicEntry ::=
			SEQUENCE { 
				asMaxBsStatsObservationPeriod
					Integer32,
				asMaxBsStatsIfDlFrameAvailableDynamic
					Integer32,
				asMaxBsStatsIfUlFrameAvailableDynamic
					Integer32,
				asMaxBsStatsIfUlBytesPerSec
					Integer32,
				asMaxBsStatsIfUlPacketsPerSec
					Integer32,
				asMaxBsStatsIfDlBytesPerSec
					Integer32,
				asMaxBsStatsIfDlPacketsPerSec
					Integer32
			 }

		-- 1.3.6.1.4.1.989.1.16.2.6.3.6.1.1
		asMaxBsStatsObservationPeriod OBJECT-TYPE
			SYNTAX Integer32 (1..60)
			MAX-ACCESS read-write
			STATUS current
			DESCRIPTION
				"Last time period for which statistics in this table calculated.
				In minutes , range 1-60 minutes, default 5 minutes."
			DEFVAL { 5 }
			::= { asMaxBsStatsBsAirInterfaceDynamicEntry 1 }

		
		-- 1.3.6.1.4.1.989.1.16.2.6.3.6.1.2
		asMaxBsStatsIfDlFrameAvailableDynamic OBJECT-TYPE
			SYNTAX Integer32 (0..100)
			MAX-ACCESS read-only
			STATUS current
			DESCRIPTION
				"The proportion of the downlink subframe that is unused (empty).
				Measured in last time period defined by observation period"
			::= { asMaxBsStatsBsAirInterfaceDynamicEntry 2 }

		
		-- 1.3.6.1.4.1.989.1.16.2.6.3.6.1.3
		asMaxBsStatsIfUlFrameAvailableDynamic OBJECT-TYPE
			SYNTAX Integer32 (0..100)
			MAX-ACCESS read-only
			STATUS current
			DESCRIPTION
				"The proportion of the downlink subframe that is unused (empty).
				Measured in last time period defined by observation period"
			::= { asMaxBsStatsBsAirInterfaceDynamicEntry 3 }

		
		-- 1.3.6.1.4.1.989.1.16.2.6.3.6.1.4
		asMaxBsStatsIfUlBytesPerSec OBJECT-TYPE
			SYNTAX Integer32
			MAX-ACCESS read-only
			STATUS current
			DESCRIPTION
				"The rate of uplink stream in bytes, accumulated in by observation period."
			::= { asMaxBsStatsBsAirInterfaceDynamicEntry 4 }

		
		-- 1.3.6.1.4.1.989.1.16.2.6.3.6.1.5
		asMaxBsStatsIfUlPacketsPerSec OBJECT-TYPE
			SYNTAX Integer32
			MAX-ACCESS read-only
			STATUS current
			DESCRIPTION
				"The rate of uplink stream in packets, accumulated in by observation period."
			::= { asMaxBsStatsBsAirInterfaceDynamicEntry 5 }

		
		-- 1.3.6.1.4.1.989.1.16.2.6.3.6.1.6
		asMaxBsStatsIfDlBytesPerSec OBJECT-TYPE
			SYNTAX Integer32
			MAX-ACCESS read-only
			STATUS current
			DESCRIPTION
				"The rate of downlink stream in bytes, accumulated in by observation period."
			::= { asMaxBsStatsBsAirInterfaceDynamicEntry 6 }

		
		-- 1.3.6.1.4.1.989.1.16.2.6.3.6.1.7
		asMaxBsStatsIfDlPacketsPerSec OBJECT-TYPE
			SYNTAX Integer32
			MAX-ACCESS read-only
			STATUS current
			DESCRIPTION
				"The rate of downlink stream in packets, accumulated in by observation period."
			::= { asMaxBsStatsBsAirInterfaceDynamicEntry 7 }

		
	
	END

--
-- AIRSPAN-STATS-MIB.mib
--
