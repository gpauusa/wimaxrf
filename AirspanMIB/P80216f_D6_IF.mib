WMAN-IF-MIB DEFINITIONS ::= BEGIN
                                    
  IMPORTS
        MODULE-IDENTITY,
        OBJECT-TYPE,
        NOTIFICATION-TYPE,
        Unsigned32, Integer32, Counter32,
        Counter64, transmission
                FROM SNMPv2-SMI
        SnmpAdminString
                FROM SNMP-FRAMEWORK-MIB
        TEXTUAL-CONVENTION,
        MacAddress, RowStatus, TruthValue,
        TimeStamp, DateAndTime        
                FROM SNMPv2-TC
        InetAddressType, InetAddress
                FROM INET-ADDRESS-MIB
        OBJECT-GROUP,
        MODULE-COMPLIANCE,
        NOTIFICATION-GROUP
                FROM SNMPv2-CONF
        ifIndex
                FROM IF-MIB;

wmanIfMib MODULE-IDENTITY
        LAST-UPDATED    "200508020000Z" -- August 02, 2005
        ORGANIZATION    "IEEE 802.16"
        CONTACT-INFO
            "WG E-mail: stds-802-16@ieee.org
             WG Chair:  Roger B. Marks
             Postal:    IEEE
             E-mail:    r.b.marks@ieee.org
             
             TGf Chair: Phillip Barber
             Postal:    Broadband Mobile Technologies, Inc
             E-mail:    pbarber@broadbandmobiletech.com             

             Editor:    Joey Chou
             Postal:    Intel Corporation
                        5000 W. Chandler Blvd,
                        Chandler, AZ 85227, USA
             E-mail:    joey.chou@intel.com"                     
        DESCRIPTION
            "This material is from unapproved IEEE Standards Draft
             P802.16f/D6 Copyright (c) 2005 IEEE.
             This MIB Module defines managed objects for
             IEEE 802.16-2004 based Subscriber Station
             and Base Station."
        REVISION        "200508020000Z"
        DESCRIPTION
            "The latest version of WMAN-IF-MIB module."
        ::= { transmission 184 }

wmanIfMibObjects  OBJECT IDENTIFIER ::= { wmanIfMib 1 }
wmanIfBsObjects OBJECT IDENTIFIER ::= { wmanIfMibObjects 1 }
wmanIfSsObjects   OBJECT IDENTIFIER ::= { wmanIfMibObjects 2 }
wmanIfCommonObjects OBJECT IDENTIFIER ::= { wmanIfMibObjects 3 }

-- Textual Conventions
WmanIfSfSchedulingType ::= TEXTUAL-CONVENTION
        STATUS      current
        DESCRIPTION     
            "The scheduling service provided by a SC for an
             upstream service flow. If the parameter is omitted
             from an upstream QOS Parameter Set, this object takes
             the value of bestEffort (2). This parameter must be
             reported as undefined (1) for downstream QOS Parameter
             Sets."
        SYNTAX      INTEGER {undefined(1),
                             bestEffort(2),
                             nonRealTimePollingService(3),
                             realTimePollingService(4),
                             reserved(5),
                             unsolicitedGrantService(6)}
                                 
WmanIfPhsRuleVerify ::= TEXTUAL-CONVENTION
        STATUS      current
        DESCRIPTION
            "The value of this field indicates to the sending entity   
             whether or not the packet header contents are to be
             verified prior to performing suppression. If PHSV is
             enabled, the sender shall compare the bytes in the packet
             header with the bytes in the PHSF that are to be
             suppressed as indicated by the PHSM."
        REFERENCE
            "Subclause 11.13.19.3.7.5 in IEEE 802.16-2004"
        SYNTAX      INTEGER {phsVerifyEnable(0),
                             phsVerifyDisable(1)}
                             
WmanIfClassifierBitMap ::= TEXTUAL-CONVENTION
        STATUS      current
        DESCRIPTION     
            "A bit of of this object is set to 1 if the parameter
             indicated by the comment was present in the classifier
             encoding, and 0 otherwise.
             Note: that BITS are encoded most significant bit first,
             so that if e.g. bits 6 and 7 are set, this object is
             encoded as the octet string '030000'H."
        REFERENCE
            "Subclause 11.13.19.3.4 in IEEE 802.16-2004"
        SYNTAX      BITS {priority(0),
                          ipTos(1),
                          ipProtocol(2),
                          ipMaskedSrcAddr(3),
                          ipMaskedDestAddr(4),
                          srcPort(5),
                          destPort(6),
                          destMacAddr(7),
                          srcMacAddr(8),
                          ethernetProtocol(9),
                          userPriority(10),
                          vlanId(11),
                          ipv6FlowLabel(12)}
                                                       
WmanIfSfState ::= TEXTUAL-CONVENTION
        STATUS      current
        DESCRIPTION     
            "WmanIfSfState defines the state of a service flow."
        SYNTAX      INTEGER {authorized(1),
                             admitted(2),
                             active(3)}
                                     
WmanIfServClassName ::= TEXTUAL-CONVENTION
        STATUS      current
        DESCRIPTION     
            "WmanIfServClassName defines the type of service
             class name."
        SYNTAX      OCTET STRING (SIZE(2..128))

WmanIfCsSpecification ::= TEXTUAL-CONVENTION
        STATUS      current
        DESCRIPTION     
            "WmanIfCsSpecification defines the types of convergence
             sublayer."
        SYNTAX      INTEGER {noCs(0),
                             packetIpV4(1),
                             packetIpV6(2),
                             packet802dot3Ethernet(3),
                             packet802dot1QVlan(4),
                             packetIpV4Over802dot3(5),
                             packetIpV6Over802dot3(6),
                             packetIpV4Over802dot1Q(7),
                             packetIpV6Over802dot1Q(8),
                             atm(9)}

WmanIfMacVersion ::= TEXTUAL-CONVENTION
        STATUS      current
        DESCRIPTION
            "Version number of IEEE 802.16."                     
        SYNTAX      INTEGER {ieee802Dot16Of2001(1),
                             ieee802Dot16cOf2002(2),
                             ieee802Dot16aOf2003(3),
                             ieee802Dot16Of2004(4)}
                             
WmanIfCidType ::= TEXTUAL-CONVENTION
        STATUS      current
        DESCRIPTION
            "Type of CID."                     
        SYNTAX      INTEGER (0 .. 65535)

WmanIfDataEncryptAlgId ::= TEXTUAL-CONVENTION
        STATUS      current
        DESCRIPTION     
            "Data encryption algorithm identifiers."
        REFERENCE            
            "Table 375 in IEEE 802.16-2004"
        SYNTAX      INTEGER {none(0),
                             des56BitCbcMode(1),
                             aesCcmMode(2)}                                                                                               

WmanIfDataAuthAlgId ::= TEXTUAL-CONVENTION
        STATUS      current
        DESCRIPTION     
            "Data authentication algorithm identifiers."
        REFERENCE            
            "Table 376 in IEEE 802.16-2004"
        SYNTAX      INTEGER {noDataAuthentication(0),
                             reserved(1)}
            
WmanIfTekEncryptAlgId ::= TEXTUAL-CONVENTION
        STATUS      current
        DESCRIPTION     
            "TEK encryption algorithm identifiers."
        REFERENCE            
            "Table 377 in IEEE 802.16-2004"
        SYNTAX      INTEGER {tripleDes128BitKey(1),
                             rsa1024BitKey(2),
                             aes128BitKey(3)}

WmanIfChannelNumber ::= TEXTUAL-CONVENTION
        STATUS      current
        DESCRIPTION     
            "Physical channel number"
        SYNTAX      INTEGER (0 .. 199)

WmanIfOfdmFecCodeType ::= TEXTUAL-CONVENTION
        STATUS      current
        DESCRIPTION     
            "FEC code type and modulation type"
        REFERENCE            
            "Table 356 and Table 362 in IEEE 802.16-2004"
        SYNTAX      INTEGER {bpskCc1Over2(0),
                             qpskRsCcCc1Over2(1),
                             qpskRsCcCc3Over4(2),
                             sixteenQamRsCcCc1Over2(3),
                             sixteenQamRsCcCc3Over4(4),
                             sixtyFourQamRsCcCc2Over3(5),
                             sixtyFourQamRsCcCc3Over4(6),
                             qpskBtc1Over2(7),
                             qpskBtc3Over4(8),
                             sixteenQamBtc3Over4(9),
                             sixteenQamBtc4Over5(10),
                             sixtyFourQamBtc2Over3(11),
                             sixtyFourQamBtc5Over6(12),
                             qpskCtc1Over2(13),
                             qpskCtc2Over3(14),
                             qpskCtc3Over4(15),
                             sixteenQamCtc1Over2(16),
                             sixteenQamCtc3Over4(17),
                             sixtyFourQamCtc2Over3(18),
                             sixtyFourQamCtc3Over4(19)}

WmanIfOfdmaFecCodeType ::= TEXTUAL-CONVENTION
        STATUS      current
        DESCRIPTION     
            "FEC code type and modulation type"
        REFERENCE            
            "Table 356 and Table 362 in IEEE 802.16-2004"
        SYNTAX 	    INTEGER {qpskCc1Over2(0),
                             qpskCc3Over4(1),
                             sixteenQamCc1Over2(2),
                             sixteenQamCc3Over4(3),
                             sixtyFourQamCc2Over3(4),
                             sixtyFourQamCc3Over4(5),
                             qpskBtc1Over2(6),
                             qpskBtc2Over3(7),
                             sixteenQamBtc3Over5(8),
                             sixteenQamBtc4Over5(9),
                             sixtyFourQamBtc5Over8(10),
                             sixtyFourQamBtc4Over5(11),
                             qpskCtc1Over2(12),
                             qpskCtc2Over3(13),
                             qpskCtc3Over4(14),
                             sixteenQamCtc1Over2(15),
                             sixteenQamCtc3Over4(16),
                             sixtyFourQamCtc2Over3(17),
                             sixtyFourQamCtc3Over4(18),
                             sixtyFourQamCtc5Over6(19),
                             qpskZtCc1Over2(20),
                             qpskZtCc3Over4(21),
                             sixteenQamZtCc1Over2(22),
                             sixteenQamZtCc3Over4(23),
                             sixtyFourQamZtCc2Over3(24),
                             sixtyFourQamZtCc3Over4(25)}
 
-- Textual convention for capabilities encodings
WmanIfNumOfUplinkCid ::= TEXTUAL-CONVENTION
        STATUS      current
        DESCRIPTION
            "The object of this type shows the number of Uplink CIDs
             the SS can support."
        REFERENCE
            "Subclause 11.7.4 in IEEE 802.16-2004"
        SYNTAX      INTEGER (2..65535)
        
WmanIfArqSupportType ::= TEXTUAL-CONVENTION
        STATUS      current
        DESCRIPTION
            "The object of this type indicates whether the SS support
             ARQ."
        REFERENCE
            "Subclause 11.7.8.1 in IEEE 802.16-2004"
        SYNTAX      INTEGER {arqNotSupported(0),
                             arqSupported(1)} 
        
WmanIfMaxDsxFlowType ::= TEXTUAL-CONVENTION
        STATUS      current
        DESCRIPTION
            "The object of this type specifies the maximum number of
             concurrent DSA, DSC, or DSD transactions that may be
             outstanding."
        REFERENCE
            "Subclause 11.7.8.2 in IEEE 802.16-2004"
        SYNTAX      INTEGER (0..255) 
        
WmanIfMacCrcSupport ::= TEXTUAL-CONVENTION
        STATUS      current
        DESCRIPTION
            "The object of this type indicates whether or not the SS
             supports MAC level CRC."
        REFERENCE
            "Subclause 11.7.8.3 in IEEE 802.16-2004"
        SYNTAX      INTEGER {noMacCrcSupport(0),
                             macCrcSupport(1)} 
        
WmanIfMaxMcaFlowType ::= TEXTUAL-CONVENTION
        STATUS      current
        DESCRIPTION
            "The object of this type specifies the maximum number of
             concurrent MCA transactions that may be outstanding."
        REFERENCE
            "Subclause 11.7.8.4 in IEEE 802.16-2004"
        SYNTAX      INTEGER (0..255) 
        
WmanIfMaxMcpGroupCid ::= TEXTUAL-CONVENTION
        STATUS      current
        DESCRIPTION
            "The object of this type indicates the maximum number of
             simultaneous Multicast Polling Groups the SS is
             capable of belonging to."
        REFERENCE
            "Subclause 11.7.8.5 in IEEE 802.16-2004"
        SYNTAX      INTEGER (0..255) 
        
WmanIfMaxPkmFlowType ::= TEXTUAL-CONVENTION
        STATUS      current
        DESCRIPTION
            "The object of this type specifies the maximum number of
             concurrent PKM transactions that may be outstanding."
        REFERENCE
            "Subclause 11.7.8.6 in IEEE 802.16-2004"
        SYNTAX      INTEGER (0..255) 
        
WmanIfAuthPolicyType ::= TEXTUAL-CONVENTION
        STATUS      current
        DESCRIPTION
            "The object of this type specifies authorization policy
             that both SS and BS need to negotiate and synchronize.
             A bit value of 0 = not supported, 1 = supported. If this
             field is omitted, then both SS and BS shall use the IEEE
             802.16 security, constituting X.509 digital certificates
             and the RSA public key encryption algorithm, as
             authorization policy."
        REFERENCE
            "Subclause 11.7.8.7 in IEEE 802.16-2004"
        SYNTAX      BITS {ieee802Dot16PrivacySupported(0),
                          reserved1(1),
                          reserved2(2),
                          reserved3(3),
                          reserved4(4),
                          reserved5(5),
                          reserved6(6),
                          reserved7(7)} 
                
WmanIfMaxNumOfSaType ::= TEXTUAL-CONVENTION
        STATUS      current
        DESCRIPTION
            "This field specifies maximum number of supported
             security association of the SS."
        REFERENCE
            "Subclause 11.7.8.8 in IEEE 802.16-2004"
        SYNTAX      INTEGER (0..255) 
        
WmanIfIpVersionType ::= TEXTUAL-CONVENTION
        STATUS      current
        DESCRIPTION
            "The object of this type indicates the version of IP used
             on the Secondary Management Connection. The valus should
             be undefined if the 2nd management CID doesn't exist."
        REFERENCE
            "Subclause 11.7.4 in IEEE 802.16-2004"
        SYNTAX      INTEGER {undefined(0),
                             ipv4(1),
                             ipv6(2)} 

WmanIfMacCsBitMap ::= TEXTUAL-CONVENTION
        STATUS      current
        DESCRIPTION
            "The object of this type indicates the set of MAC
             convergence sublayer support. When a bit is set, it
             indicates the corresponding CS feature is supported."
        REFERENCE
            "Subclause 11.7.7.1 in IEEE 802.16-2004"
        SYNTAX      BITS {atm(0),
                          packetIpv4(1),
                          packetIpv6(2),
                          packet802Dot3(3),
                          packet802Dot1Q(4),
                          packetIpv4Over802Dot3(5),
                          packetIpv6Over802Dot3(6),
                          packetIpv4Over802Dot1Q(7),
                          packetIpv6Over802Dot1Q(8)}
                                                                                
WmanIfMaxClassifiers ::= TEXTUAL-CONVENTION
        STATUS      current
        DESCRIPTION
            "The object of this type indicates the maximum number of
             admitted Classifiers that the SS is allowed to have."
        REFERENCE
            "Subclause 11.7.7.2 in IEEE 802.16-2004"
        SYNTAX      INTEGER (0..65535)
                                                                                
WmanIfPhsSupportType ::= TEXTUAL-CONVENTION
        STATUS      current
        DESCRIPTION
            "The object of this type indicates indicates the level
             of PHS support."
        REFERENCE
            "Subclause 11.7.7.3 in IEEE 802.16-2004"
        SYNTAX      INTEGER {noPhsSupport(0),
                             atmPhsSupport(1),
                             packetPhsSupport(2)} 

WmanIfBwAllocSupport ::= TEXTUAL-CONVENTION
        STATUS      current
        DESCRIPTION
            "This field indicates properties of the SS that the BS
             needs to know for bandwidth allocation purposes. When
             a bit is set, it indicates the corresponding feature
             is supported. All unspecified and reserved bits should
             be set to zero."
        REFERENCE
            "Subclause 11.8.1 in IEEE 802.16-2004"
        SYNTAX      BITS {reserved(0),
                          halfDuplexFdd(1),
                          fullDuplexFdd(2)}

WmanIfPduConstruction ::= TEXTUAL-CONVENTION
        STATUS      current
        DESCRIPTION
            "Specifies capabilities for construction and transmission
             of MAC PDUs. When piggybackedRequests bit is set, it
             indicates that the piggybacked requests are supported. The
             fsnValuesSize bit is coded as follows:
               0 - only 3-bit FSN values are supported
               1 - only 11-bit FSN values are supported
             All unspecified and reserved bits should be set to zero."
        REFERENCE
            "Subclause 11.8.2 in IEEE 802.16-2004"
        SYNTAX      BITS {piggybackedRequests(0),
                          fsnValuesSize(1)}

WmanIfSsTransitionGap ::= TEXTUAL-CONVENTION
        STATUS      current
        DESCRIPTION
            "This field indicates the transition speed SSTTG and SSRTG
             for TDD and H-FDD SSs. Allowed values are:
               OFDM mode: TDD and H-FDD 0..100
               Other modes: TDD: 0..50; H-FDD: 0..100"
        REFERENCE
            "Subclause 11.8.3.1 in IEEE 802.16-2004"
        SYNTAX      INTEGER (0..100)

WmanIfMaxTxPowerType ::= TEXTUAL-CONVENTION
        STATUS      current
        DESCRIPTION
            "This type is used to define maximum available power for 
             BPSK, QPSK, 16-QAM and 64-QAM constellations. The maximum
             power parameters are reported in dBm and quantized in 0.5
             dBm steps ranging from -64 dBm (encoded 0x00) to 63.5 dBm 
             (encoded 0xFF). Values outside this range shall be
             assigned the closest extreme. SSs that do not support
             QAM64 shall report the value of 0x00 in the maximum QAM64
             power field."
        REFERENCE
            "Subclause 11.8.3.2 in IEEE 802.16-2004"
        SYNTAX      INTEGER (0..255)

WmanIfOfdmFftSizes ::= TEXTUAL-CONVENTION
        STATUS      current
        DESCRIPTION
            "This field indicates the FFT sizes supported by the SS. 
             For each FFT size, a bit value of 0 indicates
             'not supported' while 1 indicates 'supported'."
        REFERENCE
            "Subclause 11.8.3.6.1 in IEEE 802.16-2004"
        SYNTAX      BITS {fft256(0),
                          fft2048(1)}

WmanIfOfdmSsDeModType ::= TEXTUAL-CONVENTION
        STATUS      current
        DESCRIPTION
            "This field indicates the different demodulator options
             supported by a WirelessMAN-OFDM PHY SS for downlink. This
             field is not used for other PHY specifications. A bit
             value of 0 indicates 'not supported' while 1 indicates
             'supported'."
        REFERENCE
            "Subclause 11.8.3.6.2 in IEEE 802.16-2004"
        SYNTAX      BITS {qam64(0),
                          btc(1),
                          ctc(2),
                          stc(3),
                          aac(4)}

WmanIfOfdmSsModType ::= TEXTUAL-CONVENTION
        STATUS      current
        DESCRIPTION
            "This field indicates the different modulator options
             supported by a WirelessMAN-OFDM PHY SS for uplink. This
             field is not used for other PHY specifications. A bit
             value of 0 indicates 'not supported' while 1 indicates
             'supported'."
        REFERENCE
            "Subclause 11.8.3.6.3 in IEEE 802.16-2004"
        SYNTAX      BITS {qam64(0),
                          btc(1),
                          ctc(2),
                          subchanellization(3),
                          focusedCtBwReq(4)}

WmanIfOfdmFocusedCt ::= TEXTUAL-CONVENTION
        STATUS      current
        DESCRIPTION
            "This field indicates whether the SS supports Focused
             Contention (see 8.3.7.3.3). A bit value of 0 indicates
             'not supported' while 1 indicates 'supported'."
        REFERENCE
            "Subclause 11.8.3.6.4 in IEEE 802.16-2004"
        SYNTAX      BITS {focusedCtSupport(0)}

WmanIfOfdmTcSublayer ::= TEXTUAL-CONVENTION
        STATUS      current
        DESCRIPTION
            "This field indicates whether or not the SS supports the
             TC sublayer (see 8.3.4). A bit value of 0 indicates
             'not supported' while 1 indicates 'supported'."
        REFERENCE
            "Subclause 11.8.3.6.5 in IEEE 802.16-2004"
        SYNTAX      BITS {tcSublayerSupport(0)}

WmanIfBsIdType ::= TEXTUAL-CONVENTION
        STATUS      current
        DESCRIPTION     
            "Defines the encoding of BSID. The BSID is a 6 byte number
             and follows the encoding rules of MacAddress textual
             convention, i.e. as if it were transmitted
             least-significant bit first. The value should be displayed
             with 2 parts clearly separated by a colon e.g:
             001DFF:00003A. The most significant part is representing
             the Operator ID. "
        SYNTAX      OCTET STRING (SIZE(6))

WmanIfIpv6FlowLabel ::= TEXTUAL-CONVENTION
        STATUS      current
        DESCRIPTION     
            "The value of this field specifies the matching values for
             the IPv6 Flow label field. As the flow label field has a
             length of 20 bits, the first 4 bits of the most
             significant byte shall be set to 0x0 and disregarded."
        SYNTAX      OCTET STRING (SIZE(3))
                
--
-- BS object group – containing tables and objects to be implemented in 
-- the Base station        
--
-- wmanIfBsPacketCs contain the Base Station Packet Convergence
-- Sublayer objects
--
wmanIfBsPacketCs OBJECT IDENTIFIER ::= { wmanIfBsObjects 1 }

wmanIfBsProvisionedSfTable OBJECT-TYPE
        SYNTAX      SEQUENCE OF WmanIfBsProvisionedSfEntry
        MAX-ACCESS  not-accessible
        STATUS      current
        DESCRIPTION
            "This table contains service flow profiles provisioned by
             NMS. The service flow should be created with SS(s)
             following instruction given by wmanIfBsSfState object.
             1. The QoS parameters of the service flow are provisioned 
                in wmanIfBsServiceClassTable and referenced by
                wmanIfBsServiceClassIndex.
             2. The classifier rules of the service flow are provisioned
                in wmanIfBsClassifierRuleTable, where they refer to SF
                via wmanIfBsSfId.
             
             The MAC addresses of SSs the service flow is created with
             are provisioned in wmanIfBsSsProvisionedForSfTable, where
             they refer to SF via wmanIfBsSfId."
        REFERENCE            
            "Subclause 6.3.13 and 6.3.14 in IEEE 802.16-2004"
        ::= { wmanIfBsPacketCs 1 }

wmanIfBsProvisionedSfEntry OBJECT-TYPE
        SYNTAX      WmanIfBsProvisionedSfEntry
        MAX-ACCESS  not-accessible
        STATUS      current
        DESCRIPTION
            "This table provides one row for each service flow
             provisioned by NMS. The table is indexed by
             wmanIfBsSfId."
        INDEX { ifIndex, wmanIfBsSfId }
        ::= { wmanIfBsProvisionedSfTable 1 }

WmanIfBsProvisionedSfEntry ::= SEQUENCE {
        wmanIfBsSfId                            Unsigned32,
        wmanIfBsSfDirection                     INTEGER,
        wmanIfBsServiceClassIndex               INTEGER,
        wmanIfBsSfState                         WmanIfSfState,
        wmanIfBsSfProvisionedTime               TimeStamp,
        wmanIfBsSfCsSpecification               WmanIfCsSpecification,
        wmanIfBsProvisionedSfRowStatus          RowStatus}

wmanIfBsSfId OBJECT-TYPE
        SYNTAX      Unsigned32 (1 .. 4294967295)
        MAX-ACCESS  not-accessible
        STATUS      current
        DESCRIPTION
            "A 32 bit quantity that uniquely identifies a service flow
             to both the subscriber station and base station (BS)."
        ::= { wmanIfBsProvisionedSfEntry 1 }
                
wmanIfBsSfDirection OBJECT-TYPE
        SYNTAX      INTEGER {downstream(1),
                             upstream(2)}
        MAX-ACCESS  read-create
        STATUS      current
        DESCRIPTION
            "An attribute indicating the service flow is downstream or
             upstream."
        ::= { wmanIfBsProvisionedSfEntry 2 }                        
        
wmanIfBsServiceClassIndex OBJECT-TYPE
        SYNTAX      INTEGER (1..65535)
        MAX-ACCESS  read-create
        STATUS      current
        DESCRIPTION
            "The index in wmanIfBsServiceClassTable describing the
             service class or QoS parameters for such service flow.
             If no associated entry in wmanIfBsServiceClassTable
             exists, this object returns a value of zero."
        ::= { wmanIfBsProvisionedSfEntry 3 }
                
wmanIfBsSfState OBJECT-TYPE
        SYNTAX      WmanIfSfState
        MAX-ACCESS  read-create
        STATUS      current
        DESCRIPTION
            "wmanIfBsSfState determines the requested state of a service
             flow. 
             - authorized state: A service flow is provisioned but
               not resource is reserved yet
             - admitted state: service flow has resources reserved.
             - active state: has resources committed by the BS (e.g., is
               actively sending maps containing unsolicited grants for a
               UGS-based service flow),"
        REFERENCE
            "Subclause 6.3.14.6, in IEEE 802.16-2004"
        ::= { wmanIfBsProvisionedSfEntry 4 }                
        
wmanIfBsSfProvisionedTime OBJECT-TYPE
        SYNTAX      TimeStamp
        MAX-ACCESS  read-create
        STATUS      current
        DESCRIPTION
            "Indicates the date and time when the service flow is
             provisioned."
        ::= { wmanIfBsProvisionedSfEntry 5 }

wmanIfBsSfCsSpecification OBJECT-TYPE
        SYNTAX      WmanIfCsSpecification
        MAX-ACCESS  read-create
        STATUS      current
        DESCRIPTION
            "This parameter specifies the convergence sublayer
             encapsulation mode."
        REFERENCE
            "Subclause 11.13.19.1 in IEEE 802.16-2004"             
        ::= { wmanIfBsProvisionedSfEntry 6 }
        
wmanIfBsProvisionedSfRowStatus OBJECT-TYPE
        SYNTAX          RowStatus
        MAX-ACCESS      read-create
        STATUS          current
        DESCRIPTION
            "This object is used to create a new row or modify or
             delete an existing row in this table.

             If the implementator of this MIB has choosen not
             to implement 'dynamic assignment' of profiles, this
             object is not useful and should return noSuchName
             upon SNMP request."
        ::= { wmanIfBsProvisionedSfEntry 7 }

wmanIfBsSsProvisionedForSfTable OBJECT-TYPE
        SYNTAX      SEQUENCE OF WmanIfBsSsProvisionedForSfEntry
        MAX-ACCESS  not-accessible
        STATUS      current
        DESCRIPTION
            "This table maps the MAC addresses of SSs to the service
             flows provisioned in wmanIfBsProvisionedSfTable."
        REFERENCE            
            "Subclause 6.3.14 in IEEE 802.16-2004"
        ::= { wmanIfBsPacketCs 2 }

wmanIfBsSsProvisionedForSfEntry OBJECT-TYPE
        SYNTAX      WmanIfBsSsProvisionedForSfEntry
        MAX-ACCESS  not-accessible
        STATUS      current
        DESCRIPTION
            "This table is indexed by wmanIfBsSsProvMacAddress and
             wmanIfBsProvSfId."
        INDEX { wmanIfBsSsProvMacAddress, wmanIfBsProvSfId }
        ::= { wmanIfBsSsProvisionedForSfTable 1 }

WmanIfBsSsProvisionedForSfEntry ::= SEQUENCE {
        wmanIfBsSsProvMacAddress                MacAddress,
        wmanIfBsProvSfId                        Unsigned32,
        wmanIfBsSsProvisionedForSfRowStatus     RowStatus}
        
wmanIfBsSsProvMacAddress OBJECT-TYPE
        SYNTAX      MacAddress
        MAX-ACCESS  not-accessible
        STATUS      current
        DESCRIPTION
            "The MAC address of the SS, the service flow is created
             with."
        ::= { wmanIfBsSsProvisionedForSfEntry 1 }
        
wmanIfBsProvSfId OBJECT-TYPE
        SYNTAX      Unsigned32 (1 .. 4294967295)
        MAX-ACCESS  not-accessible
        STATUS      current
        DESCRIPTION
            "A 32 bit quantity that uniquely identifies a service flow.
             The value of this object can be used by BS to index the
             wmanBsProvisionedSfTable."
        ::= { wmanIfBsSsProvisionedForSfEntry 2 }

wmanIfBsSsProvisionedForSfRowStatus OBJECT-TYPE
        SYNTAX          RowStatus
        MAX-ACCESS      read-create
        STATUS          current
        DESCRIPTION
            "This object is used to ensure that the write, create,
             delete operation to multiple columns is guaranteed to
             be treated as atomic operation by agent."
        ::= { wmanIfBsSsProvisionedForSfEntry 3 }
                                                                
wmanIfBsServiceClassTable OBJECT-TYPE
        SYNTAX      SEQUENCE OF WmanIfBsServiceClassEntry
        MAX-ACCESS  not-accessible
        STATUS      current
        DESCRIPTION
            "This table is provisioned and is indexed by
             wmanIfBsQoSProfileIndex. Each entry of the table contains
             corresponding service flow characteristic attributes
             (e.g. QoS parameter set). The value of
             wmanIfBsQoSProfileIndex is obtained from 
             wmanIfBsServiceClassIndex in wmanIfBsProvisionedSfTable"
        REFERENCE
            "Subclause 6.3.14.4 in IEEE 802.16-2004"    
        ::= { wmanIfBsPacketCs 3 }

wmanIfBsServiceClassEntry OBJECT-TYPE
        SYNTAX      WmanIfBsServiceClassEntry
        MAX-ACCESS  not-accessible
        STATUS      current
        DESCRIPTION
            "This table provides one row for each service class"
        INDEX { ifIndex, wmanIfBsQoSProfileIndex }
        ::= { wmanIfBsServiceClassTable 1 }

WmanIfBsServiceClassEntry ::= SEQUENCE {
        wmanIfBsQoSProfileIndex                 INTEGER,
        wmanIfBsQosServiceClassName             WmanIfServClassName,
        wmanIfBsQoSTrafficPriority              INTEGER,
        wmanIfBsQoSMaxSustainedRate             Unsigned32,
        wmanIfBsQoSMaxTrafficBurst              Unsigned32,
        wmanIfBsQoSMinReservedRate              Unsigned32,
        wmanIfBsQoSToleratedJitter              Unsigned32,
        wmanIfBsQoSMaxLatency                   Unsigned32,
        wmanIfBsQoSFixedVsVariableSduInd        INTEGER,            
        wmanIfBsQoSSduSize                      Unsigned32,
        wmanIfBsQosScSchedulingType             WmanIfSfSchedulingType,
        wmanIfBsQosScArqEnable                  TruthValue,
        wmanIfBsQosScArqWindowSize              INTEGER,
        wmanIfBsQosScArqBlockLifetime           INTEGER,
        wmanIfBsQosScArqSyncLossTimeout         INTEGER,
        wmanIfBsQosScArqDeliverInOrder          TruthValue,
        wmanIfBsQosScArqRxPurgeTimeout          INTEGER,
        wmanIfBsQosScArqBlockSize               INTEGER,
        wmanIfBsQosSCMinRsvdTolerableRate       Unsigned32,
        wmanIfBsQoSReqTxPolicy                  BITS,
        wmanIfBsQoSServiceClassRowStatus        RowStatus}
        
wmanIfBsQoSProfileIndex OBJECT-TYPE
        SYNTAX      INTEGER (1 .. 65535)
        MAX-ACCESS  not-accessible
        STATUS      current
        DESCRIPTION
            "The index value which uniquely identifies an entry
             in the wmanIfBsServiceClassTable"
        ::= { wmanIfBsServiceClassEntry 1 }
        
wmanIfBsQosServiceClassName  OBJECT-TYPE
        SYNTAX      WmanIfServClassName
        MAX-ACCESS  read-create
        STATUS      current
        DESCRIPTION    
            "Refers to the Service Class Name"
        REFERENCE
            "Subclause 11.13.3 in IEEE 802.16-2004"
        ::= { wmanIfBsServiceClassEntry 2 }
            
wmanIfBsQoSTrafficPriority OBJECT-TYPE
        SYNTAX      INTEGER (0..7)
        MAX-ACCESS  read-create
        STATUS      current
        DESCRIPTION
            "The value of this parameter specifies the priority
             assigned to a service flow. For uplink service flows,
             the BS should use this parameter when determining
             precedence in request service and grant generation,
             and the SS shall preferentially select contention
             Request opportunities for Priority Request CIDs
             based on this priority. Higher numbers indicate higher
             priority"
        REFERENCE
            "Subclause 11.13.5 in IEEE 802.16-2004"
        ::= { wmanIfBsServiceClassEntry 3 }
        
wmanIfBsQoSMaxSustainedRate OBJECT-TYPE
        SYNTAX      Unsigned32
        UNITS       "b/s"
        MAX-ACCESS  read-create
        STATUS      current
        DESCRIPTION
            "This parameter defines the peak information rate
             of the service. The rate is expressed in bits per
             second and pertains to the SDUs at the input to
             the system."
        REFERENCE
            "Subclause 11.13.6 in IEEE 802.16-2004"
        ::= { wmanIfBsServiceClassEntry 4 }        
                
wmanIfBsQoSMaxTrafficBurst OBJECT-TYPE
        SYNTAX      Unsigned32
        UNITS       "byte"
        MAX-ACCESS  read-create
        STATUS      current
        DESCRIPTION
            "This parameter defines the maximum burst size that
             must be accommodated for the service."
        REFERENCE
            "Subclause 11.13.7 in IEEE 802.16-2004"
        ::= { wmanIfBsServiceClassEntry 5 }
                        
wmanIfBsQoSMinReservedRate OBJECT-TYPE
        SYNTAX      Unsigned32
        UNITS       "b/s"
        MAX-ACCESS  read-create
        STATUS      current
        DESCRIPTION
            "This parameter specifies the minimum rate reserved
             for this service flow."
        REFERENCE
            "Subclause 11.13.8 in IEEE 802.16-2004"
        ::= { wmanIfBsServiceClassEntry 6 }
                                
wmanIfBsQoSToleratedJitter OBJECT-TYPE
        SYNTAX      Unsigned32
        UNITS       "millisecond"
        MAX-ACCESS  read-create
        STATUS      current
        DESCRIPTION
            "This parameter defines the Maximum delay 
             variation (jitter) for the connection."
        REFERENCE
            "Subclause 11.13.13 in IEEE 802.16-2004"
        ::= { wmanIfBsServiceClassEntry 7 }
                                
wmanIfBsQoSMaxLatency OBJECT-TYPE
        SYNTAX      Unsigned32
        UNITS       "millisecond"
        MAX-ACCESS  read-create
        STATUS      current
        DESCRIPTION
            "The value of this parameter specifies the maximum
             latency between the reception of a packet by the BS
             or SS on its network interface and the forwarding
             of the packet to its RF Interface."
        REFERENCE
            "Subclause 11.13.14 in IEEE 802.16-2004"
        ::= { wmanIfBsServiceClassEntry 8 }

wmanIfBsQoSFixedVsVariableSduInd OBJECT-TYPE
        SYNTAX      INTEGER {variableLength(0),
                             fixedLength(1)}
        MAX-ACCESS  read-create
        STATUS      current
        DESCRIPTION
            "The value of this parameter specifies whether the SDUs
             on the service flow are variable-length (0) or 
             fixed-length (1). The parameter is used only if
             packing is on for the service flow. The default value
             is 0, i.e.,variable-length SDUs."
        REFERENCE
            "Subclause 11.13.15 in IEEE 802.16-2004"
        DEFVAL      { variableLength }
        ::= { wmanIfBsServiceClassEntry 9 }

wmanIfBsQoSSduSize OBJECT-TYPE
        SYNTAX      Unsigned32
        UNITS       "byte"
        MAX-ACCESS  read-create
        STATUS      current
        DESCRIPTION
            "The value of this parameter specifies the length of the
             SDU for a fixed-length SDU service flow. This parameter
             is used only if packing is on and the service flow is
             indicated as carrying fixed-length SDUs. The default
             value is 49 bytes, i.e., VC-switched ATM cells with PHS.
             The parameter is relevant for both ATM and Packet
             Convergence Sublayers."
        REFERENCE
            "Subclause 11.13.16 in IEEE 802.16-2004"
        DEFVAL      { 49 }
        ::= { wmanIfBsServiceClassEntry 10 }
                
wmanIfBsQosScSchedulingType OBJECT-TYPE
        SYNTAX      WmanIfSfSchedulingType
        MAX-ACCESS  read-create
        STATUS      current
        DESCRIPTION
            "Specifies the upstream scheduling service used for
             upstream service flow. If the referenced parameter
             is not present in the corresponding 802.16 QOS
             Parameter Set of an upstream service flow, the
             default value of this object is bestEffort(2)."
        REFERENCE      
            "Subclause 11.13.11 in IEEE 802.16-2004"
        DEFVAL	    {bestEffort}
        ::= { wmanIfBsServiceClassEntry 11 }

wmanIfBsQosScArqEnable OBJECT-TYPE
        SYNTAX      TruthValue
        MAX-ACCESS  read-create
        STATUS      current
        DESCRIPTION
            "True(1) ARQ enabling is requested for the connection."
        REFERENCE
            "Subclause 11.13.18 in IEEE 802.16-2004"
        ::= { wmanIfBsServiceClassEntry 12 }

wmanIfBsQosScArqWindowSize	 OBJECT-TYPE
        SYNTAX      INTEGER (1 .. 1024)
        MAX-ACCESS  read-create
        STATUS      current
        DESCRIPTION
            "Indicates the maximum number of unacknowledged 
             fragments at any time."
        REFERENCE
            "Subclause 11.13.18 in IEEE 802.16-2004"
        ::= { wmanIfBsServiceClassEntry 13 }

wmanIfBsQosScArqBlockLifetime OBJECT-TYPE
        SYNTAX	    INTEGER (0 .. 65535)
        UNITS	    "10 us"
        MAX-ACCESS  read-create
        STATUS      current
        DESCRIPTION
            "The maximum time interval an ARQ fragment will be
             managed by the transmitter ARQ machine, once
             initial transmission of the fragment has occured.
             If transmission or retransmission of the fragment
             is not acknowledged by the receiver before the 
             time limit is reached, the fragment is discarded.
             A value of 0 means Infinite."
        REFERENCE
            "Subclause 11.13.18 in IEEE 802.16-2004"
        DEFVAL		{0}
        ::= { wmanIfBsServiceClassEntry 14 }

wmanIfBsQosScArqSyncLossTimeout OBJECT-TYPE
        SYNTAX      INTEGER (0 .. 65535 )
        UNITS       "10 us"
        MAX-ACCESS  read-create
        STATUS      current
        DESCRIPTION
            "The maximum interval before declaring a loss
             of synchronization of the sender and receiver
             state machines. A value of 0 means Infinite."
        REFERENCE
            "Subclause 11.13.18 in IEEE 802.16-2004"
        DEFVAL	    {0}
        ::= { wmanIfBsServiceClassEntry 15 }

wmanIfBsQosScArqDeliverInOrder  OBJECT-TYPE
        SYNTAX      TruthValue
        MAX-ACCESS  read-create
        STATUS      current
        DESCRIPTION
            "Indicates whether or not data is to be delivered
             by the receiving MAC to its client application
             in the order in which data was handed off to the
             originating MAC."
        REFERENCE
            "Subclause 11.13.18 in IEEE 802.16-2004"
        ::= { wmanIfBsServiceClassEntry 16 }

wmanIfBsQosScArqRxPurgeTimeout  OBJECT-TYPE
        SYNTAX      INTEGER (0 .. 65535)
        UNITS       "10 us"
        MAX-ACCESS  read-create
        STATUS      current
        DESCRIPTION
            "Indicates the time interval the ARQ window is advanced
             after a fragment is received. A value of 0 means
             Infinite."
        REFERENCE
            "Subclause 11.13.18 in IEEE 802.16-2004"
        DEFVAL	    {0}
        ::= { wmanIfBsServiceClassEntry 17 }

wmanIfBsQosScArqBlockSize OBJECT-TYPE
        SYNTAX      INTEGER (1..2040)
        UNITS       "byte"
        MAX-ACCESS  read-create
        STATUS      current
        DESCRIPTION
            "The value of this parameter specifies the size of an
             ARQ block. This parameter shall be established by
             negotiation during the connection creation dialog."
        REFERENCE
            "Subclause 11.13.18.8 in IEEE 802.16-2004"             
        ::= { wmanIfBsServiceClassEntry 18 } 

wmanIfBsQosSCMinRsvdTolerableRate OBJECT-TYPE
        SYNTAX      Unsigned32
        UNITS       "b/s"
        MAX-ACCESS  read-create
        STATUS      current
        DESCRIPTION
            "Minimum Tolerable Traffic Rate = R (bits/sec) with
             time base T(sec) means the following. Let S denote
             additional demand accumulated at the MAC SAP of the
             transmitter during an arbitrary time interval of the
             length T. Then the amount of data forwarded at the
             receiver to CS (in bits) during this interval should
             be not less than min {S, R * T}."
        REFERENCE
            "Subclause 11.13.9 in IEEE 802.16-2004"
        ::= { wmanIfBsServiceClassEntry 19 }
        
wmanIfBsQoSReqTxPolicy OBJECT-TYPE
        SYNTAX      BITS {noBroadcastBwReq(0),
                          reserved1(1),
                          noPiggybackReq(2),
                          noFragmentData(3),
                          noPHS(4),
                          noSduPacking(5),
                          noCrc(6),
                          reserved2(7)} 
        MAX-ACCESS  read-create
        STATUS      current
        DESCRIPTION
            "The value of this parameter provides the capability to
             specify certain attributes for the associated service
             flow. An attribute is enabled by setting the
             corresponding bit position to 1."
        REFERENCE   "Subclause 11.13.12 in IEEE 802.16-2004"
        ::= { wmanIfBsServiceClassEntry 20 }
            
wmanIfBsQoSServiceClassRowStatus OBJECT-TYPE
        SYNTAX      RowStatus
        MAX-ACCESS  read-create
        STATUS      current
        DESCRIPTION
            "This object is used to create a new row or modify or
             delete an existing row in this table.

             If the implementator of this MIB has choosen not
             to implement 'dynamic assignment' of profiles, this
             object is not useful and should return noSuchName
             upon SNMP request."
        ::= { wmanIfBsServiceClassEntry 21 }
        
wmanIfBsClassifierRuleTable OBJECT-TYPE
        SYNTAX      SEQUENCE OF WmanIfBsClassifierRuleEntry
        MAX-ACCESS  not-accessible
        STATUS      current
        DESCRIPTION
            "This table contains packet classifier rules associated
             with service flows."
        REFERENCE
            "Subclause 11.13.19.3.4 in IEEE 802.16-2004"        
        ::= { wmanIfBsPacketCs 4 }

wmanIfBsClassifierRuleEntry OBJECT-TYPE
        SYNTAX      WmanIfBsClassifierRuleEntry
        MAX-ACCESS  not-accessible
        STATUS      current
        DESCRIPTION 
           "This table provides one row for each packet classifier 
            rule, and is indexed by wmanIfBsSfId and
            wmanIfBsClassifierRuleIndex. wmanIfBsSfId identifies
            the service flow, while wmanIfBsClassifierRuleIndex
            identifies the packet classifier rule."
        INDEX { ifIndex, wmanIfBsSfId, wmanIfBsClassifierRuleIndex }
        ::= { wmanIfBsClassifierRuleTable 1 }

WmanIfBsClassifierRuleEntry::= SEQUENCE {
        wmanIfBsClassifierRuleIndex             Unsigned32,
        wmanIfBsClassifierRulePriority          INTEGER,
        wmanIfBsClassifierRuleIpTosLow          INTEGER,
        wmanIfBsClassifierRuleIpTosHigh         INTEGER,
        wmanIfBsClassifierRuleIpTosMask         INTEGER,
        wmanIfBsClassifierRuleIpProtocol        Integer32,
        wmanIfBsClassifierRuleIpSourceAddr      InetAddress,
        wmanIfBsClassifierRuleIpSourceMask      InetAddress,
        wmanIfBsClassifierRuleIpDestAddr        InetAddress,
        wmanIfBsClassifierRuleIpDestMask        InetAddress,
        wmanIfBsClassifierRuleSourcePortStart   Integer32,
        wmanIfBsClassifierRuleSourcePortEnd     Integer32,
        wmanIfBsClassifierRuleDestPortStart     Integer32,
        wmanIfBsClassifierRuleDestPortEnd       Integer32,
        wmanIfBsClassifierRuleDestMacAddr       MacAddress,
        wmanIfBsClassifierRuleDestMacMask       MacAddress,
        wmanIfBsClassifierRuleSourceMacAddr     MacAddress,
        wmanIfBsClassifierRuleSourceMacMask     MacAddress,
        wmanIfBsClassifierRuleEnetProtocolType  INTEGER,
        wmanIfBsClassifierRuleEnetProtocol      Integer32,
        wmanIfBsClassifierRuleUserPriLow        Integer32,
        wmanIfBsClassifierRuleUserPriHigh       Integer32,
        wmanIfBsClassifierRuleVlanId            Integer32,
        wmanIfBsClassifierRuleState             INTEGER,
        wmanIfBsClassifierRulePhsSize           Integer32,
        wmanIfBsClassifierRulePhsMask           OCTET STRING,
        wmanIfBsClassifierRulePhsVerify         WmanIfPhsRuleVerify,
        wmanIfBsClassifierRuleIpv6FlowLabel     WmanIfIpv6FlowLabel,
        wmanIfBsClassifierRuleBitMap            WmanIfClassifierBitMap,
        wmanIfBsClassifierRuleRowStatus         RowStatus}
       
wmanIfBsClassifierRuleIndex  OBJECT-TYPE
        SYNTAX      Unsigned32 (1..4294967295)
        MAX-ACCESS  not-accessible
        STATUS      current
        DESCRIPTION 
            "An index is assigned to a classifier in BS classifiers
             table"
        ::= { wmanIfBsClassifierRuleEntry 1 }

wmanIfBsClassifierRulePriority OBJECT-TYPE
        SYNTAX      INTEGER (0..255)
        MAX-ACCESS  read-create
        STATUS      current
        DESCRIPTION
            "The value specifies the priority for the Classifier, which
             is used for determining the order of the Classifier. A
             higher value indicates higher priority. Classifiers may
             have priorities in the range 0..255."
        REFERENCE
            "Subclause 11.13.19.3.4.1 in IEEE 802.16-2004"
        DEFVAL      { 0 }
        ::= { wmanIfBsClassifierRuleEntry 2 }

wmanIfBsClassifierRuleIpTosLow OBJECT-TYPE
        SYNTAX      INTEGER (0..255)
        MAX-ACCESS  read-create
        STATUS      current
        DESCRIPTION
            "The low value of a range of TOS byte values. If the
            referenced parameter is not present in a classifier, this
            object reports the value of 0."
        REFERENCE
            "Subclause 11.13.19.3.4.2 in IEEE 802.16-2004"
        ::= { wmanIfBsClassifierRuleEntry 3 }

wmanIfBsClassifierRuleIpTosHigh OBJECT-TYPE
        SYNTAX      INTEGER (0..255)
        MAX-ACCESS  read-create
        STATUS      current
        DESCRIPTION
            "The 8-bit high value of a range of TOS byte values.
             If the referenced parameter is not present in a classifier,
             this object reports the value of 0."
        REFERENCE
            "Subclause 11.13.19.3.4.2 in IEEE 802.16-2004"
        ::= { wmanIfBsClassifierRuleEntry 4 }

wmanIfBsClassifierRuleIpTosMask OBJECT-TYPE
        SYNTAX      INTEGER (0..255)
        MAX-ACCESS  read-create
        STATUS      current
        DESCRIPTION
            "The value of this object specifies the matching parameter
             for the IP type of service/DSCP [IETF RFC 2474] byte mask.
             An IP packet with IP type of service (ToS) byte value
             ip-tos matches this parameter if tos-low less than or
             equal (ip-tos AND tos-mask) less than or equal tos-high."
        REFERENCE
            "Subclause 11.13.19.3.4.2 in IEEE 802.16-2004"
        ::= { wmanIfBsClassifierRuleEntry 5 }

wmanIfBsClassifierRuleIpProtocol OBJECT-TYPE
        SYNTAX      Integer32 (0..255)
        MAX-ACCESS  read-create
        STATUS      current
        DESCRIPTION
            "This object indicates the value of the IP Protocol field
             required for IP packets to match this rule. If the
             referenced parameter is not present in a classifier, this
             object reports the value of 0."
        REFERENCE
            "Subclause 11.13.19.3.4.3 in IEEE 802.16-2004"
        ::= { wmanIfBsClassifierRuleEntry 6 }

wmanIfBsClassifierRuleIpSourceAddr OBJECT-TYPE
        SYNTAX      InetAddress
        MAX-ACCESS  read-create
        STATUS      current
        DESCRIPTION
            "This object specifies the value of the IP Source Address
             required for packets to match this rule. An IP packet
             matches the rule when the packet ip source address bitwise
             ANDed with the wmanIfBsClassifierRuleIpSourceMask value
             equals the wmanIfBsClassifierRuleIpSourceAddr value.
             If the referenced parameter is not present in a classifier,
             this object reports the value of 0.0.0.0."
        REFERENCE
            "Subclause 11.13.19.3.4.4 in IEEE 802.16-2004"
        ::= { wmanIfBsClassifierRuleEntry 7 }

wmanIfBsClassifierRuleIpSourceMask OBJECT-TYPE
        SYNTAX      InetAddress
        MAX-ACCESS  read-create
        STATUS      current
        DESCRIPTION
            "This object specifies which bits of a packet's IP Source
             Address that are compared to match this rule. An IP packet
             matches the rule when the packet source address bitwise
             ANDed with the
             wmanIfBsClassifierRuleIpSourceMask value equals the
             wmanIfBsClassifierRuleIpSourceAddr value.
             If the referenced parameter is not present in a classifier,
             this object reports the value of 0.0.0.0."
        REFERENCE
            "Subclause 11.13.19.3.4.4 in IEEE 802.16-2004"
        ::= { wmanIfBsClassifierRuleEntry 8 }

wmanIfBsClassifierRuleIpDestAddr OBJECT-TYPE
        SYNTAX      InetAddress
        MAX-ACCESS  read-create
        STATUS      current
        DESCRIPTION
            "This object specifies the value of the IP Destination
             Address required for packets to match this rule. An IP
             packet matches the rule when the packet IP destination
             address bitwise ANDed with the
             wmanIfBsClassifierRuleIpDestMask value equals the
             wmanIfBsClassifierRuleIpDestAddr value.
             If the referenced parameter is not present in a 
             classifier, this object reports the value of 0.0.0.0."
        REFERENCE
            "Subclause 11.13.19.3.4.5 in IEEE 802.16-2004"
        ::= { wmanIfBsClassifierRuleEntry 9 }

wmanIfBsClassifierRuleIpDestMask OBJECT-TYPE
        SYNTAX      InetAddress
        MAX-ACCESS  read-create
        STATUS      current
        DESCRIPTION
            "This object specifies which bits of a packet's IP 
             Destination Address that are compared to match this rule.
             An IP packet matches the rule when the packet destination
             address bitwise ANDed with the
             wmanIfBsClassifierRuleIpDestMask value equals the
             wmanIfBsClassifierRuleIpDestAddr value.
             If the referenced parameter is not present in a classifier
             , this object reports the value of 0.0.0.0."
        REFERENCE
            "Subclause 11.13.19.3.4.5 in IEEE 802.16-2004"
        ::= { wmanIfBsClassifierRuleEntry 10 }

wmanIfBsClassifierRuleSourcePortStart OBJECT-TYPE
        SYNTAX      Integer32 (0..65535)
        MAX-ACCESS  read-create
        STATUS      current
        DESCRIPTION
            "This object specifies the low end inclusive range of
             TCP/UDP source port numbers to which a packet is compared.
             This object is irrelevant for non-TCP/UDP IP packets.
             If the referenced parameter is not present in a
             classifier, this object reports the value of 0."
        REFERENCE
            "Subclause 11.13.19.3.4.6 in IEEE 802.16-2004"
        ::= { wmanIfBsClassifierRuleEntry 11 }

wmanIfBsClassifierRuleSourcePortEnd OBJECT-TYPE
        SYNTAX      Integer32 (0..65535)
        MAX-ACCESS  read-create
        STATUS      current
        DESCRIPTION
            "This object specifies the high end inclusive range of
             TCP/UDP source port numbers to which a packet is compared.
             This object is irrelevant for non-TCP/UDP IP packets.
             If the referenced parameter is not present in a classifier,
             this object reports the value of 65535."
        REFERENCE
            "Subclause 11.13.19.3.4.6 in IEEE 802.16-2004"
        ::= { wmanIfBsClassifierRuleEntry 12 }

wmanIfBsClassifierRuleDestPortStart OBJECT-TYPE
        SYNTAX      Integer32 (0..65535)
        MAX-ACCESS  read-create
        STATUS      current
        DESCRIPTION
            "This object specifies the low end inclusive range of
             TCP/UDP destination port numbers to which a packet is
             compared. If the referenced parameter is not present
             in a classifier, this object reports the value of 0."
        REFERENCE
            "Subclause 11.13.19.3.4.7 in IEEE 802.16-2004"
        ::= { wmanIfBsClassifierRuleEntry 13 }

wmanIfBsClassifierRuleDestPortEnd OBJECT-TYPE
        SYNTAX      Integer32 (0..65535)
        MAX-ACCESS  read-create
        STATUS      current
        DESCRIPTION
            "This object specifies the high end inclusive range of
             TCP/UDP destination port numbers to which a packet is
             compared. If the referenced parameter is not present
             in a classifier, this object reports the value of
             65535."
        REFERENCE
            "Subclause 11.13.19.3.4.7 in IEEE 802.16-2004"
        ::= { wmanIfBsClassifierRuleEntry 14 }

wmanIfBsClassifierRuleDestMacAddr OBJECT-TYPE
        SYNTAX      MacAddress
        MAX-ACCESS  read-create
        STATUS      current
        DESCRIPTION
            "An Ethernet packet matches an entry when its destination
             MAC address bitwise ANDed with 
             wmanIfBsClassifierRuleDestMacMask equals the value of
             wmanIfBsClassifierRuleDestMacAddr. If the referenced
             parameter is not present in a classifier, this object
             reports the value of '000000000000'H."
        REFERENCE
            "Subclause 11.13.19.3.4.8 in IEEE 802.16-2004"
        ::= { wmanIfBsClassifierRuleEntry 15 }

wmanIfBsClassifierRuleDestMacMask OBJECT-TYPE
        SYNTAX      MacAddress
        MAX-ACCESS  read-create
        STATUS      current
        DESCRIPTION
            "An Ethernet packet matches an entry when its destination
             MAC address bitwise ANDed with
             wmanIfBsClassifierRuleDestMacMask equals the value of
             wmanIfBsClassifierRuleDestMacAddr. If the referenced
             parameter is not present in a classifier, this object
             reports the value of '000000000000'H."
        REFERENCE
            "Subclause 11.13.19.3.4.8 in IEEE 802.16-2004"
        ::= { wmanIfBsClassifierRuleEntry 16 }

wmanIfBsClassifierRuleSourceMacAddr OBJECT-TYPE
        SYNTAX      MacAddress
        MAX-ACCESS  read-create
        STATUS      current
        DESCRIPTION
            "An Ethernet packet matches this entry when its source
             MAC address  bitwise ANDed with
             wmanIfBsClassifierRuleSourceMacMask equals the value
             of wmanIfBsClassifierRuleSourceMacAddr. If the
             referenced parameter is not present in a classifier,
             this object reports the value of '000000000000'H."
        REFERENCE
            "Subclause 11.13.19.3.4.9 in IEEE 802.16-2004"
        ::= { wmanIfBsClassifierRuleEntry 17 }

wmanIfBsClassifierRuleSourceMacMask OBJECT-TYPE
        SYNTAX      MacAddress
        MAX-ACCESS  read-create
        STATUS      current
        DESCRIPTION
            "An Ethernet packet matches an entry when its source
             MAC address bitwise ANDed with
             wmanIfBsClassifierRuleSourceMacMask equals the value of
             wmanIfBsClassifierRuleSourceMacAddr. If the referenced
             parameter is not present in a classifier, this object
             reports the value of '000000000000'H."
        REFERENCE
            "Subclause 11.13.19.3.4.9 in IEEE 802.16-2004"
        ::= { wmanIfBsClassifierRuleEntry 18 }

wmanIfBsClassifierRuleEnetProtocolType OBJECT-TYPE
        SYNTAX      INTEGER {none(0),
                             ethertype(1),
                             dsap(2)}
        MAX-ACCESS  read-create
        STATUS      current
        DESCRIPTION
            "This object indicates the format of the layer 3 protocol
             id in the Ethernet packet. A value of none(0) means that
             the rule does not use the layer 3 protocol type as a
             matching criteria. A value of ethertype(1) means that the
             rule applies only to frames which contains an EtherType
             value. Ethertype values are contained in packets using
             the Dec-Intel-Xerox (DIX) encapsulation or the RFC1042
             Sub-Network Access Protocol (SNAP) encapsulation formats.
             A value of dsap(2) means that the rule applies only to
             frames using the IEEE802.3 encapsulation format with a
             Destination Service Access Point (DSAP) other than 0xAA
             (which is reserved for SNAP). If the Ethernet frame
             contains an 802.1P/Q Tag header (i.e. EtherType 0x8100),
             this object applies to the embedded EtherType field within
             the 802.1P/Q header. If the referenced parameter is not
             present in a classifier, this object reports the value of
             0."                     
        REFERENCE
            "Subclause 11.13.19.3.4.10 in IEEE 802.16-2004"
        ::= { wmanIfBsClassifierRuleEntry 19 }

wmanIfBsClassifierRuleEnetProtocol OBJECT-TYPE
        SYNTAX      Integer32 (0..65535)
        MAX-ACCESS  read-create
        STATUS      current
        DESCRIPTION
            "If wmanIfBsClassifierRuleEnetProtocolType is none(0),
             this object is ignored when considering whether a packet
             matches the current rule.
             If wmanIfBsClassifierRuleEnetProtocolType is ethertype(1),
             this object gives the 16-bit value of the EtherType that
             the packet must match in order to match the rule.
             If wmanIfBsClassifierRuleEnetProtocolType is dsap(2), the
             lower 8 bits of this object's value must match the DSAP
             byte of the packet in order to match the rule.
             If the Ethernet frame contains an 802.1P/Q Tag header
             (i.e. EtherType 0x8100), this object applies to the
             embedded EtherType field within the 802.1P/Q header.
             If the referenced parameter is not present in the
             classifier, the value of this object is reported as 0."
        REFERENCE
            "Subclause 11.13.19.3.4.10 in IEEE 802.16-2004"
        ::= { wmanIfBsClassifierRuleEntry 20 }

wmanIfBsClassifierRuleUserPriLow OBJECT-TYPE
        SYNTAX      Integer32 (0..7)
        MAX-ACCESS  read-create
        STATUS      current
        DESCRIPTION
            "This object applies only to Ethernet frames using the
             802.1P/Q tag header (indicated with EtherType 0x8100).
             Such frames include a 16-bit Tag that contains a 3 bit
             Priority field and a 12 bit VLAN number.
             Tagged Ethernet packets must have a 3-bit Priority field
             within the range of wmanIfBsClassifierRuleUserPriLow and
             wmanIfBsClassifierRuleUserPriHigh in order to match this
             rule.
             If the referenced parameter is not present in the
             classifier, the value of this object is reported as 0."
        REFERENCE
            "Subclause 11.13.19.3.4.11 in IEEE 802.16-2004"
        ::= { wmanIfBsClassifierRuleEntry 21 }

wmanIfBsClassifierRuleUserPriHigh OBJECT-TYPE
        SYNTAX      Integer32 (0..7)
        MAX-ACCESS  read-create
        STATUS      current
        DESCRIPTION
            "This object applies only to Ethernet frames using the
             802.1P/Q tag header (indicated with EtherType 0x8100).
             Such frames include a 16-bit Tag that contains a 3 bit
             Priority field and a 12 bit VLAN number.
             Tagged Ethernet packets must have a 3-bit Priority
             field within the range of wmanIfBsClassifierRuleUserPriLow
             and wmanIfBsClassifierRuleUserPriHigh in order to match
             this rule.
             If the referenced parameter is not present in the 
             classifier, the value of this object is reported as 7."
        REFERENCE
            "Subclause 11.13.19.3.4.11 in IEEE 802.16-2004"
        ::= { wmanIfBsClassifierRuleEntry 22 }

wmanIfBsClassifierRuleVlanId OBJECT-TYPE
        SYNTAX      Integer32 (0..4095)
        MAX-ACCESS  read-create
        STATUS      current
        DESCRIPTION
            "This object applies only to Ethernet frames using the
             802.1P/Q tag header.
             If this object's value is nonzero, tagged packets must
             have a VLAN Identifier that matches the value in order
             to match the rule.
             Only the least significant 12 bits of this object's
             value are valid.
             If the referenced parameter is not present in the
             classifier, the value of this object is reported as 0."
        REFERENCE
            "Subclause 11.13.19.3.4.12 in IEEE 802.16-2004"
        ::= { wmanIfBsClassifierRuleEntry 23 }

wmanIfBsClassifierRuleState OBJECT-TYPE
        SYNTAX      INTEGER {active(1),
                             inactive(2)}
        MAX-ACCESS  read-create
        STATUS      current
        DESCRIPTION
            "This object indicates whether or not the classifier is
             enabled to classify packets to a Service Flow.
             If the referenced parameter is not present in the
             classifier, the value of this object is reported
             as active(1)."
        ::= { wmanIfBsClassifierRuleEntry 24 }
        
wmanIfBsClassifierRulePhsSize OBJECT-TYPE
        SYNTAX      Integer32
        UNITS       "byte"
        MAX-ACCESS  read-create
        STATUS      current
        DESCRIPTION                                                     
            "This object is used to configure the PHS rule for this
             classifer. The value of this field - PHSS is the total
             number of bytes in the header to be suppressed and then
             restored in a service flow that uses PHS. If the value of
             this field is 0 bytes then PHS is disabled for this
             classifer. If flag phsMask in wmanIfBsClassifierRuleBitMap
             is set to 0 and flag phsSize in
             wmanIfBsClassifierRuleBitMap is set to 0, then BS can still
             create PHS rules using its own custom mask (i.e. the rule
             is not configured by NMS)."
        REFERENCE
            "Subclause 11.13.19.3.7.4 in IEEE 802.16-2004"
        DEFVAL      {0}
        ::= { wmanIfBsClassifierRuleEntry 25 }
        
wmanIfBsClassifierRulePhsMask OBJECT-TYPE
        SYNTAX      OCTET STRING (SIZE(0..65535))
        MAX-ACCESS  read-create
        STATUS      current
        DESCRIPTION                                                     
            "This object is used to configure the PHS rule for this
             classifer. It is encoded as follows:
             bit 0:
                0 = don't suppress the 1st byte of the suppression field
                1 = suppress first byte of the suppression field
             bit 1:
                0 = don't suppress the 2nd byte of the suppression field
                1 = suppress second byte of the suppression field
             bit x:
                0 = don't suppress the (x+1) byte of the suppression
                    field
                1 = suppress (x+1) byte of the suppression field
             where the length of the octet string is ceiling
             (wmanIfBsClassifierRulePhsSize/8). BS should use this value
             to create a new PHS rule index (PHSI) and field (PHSF) as
             defined in the standard. If flag phsMask in
             wmanIfBsClassifierRuleBitMap is set to 0 and flag phsSize
             in wmanIfBsClassifierRuleBitMap is set to 0, then BS can
             still create PHS rules using its own custom mask (i.e. the
             rule is not configured by NMS)."
        REFERENCE
            "Subclause 11.13.19.3.7.3 in IEEE 802.16-2004"
        ::= { wmanIfBsClassifierRuleEntry 26 }

wmanIfBsClassifierRulePhsVerify OBJECT-TYPE
        SYNTAX      WmanIfPhsRuleVerify
        MAX-ACCESS  read-create
        STATUS      current
        DESCRIPTION
            "The value of this field indicates to the sending entity    
             whether or not the packet header contents are to be
             verified prior to performing suppression."
        DEFVAL      { phsVerifyEnable }
        ::= { wmanIfBsClassifierRuleEntry 27 }

wmanIfBsClassifierRuleIpv6FlowLabel OBJECT-TYPE
        SYNTAX      WmanIfIpv6FlowLabel
        MAX-ACCESS  read-create
        STATUS      current
        DESCRIPTION
            "The value of this field specifies the matching values for
             the IPv6 Flow label field."
        ::= { wmanIfBsClassifierRuleEntry 28 }
                 
wmanIfBsClassifierRuleBitMap OBJECT-TYPE
        SYNTAX      WmanIfClassifierBitMap
        MAX-ACCESS  read-create
        STATUS      current
        DESCRIPTION
            "This object indicates which parameter encodings were
             actually present in the entry. A bit set to '1' indicates
             the corresponding classifier encoding is present, and '0'
             means otherwise"
        ::= { wmanIfBsClassifierRuleEntry 29 }
    
wmanIfBsClassifierRuleRowStatus OBJECT-TYPE
        SYNTAX      RowStatus
        MAX-ACCESS  read-create
        STATUS      current
        DESCRIPTION
            "This object is used to create a new row or modify or
             delete an existing row in this table.

             If the implementator of this MIB has choosen not
             to implement 'dynamic assignment' of profiles, this
             object is not useful and should return noSuchName
             upon SNMP request."
        ::= { wmanIfBsClassifierRuleEntry 30 }
        
wmanIfBsSsPacketCounterTable OBJECT-TYPE
        SYNTAX      SEQUENCE OF WmanIfBsSsPacketCounterEntry
        MAX-ACCESS  not-accessible
        STATUS      current
        DESCRIPTION
            "This table contains counters to keep track of the number
             of packets and octets that have been received or 
             transmitted on the per service flow basis."        
        ::= { wmanIfBsPacketCs 5 }

wmanIfBsSsPacketCounterEntry OBJECT-TYPE
        SYNTAX      WmanIfBsSsPacketCounterEntry
        MAX-ACCESS  not-accessible
        STATUS      current
        DESCRIPTION 
           "This table provides one row for each service flow, and 
            is indexed by ifIndex and wmanIfCmnCpsSfId."
        INDEX { ifIndex, wmanIfCmnCpsSfMacAddress,
                wmanIfCmnCpsSfId }
        ::= { wmanIfBsSsPacketCounterTable 1 }

WmanIfBsSsPacketCounterEntry::= SEQUENCE {
        wmanIfBsSsMacSduCount                   Counter64,
        wmanIfBsSsOctetCount                    Counter64,
        wmanIfBsSsResetCounter                  INTEGER,
        wmanIfBsSsResetCounterTime              TimeStamp}

wmanIfBsSsMacSduCount OBJECT-TYPE
        SYNTAX      Counter64
        MAX-ACCESS  read-only
        STATUS      current
        DESCRIPTION
            "This object counts the number of MAC SDUs that have
             been transmitted or received."
        ::= { wmanIfBsSsPacketCounterEntry 1 }

wmanIfBsSsOctetCount OBJECT-TYPE
        SYNTAX      Counter64
        MAX-ACCESS  read-only
        STATUS      current
        DESCRIPTION
            "This object counts the number of octets of MAC SDUs
             that have been transmitted or received."
        ::= { wmanIfBsSsPacketCounterEntry 2 }
                
wmanIfBsSsResetCounter OBJECT-TYPE
        SYNTAX      INTEGER {null(0),
                             resetCounter(1)}
        MAX-ACCESS  read-write
        STATUS      current
        DESCRIPTION
            "When this attribute is SET to resetCounter(1), the
             corresponding entry of packet counters will be reset.
             A GET operation performed on this object will always
             return null(0). The counter is normally reset after
             the packet count information is retrieved. "
        ::= { wmanIfBsSsPacketCounterEntry 3 }
        
wmanIfBsSsResetCounterTime OBJECT-TYPE
        SYNTAX      TimeStamp
        MAX-ACCESS  read-only
        STATUS      current
        DESCRIPTION
            "Indicates the date and time when the counter is
             reset."
        ::= { wmanIfBsSsPacketCounterEntry 4 }
                                                                                          
--
-- wmanIfBsCps contain the Base Station Common Part Sublayer objects
--
wmanIfBsCps OBJECT IDENTIFIER ::= { wmanIfBsObjects 2 }

wmanIfBsRegisteredSsTable OBJECT-TYPE
        SYNTAX      SEQUENCE OF WmanIfBsRegisteredSsEntry
        MAX-ACCESS  not-accessible
        STATUS      current
        DESCRIPTION
            "This table contains the basic capability information
             of SSs that have been negotiated and agreed between
             BS and SS via REG-REQ and REG-RSP messages. An entry
             in this table indicates the SS has entered and registered
             into the BS."
        REFERENCE
            "Subclause 6.3.2.3.7 in IEEE 802.16-2004"
        ::= { wmanIfBsCps 1 }

wmanIfBsRegisteredSsEntry OBJECT-TYPE
        SYNTAX      WmanIfBsRegisteredSsEntry
        MAX-ACCESS  not-accessible
        STATUS      current
        DESCRIPTION
            "This table provides one row for each SS that has been
             registered in the BS, and is indexed by 
             wmanIfBsSsMacAddress. The primary index is the ifIndex
             with an ifType of propBWAp2Mp, indicating the BS sector
             with which the SS is associated. wmanIfBsSsMacAddress
             identifies the SS being registered."
        INDEX { ifIndex, wmanIfBsSsMacAddress }
        ::= { wmanIfBsRegisteredSsTable 1 }

WmanIfBsRegisteredSsEntry ::= SEQUENCE {        
        wmanIfBsSsMacAddress                    MacAddress,
        wmanIfBsSsBasicCid                      WmanIfCidType,
        wmanIfBsSsPrimaryCid                    WmanIfCidType,
        wmanIfBsSsSecondaryCid                  WmanIfCidType,
        wmanIfBsSsManagementSupport             INTEGER,
        wmanIfBsSsIpManagementMode              INTEGER,
        wmanIfBsSs2ndMgmtArqEnable              TruthValue,
        wmanIfBsSs2ndMgmtArqWindowSize          INTEGER,
        wmanIfBsSs2ndMgmtArqDnLinkTxDelay       INTEGER,
        wmanIfBsSs2ndMgmtArqUpLinkTxDelay       INTEGER,
        wmanIfBsSs2ndMgmtArqDnLinkRxDelay       INTEGER,
        wmanIfBsSs2ndMgmtArqUpLinkRxDelay       INTEGER,
        wmanIfBsSs2ndMgmtArqBlockLifetime       INTEGER,
        wmanIfBsSs2ndMgmtArqSyncLossTimeout     INTEGER,
        wmanIfBsSs2ndMgmtArqDeliverInOrder      TruthValue,
        wmanIfBsSs2ndMgmtArqRxPurgeTimeout      INTEGER,
        wmanIfBsSs2ndMgmtArqBlockSize           INTEGER,
        wmanIfBsSsVendorIdEncoding              OCTET STRING,
        wmanIfBsSsAasBroadcastPermission        INTEGER, 
        wmanIfBsSsMaxTxPowerBpsk                WmanIfMaxTxPowerType, 
        wmanIfBsSsMaxTxPowerQpsk                WmanIfMaxTxPowerType,
        wmanIfBsSsMaxTxPower16Qam               WmanIfMaxTxPowerType,
        wmanIfBsSsMaxTxPower64Qam               WmanIfMaxTxPowerType,
        wmanIfBsSsMacVersion                    WmanIfMacVersion}
       
wmanIfBsSsMacAddress OBJECT-TYPE
        SYNTAX      MacAddress 
        MAX-ACCESS  not-accessible
        STATUS      current
        DESCRIPTION
            "The MAC address of SS is received from the RNG-REQ
             message. When SS registers, this MAC address is entered
             into the table, and used as the identifier to the SS."
        REFERENCE
            "Subclause 6.3.2.3.5 in IEEE 802.16-2004"
        ::= { wmanIfBsRegisteredSsEntry 1 }
                       
wmanIfBsSsBasicCid OBJECT-TYPE
        SYNTAX      WmanIfCidType 
        MAX-ACCESS  read-only
        STATUS      current
        DESCRIPTION
            "The value of this object indicates the SS's basic CID
             that was sent in the RNG-RSP message."
        REFERENCE
            "Subclause 6.3.2.3.6 in IEEE 802.16-2004"
        ::= { wmanIfBsRegisteredSsEntry 2 }
        
wmanIfBsSsPrimaryCid OBJECT-TYPE
        SYNTAX      WmanIfCidType 
        MAX-ACCESS  read-only
        STATUS      current
        DESCRIPTION
            "The value of this object indicates the primary CID of the
             SS received from the RNG-RSP message."
        REFERENCE
            "Subclause 6.3.2.3.6 in IEEE 802.16-2004"
        ::= { wmanIfBsRegisteredSsEntry 3 }
        
wmanIfBsSsSecondaryCid OBJECT-TYPE
        SYNTAX      WmanIfCidType 
        MAX-ACCESS  read-only
        STATUS      current
        DESCRIPTION
            "The value of this object indicates the secondary
             management CID present in the REG-RSP message. The value
             should be null if the 2nd management channel is not
             available."
        REFERENCE
            "Subclause 6.4.2.3.8 in IEEE 802.16-2004"
        ::= { wmanIfBsRegisteredSsEntry 4 }
        
wmanIfBsSsManagementSupport OBJECT-TYPE
        SYNTAX      INTEGER {unmanagedSs(0),
                             managedSs(1)} 
        MAX-ACCESS  read-only
        STATUS      current
        DESCRIPTION
            "This object indicates whether or not the SS is managed."
        REFERENCE
            "Subclause 11.7.2 in IEEE 802.16-2004"
        ::= { wmanIfBsRegisteredSsEntry 5 }
                                                                                        
wmanIfBsSsIpManagementMode OBJECT-TYPE
        SYNTAX      INTEGER {unmanaged(0),
                             ipManaged(1)} 
        MAX-ACCESS  read-only
        STATUS      current
        DESCRIPTION
            "The IP management mode parameter dictates whether
             the provider intends to manage the SS on an ongoing
             basis via IP-based mechanisms."
        REFERENCE
            "Subclause 11.7.3 in IEEE 802.16-2004"
        ::= { wmanIfBsRegisteredSsEntry 6 }

wmanIfBsSs2ndMgmtArqEnable OBJECT-TYPE
        SYNTAX      TruthValue
        MAX-ACCESS  read-only
        STATUS      current
        DESCRIPTION
            "True(1) ARQ enabling is requested for the 2nd
             management channel."
        REFERENCE
            "Subclause 11.13.18.1 in IEEE 802.16-2004"
        ::= { wmanIfBsRegisteredSsEntry 7 }

wmanIfBsSs2ndMgmtArqWindowSize	 OBJECT-TYPE
        SYNTAX      INTEGER (1 .. 1024)
        MAX-ACCESS  read-only
        STATUS      current
        DESCRIPTION
            "Indicates the maximum number of unacknowledged 
             fragments at any time for 2nd management channel."
        REFERENCE
            "Subclause 11.13.18.2 in IEEE 802.16-2004"
        ::= { wmanIfBsRegisteredSsEntry 8 }

wmanIfBsSs2ndMgmtArqDnLinkTxDelay OBJECT-TYPE
        SYNTAX      INTEGER (0 .. 65535)
        UNITS       "us"
        MAX-ACCESS  read-only
        STATUS      current
        DESCRIPTION
            "The object defines the ARQ transmitter delay for
             downlink transmission."
        REFERENCE
            "Subclause 11.13.18.3 in IEEE 802.16-2004"
        ::= { wmanIfBsRegisteredSsEntry 9 }

wmanIfBsSs2ndMgmtArqUpLinkTxDelay OBJECT-TYPE
        SYNTAX      INTEGER (0 .. 65535)
        UNITS       "us"
        MAX-ACCESS  read-only
        STATUS      current
        DESCRIPTION
            "The object defines the ARQ transmitter delay for
             uplink transmission."
        REFERENCE
            "Subclause 11.13.18.3 in IEEE 802.16-2004"
        ::= { wmanIfBsRegisteredSsEntry 10 }

wmanIfBsSs2ndMgmtArqDnLinkRxDelay OBJECT-TYPE
        SYNTAX      INTEGER (0 .. 65535)
        UNITS       "us"
        MAX-ACCESS  read-only
        STATUS      current
        DESCRIPTION
            "The object defines the ARQ receiver delay for
             downlink transmission."
        REFERENCE
            "Subclause 11.13.18.3 in IEEE 802.16-2004"
        ::= { wmanIfBsRegisteredSsEntry 11 }

wmanIfBsSs2ndMgmtArqUpLinkRxDelay OBJECT-TYPE
        SYNTAX      INTEGER (0 .. 65535)
        UNITS       "us"
        MAX-ACCESS  read-only
        STATUS      current
        DESCRIPTION
            "The object defines the ARQ receiver delay for
             uplink transmission."
        REFERENCE
            "Subclause 11.13.18.3 in IEEE 802.16-2004"
        ::= { wmanIfBsRegisteredSsEntry 12 }
                
wmanIfBsSs2ndMgmtArqBlockLifetime OBJECT-TYPE
        SYNTAX      INTEGER (0 .. 65535)
        UNITS       "10 us"
        MAX-ACCESS  read-only
        STATUS      current
        DESCRIPTION
            "The maximum time interval an ARQ fragment will be
             managed by the transmitter ARQ machine, once
             initial transmission of the fragment has occured.
             If transmission or retransmission of the fragment
             is not acknowledged by the receiver before the 
             time limit is reached, the fragment is discarded.
             A value of 0 means Infinite."
        REFERENCE
            "Subclause 11.13.18.4 in IEEE 802.16-2004"
        DEFVAL		{0}
        ::= { wmanIfBsRegisteredSsEntry 13 }

wmanIfBsSs2ndMgmtArqSyncLossTimeout OBJECT-TYPE
        SYNTAX      INTEGER (0 .. 65535)
        UNITS       "10 us"
        MAX-ACCESS  read-only
        STATUS      current
        DESCRIPTION
            "The maximum interval before declaring a loss
             of synchronization of the sender and receiver
             state machines. A value of 0 means Infinite."
        REFERENCE
            "Subclause 11.13.18.5 in IEEE 802.16-2004"
        DEFVAL	    {0}
        ::= { wmanIfBsRegisteredSsEntry 14 }

wmanIfBsSs2ndMgmtArqDeliverInOrder  OBJECT-TYPE
        SYNTAX      TruthValue
        MAX-ACCESS  read-only
        STATUS      current
        DESCRIPTION
            "Indicates whether or not data is to be delivered
             by the receiving MAC to its client application
             in the order in which data was handed off to the
             originating MAC."
        REFERENCE
            "Subclause 11.13.18.6 in IEEE 802.16-2004"
        ::= { wmanIfBsRegisteredSsEntry 15 }

wmanIfBsSs2ndMgmtArqRxPurgeTimeout  OBJECT-TYPE
        SYNTAX      INTEGER (0 .. 65535)
        UNITS       "10 us"
        MAX-ACCESS  read-only
        STATUS      current
        DESCRIPTION
            "Indicates the time interval the ARQ window is advanced
             after a fragment is received. A value of 0 means Infinite."
        REFERENCE
            "Subclause 11.13.18.7 in IEEE 802.16-2004"
        DEFVAL	    {0}
        ::= { wmanIfBsRegisteredSsEntry 16 }                                               

wmanIfBsSs2ndMgmtArqBlockSize OBJECT-TYPE
        SYNTAX      INTEGER (1 .. 2040)
        MAX-ACCESS  read-only
        STATUS      current
        DESCRIPTION
            "This parameter specifies the size of a ARQ block. This
             parameter shall be established by negotiation during the
             connection setup. The requester includes its desired
             setting in the REQ message. The receiver of the REQ
             message shall take the smaller of the value it prefers and
             value in the REQ message. The minimum value is included in
             the RSP message."
        REFERENCE
            "Subclause 11.13.18.8 in IEEE 802.16-2004"
        ::= { wmanIfBsRegisteredSsEntry 17 }
        
wmanIfBsSsVendorIdEncoding OBJECT-TYPE
        SYNTAX      OCTET STRING (SIZE(3))
        MAX-ACCESS  read-only
        STATUS      current
        DESCRIPTION
            "The value field contains the vendor identification
             specified by the 3 byte vendor-specific organizationally
             unique identifier of the SS or BS MAC address.A vendor ID
             used in a REG-REQ shall be the Vendor ID of the SS sending
             the request. A vendor ID used in a REG-RSP shall be the
             Vendor ID of the BS sending the response."
        REFERENCE
            "Subclause 11.1.5 in IEEE 802.16-2004"
        ::= { wmanIfBsRegisteredSsEntry 18 }

wmanIfBsSsAasBroadcastPermission OBJECT-TYPE
        SYNTAX	    INTEGER {contBasedBwReqPermitted(0),
                             contBasedBwReqNotPermitted(1)}
        MAX-ACCESS  read-only
        STATUS      current
        DESCRIPTION
            "This parameter specifies if SS can issue contention-based
             bandwidth request or not."
        REFERENCE
            "Subclause 11.6 in IEEE 802.16-2004"
        ::= { wmanIfBsRegisteredSsEntry 19 }

wmanIfBsSsMaxTxPowerBpsk OBJECT-TYPE
        SYNTAX      WmanIfMaxTxPowerType                         
        MAX-ACCESS  read-only
        STATUS      current
        DESCRIPTION
            "The maximum available power for BPSK. The maximum power
             parameters are reported in dBm and quantized in 0.5 dBm
             steps ranging from -64 dBm (encoded 0x00) to 63.5 dBm
             (encoded 0xFF). Values outside this range shall be assigned
             the closest extreme. This parameter is only applicable to
             systems supporting the SCa, OFDM or OFDMA PHY."
        REFERENCE
            "Subclause 11.8.3.2 in IEEE 802.16-2004"
        ::= { wmanIfBsRegisteredSsEntry 20 }

wmanIfBsSsMaxTxPowerQpsk OBJECT-TYPE
        SYNTAX      WmanIfMaxTxPowerType                         
        MAX-ACCESS  read-only
        STATUS      current
        DESCRIPTION
            "The maximum available power for QPSK. The maximum power
             parameters are reported in dBm and quantized in 0.5 dBm
             steps ranging from -64 dBm (encoded 0x00) to 63.5 dBm
             (encoded 0xFF). Values outside this range shall be assigned
             to closest extreme. This parameter is only applicable to
             systems supporting the SCa, OFDM or OFDMA PHY."
        REFERENCE
            "Subclause 11.8.3.2 in IEEE 802.16-2004"
        ::= { wmanIfBsRegisteredSsEntry 21 }
        
wmanIfBsSsMaxTxPower16Qam OBJECT-TYPE
        SYNTAX      WmanIfMaxTxPowerType                         
        MAX-ACCESS  read-only
        STATUS      current
        DESCRIPTION
            "The maximum available power for 16-QAM constellations.
             The maximum power parameters are reported in dBm and
             quantized in 0.5 dBm steps ranging from -64 dBm (encoded
             0x00) to 63.5 dBm (encoded 0xFF). Values outside this
             range shall be assigned the closest extreme. This parameter
             is only applicable to systems supporting the SCa, OFDM or
             OFDMA PHY."
        REFERENCE
            "Subclause 11.8.3.2 in IEEE 802.16-2004"
        ::= { wmanIfBsRegisteredSsEntry 22 }
        
wmanIfBsSsMaxTxPower64Qam OBJECT-TYPE
        SYNTAX      WmanIfMaxTxPowerType                         
        MAX-ACCESS  read-only
        STATUS      current
        DESCRIPTION
            "The maximum available power for 64-QAM constellations.
             The maximum power parameters are reported in dBm and
             quantized in 0.5 dBm steps ranging from -64 dBm (encoded
             0x00) to 63.5 dBm (encoded 0xFF). Values outside this
             range shall be assigned the closest extreme. SSs that do
             not support QAM64 shall report the value of 0x00. This
             parameter is only applicable to systems supporting the SCa,
             OFDM or OFDMA PHY."
        REFERENCE
            "Subclause 11.8.3.2 in IEEE 802.16-2004"
        ::= { wmanIfBsRegisteredSsEntry 23 }
                
wmanIfBsSsMacVersion OBJECT-TYPE
        SYNTAX      WmanIfMacVersion                         
        MAX-ACCESS  read-only
        STATUS      current
        DESCRIPTION
            "This parameter specifies the version of 802.16 to which the
             message originator conforms."
        REFERENCE
            "Subclause 11.1.3 in IEEE 802.16-2004"
        ::= { wmanIfBsRegisteredSsEntry 24 }  
               
--
-- wmanIfBsConfigurationTable contains global parameters common in BS       
--
wmanIfBsConfigurationTable OBJECT-TYPE
        SYNTAX      SEQUENCE OF WmanIfBsConfigurationEntry
        MAX-ACCESS  not-accessible
        STATUS      current
        DESCRIPTION
            "This table provides one row for each BS sector that
             contains the BS system parameters as defined in Subclause
             10.1 of [3]. The objects in this table define the default
             behaviour of the BS for 2nd Management Channel scheduling
             and SFID allocation as well as configuration parameters
             of the CPS scheduler and AAS system."
        REFERENCE
            "Subclause 10.1 in IEEE 802.16-2004"
        ::= { wmanIfBsCps 2 }

wmanIfBsConfigurationEntry OBJECT-TYPE
        SYNTAX      WmanIfBsConfigurationEntry
        MAX-ACCESS  not-accessible
        STATUS      current
        DESCRIPTION
            "This table is indexed by ifIndex with an ifType of
             propBWAp2Mp."
        INDEX { ifIndex }
        ::= { wmanIfBsConfigurationTable 1 }

WmanIfBsConfigurationEntry ::= SEQUENCE {
        wmanIfBsDcdInterval                     INTEGER,
        wmanIfBsUcdInterval                     INTEGER,
        wmanIfBsUcdTransition                   INTEGER,
        wmanIfBsDcdTransition                   INTEGER,
        wmanIfBsInitialRangingInterval          INTEGER,
        wmanIfBsSsULMapProcTime                 Unsigned32,
        wmanIfBsSsRangRespProcTime              Unsigned32,
        wmanIfBsT5Timeout                       INTEGER,
        wmanIfBsT9Timeout                       INTEGER,
        wmanIfBsT13Timeout                      INTEGER,
        wmanIfBsT15Timeout                      INTEGER,
        wmanIfBsT17Timeout                      INTEGER,
        wmanIfBsT27IdleTimer                    Unsigned32,
        wmanIfBsT27ActiveTimer                  Unsigned32,
        wmanIfBs2ndMgmtDlQoSProfileIndex        INTEGER,
        wmanIfBs2ndMgmtUlQoSProfileIndex        INTEGER,
        wmanIfBsAutoSfidEnabled                 INTEGER,
        wmanIfBsAutoSfidRangeMin                Unsigned32,
        wmanIfBsAutoSfidRangeMax                Unsigned32,
        wmanIfBsAasChanFbckReqFreq              INTEGER,
        wmanIfBsAasBeamSelectFreq               INTEGER,
        wmanIfBsAasChanFbckReqResolution        INTEGER,
        wmanIfBsAasBeamReqResolution            INTEGER,
        wmanIfBsAasNumOptDiversityZones         INTEGER,
        wmanIfBsResetSector                     INTEGER}
        
wmanIfBsDcdInterval OBJECT-TYPE
        SYNTAX      INTEGER (0..10000)
        UNITS       "milliseconds"
        MAX-ACCESS  read-write
        STATUS      current
        DESCRIPTION
            "Time between transmission of DCD messages in ms."
        ::= { wmanIfBsConfigurationEntry 1 }

wmanIfBsUcdInterval OBJECT-TYPE
        SYNTAX      INTEGER (0..10000)
        UNITS       "milliseconds"
        MAX-ACCESS  read-write
        STATUS      current
        DESCRIPTION
            "Time between transmission of UCD messages in ms."
        ::= { wmanIfBsConfigurationEntry 2 }

wmanIfBsUcdTransition OBJECT-TYPE
        SYNTAX      INTEGER (2..65535)
        UNITS       "Number of MAC Frames"
        MAX-ACCESS  read-write
        STATUS      current
        DESCRIPTION
            "The time the BS shall wait after transmitting a UCD message
             with an incremented Configuration Change Count before
             issuing a UL-MAP message referring to
             Uplink_Burst_Profiles defined in that UCD message."
        ::= { wmanIfBsConfigurationEntry 3 }
                                
wmanIfBsDcdTransition OBJECT-TYPE
        SYNTAX      INTEGER (2..65535)
        UNITS       "Number of MAC Frames"
        MAX-ACCESS  read-write
        STATUS      current
        DESCRIPTION
            "The time the BS shall wait after transmitting a DCD message
             with an incremented Configuration Change Count before
             issuing a DL-MAP message referring to
             Downlink_Burst_Profiles defined in that DCD message."
        ::= { wmanIfBsConfigurationEntry 4 }

wmanIfBsInitialRangingInterval OBJECT-TYPE
        SYNTAX      INTEGER(0..2000)
        UNITS       "milliseconds"
        MAX-ACCESS  read-write
        STATUS      current
        DESCRIPTION
            "Time between Initial Ranging regions assigned by the BS
             in ms."
        ::= { wmanIfBsConfigurationEntry 5 }

wmanIfBsSsULMapProcTime OBJECT-TYPE
        SYNTAX      Unsigned32 (200 .. 4294967295) 
        UNITS       "micro seconds"
        MAX-ACCESS  read-write
        STATUS      current
        DESCRIPTION
            "Time provided between arrival of the last bit of a UL-MAP
             at an SS and effectiveness of that map in us."
        ::= { wmanIfBsConfigurationEntry 6 }

wmanIfBsSsRangRespProcTime OBJECT-TYPE
        SYNTAX      Unsigned32 (10000 .. 4294967295)
        UNITS       "micro seconds"
        MAX-ACCESS  read-write
        STATUS      current
        DESCRIPTION
            "Time allowed for an SS following receipt of a ranging
             response before it is expected to reply to an invited
             ranging request in us."
        ::= { wmanIfBsConfigurationEntry 7 }

wmanIfBsT5Timeout OBJECT-TYPE
        SYNTAX      INTEGER (0 .. 2000)
        UNITS       "milliseconds"
        MAX-ACCESS  read-write
        STATUS      current
        DESCRIPTION
        	"Wait for Uplink Channel Change Response in ms."
        ::= { wmanIfBsConfigurationEntry 8 }

wmanIfBsT9Timeout OBJECT-TYPE
        SYNTAX      INTEGER (300 .. 65535)
        UNITS       "milliseconds"
        MAX-ACCESS  read-write
        STATUS      current
        DESCRIPTION
        	"Registration Timeout, the time allowed between the BS
        	 sending a RNG-RSP (success) to an SS, and receiving a
        	 SBC-REQ from that same SS in ms."
        ::= { wmanIfBsConfigurationEntry 9 }

wmanIfBsT13Timeout OBJECT-TYPE
        SYNTAX      INTEGER (15 .. 65535)
        UNITS       "minutes"
        MAX-ACCESS  read-write
        STATUS      current
        DESCRIPTION
        	"The time allowed for an SS, following receipt of a
        	 REG-RSP message to send a TFTP-CPLT message to the BS
        	 in min."
        ::= { wmanIfBsConfigurationEntry 10 }

wmanIfBsT15Timeout OBJECT-TYPE
        SYNTAX      INTEGER (20 .. 65535)
        UNITS       "milliseconds"
        MAX-ACCESS  read-write
        STATUS      current
        DESCRIPTION
        	"Wait for MCA-RSP in ms."
        ::= { wmanIfBsConfigurationEntry 11 }

wmanIfBsT17Timeout OBJECT-TYPE
        SYNTAX      INTEGER (5 .. 65535)
        UNITS       "minutes"
        MAX-ACCESS  read-write
        STATUS      current
        DESCRIPTION
        	"Time allowed for SS to complete SS Authorization and
        	  Key Exchange in minutes."
        ::= { wmanIfBsConfigurationEntry 12 }

wmanIfBsT27IdleTimer OBJECT-TYPE
        SYNTAX      Unsigned32 (10000 .. 4294967295)
        UNITS       "us"
        MAX-ACCESS  read-write
        STATUS      current
        DESCRIPTION
        	"Maximum time between unicast grants to SS when BS believes 
        	 SS uplink transmission quality is good enough."
        ::= { wmanIfBsConfigurationEntry 13 }

wmanIfBsT27ActiveTimer OBJECT-TYPE
        SYNTAX      Unsigned32 (10000 .. 4294967295)
        UNITS       "us"
        MAX-ACCESS  read-write
        STATUS      current
        DESCRIPTION
        	"Maximum time between unicast grants to SS when BS believes 
        	 SS uplink transmission quality is not good enough."
        ::= { wmanIfBsConfigurationEntry 14 }


wmanIfBs2ndMgmtDlQoSProfileIndex OBJECT-TYPE
        SYNTAX      INTEGER (1..65535)
        MAX-ACCESS  read-write
        STATUS      current
        DESCRIPTION
            "This object defines the index of a row in
             wmanIfBsServiceClassTable which is used to obtain all QoS
             parameters required for the BS downlink scheduler to
             properly allocate and manage the bandwidth and schedule
             the 2nd Management Connection traffic. The 2nd Management
             Connection traffic doesn't differ from Traffic Connection
             traffic in the area of QoS management."
         ::= { wmanIfBsConfigurationEntry 15 }

wmanIfBs2ndMgmtUlQoSProfileIndex OBJECT-TYPE
        SYNTAX      INTEGER (1..65535)
        MAX-ACCESS  read-write
        STATUS      current
        DESCRIPTION
            "This object defines the index of a row in
             wmanIfBsServiceClassTable which is used to obtain all QoS
             parameters required for the BS uplink scheduler to
             properly allocate and manage the bandwidth and schedule
             the 2nd Management Connection traffic. The 2nd Management
             Connection traffic doesn't differ from Traffic Connection
             traffic in the area of QoS management."
        ::= { wmanIfBsConfigurationEntry 16 }

wmanIfBsAutoSfidEnabled OBJECT-TYPE
        SYNTAX      INTEGER {autoSfidDisabled(0),
                             autoSfidEnabled(1)}
        MAX-ACCESS  read-write
        STATUS      current
        DESCRIPTION
            "This object defines whether the BS is allowed to
             autonomously allocate SFIDs. When the object is set to
             autoSfidEnabled, the BS is allowed to autonomously allocate
             SFIDs from the range of allowed values defined by
             wmanIfBsConfigExtAutoSfidRangeMin and 
             wmanIfBsConfigExtAutoSfidRangeMax. A SF is created
             autonomously when it has not been provisioned in the
             wmanIfBsProvisionedSfTable and may be initiated by either
             the SS or BS. The BS should always initiate SF creation
             based on the provisioned Service flows configured in
             wmanIfBsProvisionedSfTable."
        REFERENCE
            "Subclause 11.13.1 in IEEE 802.16-2004"
         ::= { wmanIfBsConfigurationEntry 17 }

wmanIfBsAutoSfidRangeMin OBJECT-TYPE
        SYNTAX      Unsigned32 ( 1 .. 4294967295)
        MAX-ACCESS  read-write
        STATUS      current
        DESCRIPTION
            "This object defines the minimum value of the range of SFID
             values allocated for the BS sector for the purpose of
             autonomous creation of service flows. This value is used
             when the object wmanIfBsAutoSfidEnabled allows
             autonomous creation of SFIDs."
        REFERENCE
            "Subclause 11.13.1 in IEEE 802.16-2004"
        ::= { wmanIfBsConfigurationEntry 18 }

wmanIfBsAutoSfidRangeMax OBJECT-TYPE
        SYNTAX      Unsigned32 ( 1 .. 4294967295)
        MAX-ACCESS  read-write
        STATUS      current
        DESCRIPTION
            "This object defines the maximum value of the range of SFID
             values allocated for the BS sector for the purpose of
             autonomous creation of the service flows. This value is
             used when the object wmanIfBsAutoSfidEnabled allows
             autonomous creation of SFIDs."
        REFERENCE
            "Subclause 11.13.1 in IEEE 802.16-2004"
        ::= { wmanIfBsConfigurationEntry 19 }

wmanIfBsAasChanFbckReqFreq OBJECT-TYPE
        SYNTAX      INTEGER (5..10000)
        UNITS       "ms"
        MAX-ACCESS  read-write
        STATUS      current
        DESCRIPTION
            "This object defines AAS channel feedback request frequency.
             It controls the frequency of downlink beam measurements.
             The relevant MAC messages are AAS-FBCK-REQ/RSP"
        REFERENCE
            "Subclause 6.3.2.3.40 in IEEE 802.16-2004"
        ::= { wmanIfBsConfigurationEntry 20 }

wmanIfBsAasBeamSelectFreq OBJECT-TYPE
        SYNTAX      INTEGER (5..10000)
        UNITS       "ms"
        MAX-ACCESS  read-write
        STATUS      current
        DESCRIPTION
            "This object defines AAS beam select frequency.
             It controls how often SS issues beam select messages.
             The relevant MAC message is AAS_Beam_Select"
        REFERENCE
            "Subclause 6.3.2.3.41 in IEEE 802.16-2004"
        ::= { wmanIfBsConfigurationEntry 21 }

wmanIfBsAasChanFbckReqResolution OBJECT-TYPE
        SYNTAX      INTEGER {aasChanFbckRes00(0),
                             aasChanFbckRes01(1),
                             aasChanFbckRes10(2),
                             aasChanFbckRes11(3)}
        MAX-ACCESS  read-write
        STATUS      current
        DESCRIPTION
            "This object defines AAS feedback request frequency
             measurements resolution. It is coded as follows:
             aasChanFbckRes00 - every 4th carrier
                                (-100, -96, -92, .., 100)
             aasChanFbckRes01 - every 8th carrier
                                (-100, -92, -84, .., 100)
             aasChanFbckRes10 - every 16th carrier
                                (-100, -84, -68, .., 100)
             aasChanFbckRes11 - every 32th carrier
                                (-100, -68, -36, .., 100)"
        REFERENCE
            "Subclause 8.3.6.4 in IEEE 802.16-2004"
        ::= { wmanIfBsConfigurationEntry 22 }

wmanIfBsAasBeamReqResolution OBJECT-TYPE
        SYNTAX      INTEGER {aasBeamReqRes000(0),
                             aasBeamReqRes001(1),
                             aasBeamReqRes010(2),
                             aasBeamReqRes011(3),
                             aasBeamReqRes100(4)}
        MAX-ACCESS  read-write
        STATUS      current
        DESCRIPTION
            "This object defines AAS beam select request resolution
             parameter. It is coded as follows:
             aasBeamReqRes000 - every 4th carrier
             aasBeamReqRes001 - every 8th carrier
             aasBeamReqRes010 - every 16th carrier
             aasBeamReqRes011 - every 32th carrier
             aasBeamReqRes100 - every 64th carrier"
        REFERENCE
            "Subclause 8.3.6.5 in IEEE 802.16-2004"
        ::= { wmanIfBsConfigurationEntry 23 }

wmanIfBsAasNumOptDiversityZones OBJECT-TYPE
        SYNTAX      INTEGER (0..65535)
        MAX-ACCESS  read-write
        STATUS      current
        DESCRIPTION
            "This object defines the number of optional diversity zones
             transmitted in downlink."
        REFERENCE
            "Figure 209 in IEEE 802.16-2004"
        ::= { wmanIfBsConfigurationEntry 24 }

wmanIfBsResetSector  OBJECT-TYPE
        SYNTAX      INTEGER {actionResetSectorNoAction(0),
                             actionResetSector(1)}
        MAX-ACCESS  read-write
        STATUS      current
        DESCRIPTION 
            "This object should be implemented as follows:
             - When set to actionsResetSector value, instructs BS to
               reset the sector identified by ifIndex. As a result of
               this action the Phy and Mac of this sector should be
               reinitialised.
             - When set to value different than actionsResetSector it
               should be ignored
             - When read it should return actionsResetSectorNoAction"
        ::= { wmanIfBsConfigurationEntry 25 }
                
--
-- Base Station Channel Measurement Table
--         
wmanIfBsChannelMeasurementTable OBJECT-TYPE
        SYNTAX      SEQUENCE OF   WmanIfBsChannelMeasurementEntry
        MAX-ACCESS  not-accessible
        STATUS      current
        DESCRIPTION
            "This table contains channel measurement information as
             derived from BS measurement of uplink signal from SS,
             and the downlink signal as reported from SS using
             REP-REQ/RSP messages. The table shall be maintained as
             FIFO to store measurement samples that can be used to
             create RSSI and CINR histogram report. When the
             measurement entry for a SS reaches the limit, the oldest
             entry shall be deleted as the new entry is added to the
             table."
        REFERENCE
            "6.3.2.3.33 in IEEE 802.16-2004"
        ::= { wmanIfBsCps 3 }

wmanIfBsChannelMeasurementEntry OBJECT-TYPE
        SYNTAX      WmanIfBsChannelMeasurementEntry
        MAX-ACCESS  not-accessible
        STATUS      current
        DESCRIPTION
            "Each entry in the table contains RSSI and CINR
             signal quality measurement on signal received from the SS.
             The primary index is the ifIndex with ifType of propBWAp2Mp
             identifing the BS sector. wmanIfBsSsMacAddress identifies
             the SS from which the signal was received.
             wmanIfBsChannelDirection is the index to the direction of
             the channel. wmanIfBsHistogramIndex is the index to
             histogram samples. Since there is no time stamp in the
             table, wmanIfBsHistogramIndex should be increased
             monotonically, and wraps around when it reaches the
             implementation specific limit."
        INDEX       { ifIndex,
                      wmanIfBsSsMacAddress,
                      wmanIfBsChannelDirection,
                      wmanIfBsHistogramIndex }
        ::= { wmanIfBsChannelMeasurementTable  1 }

WmanIfBsChannelMeasurementEntry ::= SEQUENCE {
        wmanIfBsChannelDirection                INTEGER, 
        wmanIfBsHistogramIndex                  Unsigned32,
        wmanIfBsChannelNumber                   WmanIfChannelNumber,
        wmanIfBsStartFrame                      INTEGER,
        wmanIfBsDuration                        INTEGER,
        wmanIfBsBasicReport                     BITS,
        wmanIfBsMeanCinrReport                  INTEGER,
        wmanIfBsMeanRssiReport                  INTEGER,
        wmanIfBsStdDeviationCinrReport          INTEGER,
        wmanIfBsStdDeviationRssiReport          INTEGER}
               
wmanIfBsChannelDirection OBJECT-TYPE
        SYNTAX      INTEGER {downstream(1),
                             upstream(2)} 
        MAX-ACCESS  not-accessible
        STATUS      current
        DESCRIPTION
            "wmanIfBsChannelDirection identifies the direction of a
             a channel where the measurement takes place."
        ::= { wmanIfBsChannelMeasurementEntry 1 }

wmanIfBsHistogramIndex OBJECT-TYPE
        SYNTAX      Unsigned32 (1 .. 4294967295) 
        MAX-ACCESS  read-only
        STATUS      current
        DESCRIPTION
            "wmanIfBsHistogramIndex identifies the histogram samples
             in the table for each subscriber station."
        ::= { wmanIfBsChannelMeasurementEntry 2 }
                 
wmanIfBsChannelNumber OBJECT-TYPE
        SYNTAX      WmanIfChannelNumber 
        MAX-ACCESS  read-only
        STATUS      current
        DESCRIPTION
            "Physical channel number to be reported on is only
             applicable to license exempt band. For licensed band,
             this parameter should be null."
        REFERENCE
            "Subclause 11.12 in IEEE 802.16-2004"
        ::= { wmanIfBsChannelMeasurementEntry 3 }
               
wmanIfBsStartFrame OBJECT-TYPE
        SYNTAX      INTEGER (0..65535) 
        MAX-ACCESS  read-only
        STATUS      current
        DESCRIPTION
            "Frame number in which measurement for this channel
             started."
        REFERENCE
            "Subclause 11.12 in IEEE 802.16-2004"
        ::= { wmanIfBsChannelMeasurementEntry 4 }
                
wmanIfBsDuration OBJECT-TYPE
        SYNTAX      INTEGER (0 .. 16777215) 
        MAX-ACCESS  read-only
        STATUS      current
        DESCRIPTION
            "Cumulative measurement duration on the channel in
             multiples of Ts. For any value exceeding 0xFFFFFF,
             report 0xFFFFFF."
        REFERENCE
            "Subclause 11.12 in IEEE 802.16-2004"
        ::= { wmanIfBsChannelMeasurementEntry 5 }
                        
wmanIfBsBasicReport OBJECT-TYPE
        SYNTAX      BITS {wirelessHuman(0),
                          unknownTransmission(1),
                          primaryUser(2),
                          channelNotMeasured(3)}                          
        MAX-ACCESS  read-only
        STATUS      current
        DESCRIPTION
            "Bit #0: WirelessHUMAN detected on the channel
             Bit #1: Unknown transmissions detected on the channel
             Bit #2: Primary User detected on the channel
             Bit #3: Unmeasured. Channel not measured"
        REFERENCE
            "Subclause 11.12 in IEEE 802.16-2004"
        ::= { wmanIfBsChannelMeasurementEntry 6 }                        
                                          
wmanIfBsMeanCinrReport OBJECT-TYPE
        SYNTAX      INTEGER (0 .. 41) 
        UNITS       "dB"
        MAX-ACCESS  read-only
        STATUS      current
        DESCRIPTION
            "Mean CINR report."
        REFERENCE
            "Subclause 8.2.2, 8.3.9 in IEEE 802.16-2004"
        ::= { wmanIfBsChannelMeasurementEntry 7 }
                                          
wmanIfBsMeanRssiReport OBJECT-TYPE
        SYNTAX      INTEGER (0 .. 83)
        UNITS       "dBm" 
        MAX-ACCESS  read-only
        STATUS      current
        DESCRIPTION
            "Mean RSSI report."
        REFERENCE
            "Subclause 8.2.2, 8.3.9 in IEEE 802.16-2004"
        ::= { wmanIfBsChannelMeasurementEntry 8 }
        
wmanIfBsStdDeviationCinrReport OBJECT-TYPE
        SYNTAX      INTEGER (0 .. 41) 
        UNITS       "dB"
        MAX-ACCESS  read-only
        STATUS      current
        DESCRIPTION
             "Standard deviation CINR report."
        REFERENCE
            "Subclause 8.2.2, 8.3.9 in IEEE 802.16-2004"
        ::= { wmanIfBsChannelMeasurementEntry 9 }
                                          
wmanIfBsStdDeviationRssiReport OBJECT-TYPE
        SYNTAX      INTEGER (0 .. 83)
        UNITS       "dB"
        MAX-ACCESS  read-only
        STATUS      current
        DESCRIPTION
             "Standard deviation RSSI report."
        REFERENCE
            "Subclause 8.2.2, 8.3.9 in IEEE 802.16-2004"
        ::= { wmanIfBsChannelMeasurementEntry 10 }
               
--
-- Base Station capabilities
--
wmanIfBsCapabilities OBJECT IDENTIFIER ::= { wmanIfBsCps 4 }

wmanIfBsSsReqCapabilitiesTable OBJECT-TYPE
        SYNTAX      SEQUENCE OF WmanIfBsSsReqCapabilitiesEntry
        MAX-ACCESS  not-accessible
        STATUS      current
        DESCRIPTION
            "This table contains the basic capability information of SSs
             that have been reported by SSs to BS using RNG-REQ, SBC-REQ
             and REG-REQ messages. Entries in this table should be
             created when an SS registers with a BS."
        ::= { wmanIfBsCapabilities 1 }

wmanIfBsSsReqCapabilitiesEntry OBJECT-TYPE
        SYNTAX      WmanIfBsSsReqCapabilitiesEntry
        MAX-ACCESS  not-accessible
        STATUS      current
        DESCRIPTION
            "This table provides one row for each SS that has been
             registered in the BS. This table augments the table 
             wmanIfBsRegisteredSsTable."
        AUGMENTS { wmanIfBsRegisteredSsEntry }
        ::= { wmanIfBsSsReqCapabilitiesTable 1 }

WmanIfBsSsReqCapabilitiesEntry ::= SEQUENCE {        
        wmanIfBsSsReqCapUplinkCidSupport        WmanIfNumOfUplinkCid,
        wmanIfBsSsReqCapArqSupport              WmanIfArqSupportType,
        wmanIfBsSsReqCapDsxFlowControl          WmanIfMaxDsxFlowType,
        wmanIfBsSsReqCapMacCrcSupport           WmanIfMacCrcSupport,
        wmanIfBsSsReqCapMcaFlowControl          WmanIfMaxMcaFlowType,
        wmanIfBsSsReqCapMcpGroupCidSupport      WmanIfMaxMcpGroupCid,
        wmanIfBsSsReqCapPkmFlowControl          WmanIfMaxPkmFlowType,
        wmanIfBsSsReqCapAuthPolicyControl       WmanIfAuthPolicyType,
        wmanIfBsSsReqCapMaxNumOfSupportedSA     WmanIfMaxNumOfSaType,
        wmanIfBsSsReqCapIpVersion               WmanIfIpVersionType,
        wmanIfBsSsReqCapMacCsSupportBitMap      WmanIfMacCsBitMap,
        wmanIfBsSsReqCapMaxNumOfClassifier      WmanIfMaxClassifiers,
        wmanIfBsSsReqCapPhsSupport              WmanIfPhsSupportType,
        wmanIfBsSsReqCapBandwidthAllocSupport   WmanIfBwAllocSupport,
        wmanIfBsSsReqCapPduConstruction         WmanIfPduConstruction,
        wmanIfBsSsReqCapTtgTransitionGap        WmanIfSsTransitionGap,
        wmanIfBsSsReqCapRtgTransitionGap        WmanIfSsTransitionGap}
       
wmanIfBsSsReqCapUplinkCidSupport OBJECT-TYPE
        SYNTAX      WmanIfNumOfUplinkCid
        MAX-ACCESS  read-only
        STATUS      current
        DESCRIPTION 
           "This object shows the number of Uplink CIDs the SS can
            support."
        ::= { wmanIfBsSsReqCapabilitiesEntry 1 }
        
wmanIfBsSsReqCapArqSupport OBJECT-TYPE
        SYNTAX      WmanIfArqSupportType
        MAX-ACCESS  read-only
        STATUS      current
        DESCRIPTION 
            "This object indicates whether the SS supports ARQ."
        ::= { wmanIfBsSsReqCapabilitiesEntry 2 }
        
wmanIfBsSsReqCapDsxFlowControl OBJECT-TYPE
        SYNTAX      WmanIfMaxDsxFlowType
        MAX-ACCESS  read-only
        STATUS      current
        DESCRIPTION
            "This object specifies the maximum number of concurrent
             DSA, DSC, or DSD transactions that SS is capable of having
             outstanding."
        DEFVAL		{ 0 }
        ::= { wmanIfBsSsReqCapabilitiesEntry 3 }
        
wmanIfBsSsReqCapMacCrcSupport OBJECT-TYPE
        SYNTAX      WmanIfMacCrcSupport
        MAX-ACCESS  read-only
        STATUS      current
        DESCRIPTION 
            "This object indicates whether or not the SS supports MAC
             level CRC."
        DEFVAL		{ macCrcSupport }
        ::= { wmanIfBsSsReqCapabilitiesEntry 4 }
        
wmanIfBsSsReqCapMcaFlowControl OBJECT-TYPE
        SYNTAX      WmanIfMaxMcaFlowType
        MAX-ACCESS  read-only
        STATUS      current
        DESCRIPTION
            "This object specifies the maximum number of concurrent MCA
             transactions that SS is capable of having outstanding."
        DEFVAL		{ 0 }
        ::= { wmanIfBsSsReqCapabilitiesEntry 5 }
        
wmanIfBsSsReqCapMcpGroupCidSupport OBJECT-TYPE
        SYNTAX      WmanIfMaxMcpGroupCid
        MAX-ACCESS  read-only
        STATUS      current
        DESCRIPTION
            "This object indicates the maximum number of
             simultaneous Multicast Polling Groups the SS is
             capable of belonging to."
        DEFVAL		{ 0 }    
        ::= { wmanIfBsSsReqCapabilitiesEntry 6 }
        
wmanIfBsSsReqCapPkmFlowControl OBJECT-TYPE
        SYNTAX      WmanIfMaxPkmFlowType
        MAX-ACCESS  read-only
        STATUS      current
        DESCRIPTION
            "This object specifies the maximum number of concurrent PKM
             transactions that SS is capable of having outstanding."
        DEFVAL		{ 0 }
        ::= { wmanIfBsSsReqCapabilitiesEntry 7 }
        
wmanIfBsSsReqCapAuthPolicyControl OBJECT-TYPE
        SYNTAX      WmanIfAuthPolicyType
        MAX-ACCESS  read-only
        STATUS      current
        DESCRIPTION
            "This object specifies authorization policy that SS is
             capable of. A bit value of 0 = not supported,
             1 = supported. If this field is omitted, then both SS and
             BS shall use the IEEE 802.16 security, constituting X.509
             digital certificates and the RSA public key encryption
             algorithm, as authorization policy."
        ::= { wmanIfBsSsReqCapabilitiesEntry 8 }
                
wmanIfBsSsReqCapMaxNumOfSupportedSA OBJECT-TYPE
        SYNTAX      WmanIfMaxNumOfSaType
        MAX-ACCESS  read-only
        STATUS      current
        DESCRIPTION
            "This field specifies the maximum number of supported
             security associations of the SS."
        DEFVAL		{ 1 }
        ::= { wmanIfBsSsReqCapabilitiesEntry 9 }
        
wmanIfBsSsReqCapIpVersion OBJECT-TYPE
        SYNTAX      WmanIfIpVersionType
        MAX-ACCESS  read-only
        STATUS      current
        DESCRIPTION
            "This object indicates the version of IP used on the 2nd
             Management Connection. The value should be undefined
             if the 2nd management CID doesn't exist."
        ::= { wmanIfBsSsReqCapabilitiesEntry 10 }                                                                                

wmanIfBsSsReqCapMacCsSupportBitMap OBJECT-TYPE
        SYNTAX      WmanIfMacCsBitMap
        MAX-ACCESS  read-only
        STATUS      current
        DESCRIPTION
            "This object indicates SS reported set of MAC convergence
             sublayer support. When a bit is set, it indicates
             the corresponding CS feature is supported."
        ::= { wmanIfBsSsReqCapabilitiesEntry 11 }
                                                                                
wmanIfBsSsReqCapMaxNumOfClassifier OBJECT-TYPE
        SYNTAX      WmanIfMaxClassifiers
        MAX-ACCESS  read-only
        STATUS      current
        DESCRIPTION
            "This object indicates the maximum number of admitted
             Classifiers that the SS can support."
        DEFVAL      { 0 }
        ::= { wmanIfBsSsReqCapabilitiesEntry 12 }
                                                                                
wmanIfBsSsReqCapPhsSupport OBJECT-TYPE
        SYNTAX      WmanIfPhsSupportType
        MAX-ACCESS  read-only
        STATUS      current
        DESCRIPTION
            "This object indicates indicates the level of SS support
             for PHS."
        DEFVAL      { noPhsSupport }
        ::= { wmanIfBsSsReqCapabilitiesEntry 13 }
                                                                                
wmanIfBsSsReqCapBandwidthAllocSupport OBJECT-TYPE
        SYNTAX      WmanIfBwAllocSupport
        MAX-ACCESS  read-only
        STATUS      current
        DESCRIPTION
            "This field indicates the bandwidth allocation
             capabilities of the SS. The usage is defined by
             WmanIfBwAllocSupport."
        ::= { wmanIfBsSsReqCapabilitiesEntry 14 }
                                                                        
wmanIfBsSsReqCapPduConstruction OBJECT-TYPE
        SYNTAX      WmanIfPduConstruction
        MAX-ACCESS  read-only
        STATUS      current
        DESCRIPTION
            "This field indicates the SS's capabilities for
             construction and transmission of MAC PDUs. The usage
             is defined by WmanIfPduConstruction."
        ::= { wmanIfBsSsReqCapabilitiesEntry 15 }

wmanIfBsSsReqCapTtgTransitionGap OBJECT-TYPE
        SYNTAX      WmanIfSsTransitionGap
        UNITS       "us"
        MAX-ACCESS  read-only
        STATUS      current
        DESCRIPTION
            "This field indicates the SS's transition speed SSTTG
             for TDD and H-FDD SSs. The usage is defined by
             WmanIfSsTransitionGap."
        ::= { wmanIfBsSsReqCapabilitiesEntry 16 }

wmanIfBsSsReqCapRtgTransitionGap OBJECT-TYPE
        SYNTAX      WmanIfSsTransitionGap
        UNITS       "us"
        MAX-ACCESS  read-only
        STATUS      current
        DESCRIPTION
            "This field indicates the SS's transition speed SSRTG
             for TDD and H-FDD SSs. The usage is defined by
             WmanIfSsTransitionGap."
        ::= { wmanIfBsSsReqCapabilitiesEntry 17 }

wmanIfBsSsRspCapabilitiesTable OBJECT-TYPE
        SYNTAX      SEQUENCE OF WmanIfBsSsRspCapabilitiesEntry
        MAX-ACCESS  not-accessible
        STATUS      current
        DESCRIPTION
            "This table contains the basic capability information of SSs
             that have been negotiated and agreed between BS and SS via
             RNG-REQ/RSP, SBC-REQ/RSP and REG-REQ/RSP messages. 
             This table augments the wmanIfBsRegisteredSsTable."
        REFERENCE
            "Subclause 6.3.2.3.7 in IEEE 802.16-2004"
        ::= { wmanIfBsCapabilities 2 }

wmanIfBsSsRspCapabilitiesEntry OBJECT-TYPE
        SYNTAX      WmanIfBsSsRspCapabilitiesEntry
        MAX-ACCESS  not-accessible
        STATUS      current
        DESCRIPTION
            "This table provides one row for each SS that has been
             registered in the BS. This table augments the
             wmanIfBsRegisteredSsTable. "
        AUGMENTS { wmanIfBsRegisteredSsEntry }
        ::= { wmanIfBsSsRspCapabilitiesTable 1 }

WmanIfBsSsRspCapabilitiesEntry ::= SEQUENCE {        
        wmanIfBsSsRspCapUplinkCidSupport        WmanIfNumOfUplinkCid,
        wmanIfBsSsRspCapArqSupport              WmanIfArqSupportType,
        wmanIfBsSsRspCapDsxFlowControl          WmanIfMaxDsxFlowType,
        wmanIfBsSsRspCapMacCrcSupport           WmanIfMacCrcSupport,
        wmanIfBsSsRspCapMcaFlowControl          WmanIfMaxMcaFlowType,
        wmanIfBsSsRspCapMcpGroupCidSupport      WmanIfMaxMcpGroupCid,
        wmanIfBsSsRspCapPkmFlowControl          WmanIfMaxPkmFlowType,
        wmanIfBsSsRspCapAuthPolicyControl       WmanIfAuthPolicyType,
        wmanIfBsSsRspCapMaxNumOfSupportedSA     WmanIfMaxNumOfSaType,
        wmanIfBsSsRspCapIpVersion               WmanIfIpVersionType,
        wmanIfBsSsRspCapMacCsSupportBitMap      WmanIfMacCsBitMap,
        wmanIfBsSsRspCapMaxNumOfClassifier      WmanIfMaxClassifiers,
        wmanIfBsSsRspCapPhsSupport              WmanIfPhsSupportType,
        wmanIfBsSsRspCapBandwidthAllocSupport   WmanIfBwAllocSupport,
        wmanIfBsSsRspCapPduConstruction         WmanIfPduConstruction,
        wmanIfBsSsRspCapTtgTransitionGap        WmanIfSsTransitionGap,
        wmanIfBsSsRspCapRtgTransitionGap        WmanIfSsTransitionGap}

wmanIfBsSsRspCapUplinkCidSupport OBJECT-TYPE
        SYNTAX      WmanIfNumOfUplinkCid
        MAX-ACCESS  read-only
        STATUS      current
        DESCRIPTION
            "Negotiated number of Uplink CIDs the SS can support."
        ::= { wmanIfBsSsRspCapabilitiesEntry 1 }
        
wmanIfBsSsRspCapArqSupport OBJECT-TYPE
        SYNTAX      WmanIfArqSupportType
        MAX-ACCESS  read-only
        STATUS      current
        DESCRIPTION
            "This object indicates whether the SS is allowed to use ARQ 
             as a result of the capabilities negotiation."
        ::= { wmanIfBsSsRspCapabilitiesEntry 2 }
        
wmanIfBsSsRspCapDsxFlowControl OBJECT-TYPE
        SYNTAX      WmanIfMaxDsxFlowType
        MAX-ACCESS  read-only
        STATUS      current
        DESCRIPTION 
            "Negotiated maximum number of concurrent DSA, DSC, or DSD
             transactions that may be outstanding."
        ::= { wmanIfBsSsRspCapabilitiesEntry 3 }
        
wmanIfBsSsRspCapMacCrcSupport OBJECT-TYPE
        SYNTAX      WmanIfMacCrcSupport
        MAX-ACCESS  read-only
        STATUS      current
        DESCRIPTION
            "This object indicates whether or not the SS is allowed to
             use MAC level CRC as a result of the capabilities
             negotiation."
        DEFVAL		{ macCrcSupport }
        ::= { wmanIfBsSsRspCapabilitiesEntry 4 }
        
wmanIfBsSsRspCapMcaFlowControl OBJECT-TYPE
        SYNTAX      WmanIfMaxMcaFlowType
        MAX-ACCESS  read-only
        STATUS      current
        DESCRIPTION
            "Negotiated maximum number of concurrent
             MCA transactions that may be outstanding."
        DEFVAL		{ 0 }
        ::= { wmanIfBsSsRspCapabilitiesEntry 5 }
        
wmanIfBsSsRspCapMcpGroupCidSupport OBJECT-TYPE
        SYNTAX      WmanIfMaxMcpGroupCid
        MAX-ACCESS  read-only
        STATUS      current
        DESCRIPTION
            "Negotiated maximum number of simultaneous Multicast
             Polling Groups the SS is capable of belonging to."
        DEFVAL		{ 0 }    
        ::= { wmanIfBsSsRspCapabilitiesEntry 6 }
        
wmanIfBsSsRspCapPkmFlowControl OBJECT-TYPE
        SYNTAX      WmanIfMaxPkmFlowType
        MAX-ACCESS  read-only
        STATUS      current
        DESCRIPTION
            "Negotiated maximum number of concurrent PKM
             transactions that may be outstanding."
        DEFVAL		{ 0 }
        ::= { wmanIfBsSsRspCapabilitiesEntry 7 }
        
wmanIfBsSsRspCapAuthPolicyControl OBJECT-TYPE
        SYNTAX      WmanIfAuthPolicyType
        MAX-ACCESS  read-only
        STATUS      current
        DESCRIPTION
            "This object specifies negotiated authorization policy.
             A bit value of 0 = not supported, 1 = supported. If this
             field is omitted, then both SS and BS shall use the IEEE
             802.16 security, constituting X.509 digital certificates
             and the RSA public key encryption algorithm, as
             authorization policy."
        ::= { wmanIfBsSsRspCapabilitiesEntry 8 }
                
wmanIfBsSsRspCapMaxNumOfSupportedSA OBJECT-TYPE
        SYNTAX      WmanIfMaxNumOfSaType
        MAX-ACCESS  read-only
        STATUS      current
        DESCRIPTION
            "Negotiated maximum number of supported security
             association of the SS."
        DEFVAL		{ 1 }
        ::= { wmanIfBsSsRspCapabilitiesEntry 9 }
        
wmanIfBsSsRspCapIpVersion OBJECT-TYPE
        SYNTAX      WmanIfIpVersionType
        MAX-ACCESS  read-only
        STATUS      current
        DESCRIPTION
            "Negotiated version of IP used on the 2nd Management
             Connection. The value should be undefined if the 2nd
             management CID doesn't exist."
        ::= { wmanIfBsSsRspCapabilitiesEntry 10 }                                                                                

wmanIfBsSsRspCapMacCsSupportBitMap OBJECT-TYPE
        SYNTAX      WmanIfMacCsBitMap
        MAX-ACCESS  read-only
        STATUS      current
        DESCRIPTION
            "Negotiated set of MAC convergence sublayer support.
             When a bit is set, it indicates the corresponding CS
             feature is supported."
        ::= { wmanIfBsSsRspCapabilitiesEntry 11 }
                                                                                
wmanIfBsSsRspCapMaxNumOfClassifier OBJECT-TYPE
        SYNTAX      WmanIfMaxClassifiers
        MAX-ACCESS  read-only
        STATUS      current
        DESCRIPTION
            "Negotiated maximum number of admitted Classifiers
             that the SS is allowed to have."
        DEFVAL      { 0 }
        ::= { wmanIfBsSsRspCapabilitiesEntry 12 }
                                                                                
wmanIfBsSsRspCapPhsSupport OBJECT-TYPE
        SYNTAX      WmanIfPhsSupportType
        MAX-ACCESS  read-only
        STATUS      current
        DESCRIPTION
            "This object indicates the negotiated level of PHS
             support."
        DEFVAL      { noPhsSupport }
        ::= { wmanIfBsSsRspCapabilitiesEntry 13 }
                                                                                
wmanIfBsSsRspCapBandwidthAllocSupport OBJECT-TYPE
        SYNTAX      WmanIfBwAllocSupport
        MAX-ACCESS  read-only
        STATUS      current
        DESCRIPTION
            "This field indicates negotiated properties of the SS 
             for bandwidth allocation purposes. The usage is defined
             by WmanIfCapBandwidthAllocSupportType."
        ::= { wmanIfBsSsRspCapabilitiesEntry 14 }
                                                                        
wmanIfBsSsRspCapPduConstruction OBJECT-TYPE
        SYNTAX      WmanIfPduConstruction
        MAX-ACCESS  read-only
        STATUS      current
        DESCRIPTION
            "Specifies negotiated capabilities for construction and
             transmission of MAC PDUs. The usage is defined by
             WmanIfCapPduConstructionType."
        ::= { wmanIfBsSsRspCapabilitiesEntry 15 }

wmanIfBsSsRspCapTtgTransitionGap OBJECT-TYPE
        SYNTAX      WmanIfSsTransitionGap
        UNITS       "us"
        MAX-ACCESS  read-only
        STATUS      current
        DESCRIPTION
            "This field indicates the negotiated transition speed
             SSTTG for TDD and H-FDD SSs. The usage is defined by
             WmanIfCapSsTransitionGapType."
        ::= { wmanIfBsSsRspCapabilitiesEntry 16 }

wmanIfBsSsRspCapRtgTransitionGap OBJECT-TYPE
        SYNTAX      WmanIfSsTransitionGap
        UNITS       "us"
        MAX-ACCESS  read-only
        STATUS      current
        DESCRIPTION
            "This field indicates the negotiated transition speed
             SSRTG for TDD and H-FDD SSs. The usage is defined by
             WmanIfCapSsTransitionGapType."
        ::= { wmanIfBsSsRspCapabilitiesEntry 17 }

wmanIfBsBasicCapabilitiesTable OBJECT-TYPE
        SYNTAX      SEQUENCE OF WmanIfBsBasicCapabilitiesEntry
        MAX-ACCESS  not-accessible
        STATUS      current
        DESCRIPTION
            "This table contains the basic capabilities of the BS as
             implemented in BS hardware and software. These capabilities
             along with the configuration for them
             (wmanIfBsCapabilitiesConfigTable) are used for negotiation
             of basic capabilities with SS using RNG-RSP, SBC-RSP and
             REG-RSP messages. The negotiated capabilities are obtained
             by interSubclause of SS raw reported capabilities, BS raw
             capabilities and BS configured capabilities. The objects in
             the table have read-only access. The table is maintained
             by BS."
        ::= { wmanIfBsCapabilities 3 }

wmanIfBsBasicCapabilitiesEntry OBJECT-TYPE
        SYNTAX      WmanIfBsBasicCapabilitiesEntry
        MAX-ACCESS  not-accessible
        STATUS      current
        DESCRIPTION
            "This table provides one row for each BS sector and is
             indexed by ifIndex."
        INDEX { ifIndex }
        ::= { wmanIfBsBasicCapabilitiesTable 1 }

WmanIfBsBasicCapabilitiesEntry ::= SEQUENCE {
        wmanIfBsCapUplinkCidSupport             WmanIfNumOfUplinkCid,
        wmanIfBsCapArqSupport                   WmanIfArqSupportType,
        wmanIfBsCapDsxFlowControl               WmanIfMaxDsxFlowType,
        wmanIfBsCapMacCrcSupport                WmanIfMacCrcSupport,
        wmanIfBsCapMcaFlowControl               WmanIfMaxMcaFlowType,
        wmanIfBsCapMcpGroupCidSupport           WmanIfMaxMcpGroupCid,
        wmanIfBsCapPkmFlowControl               WmanIfMaxPkmFlowType,
        wmanIfBsCapAuthPolicyControl            WmanIfAuthPolicyType,
        wmanIfBsCapMaxNumOfSupportedSA          WmanIfMaxNumOfSaType,
        wmanIfBsCapIpVersion                    WmanIfIpVersionType,
        wmanIfBsCapMacCsSupportBitMap           WmanIfMacCsBitMap,
        wmanIfBsCapMaxNumOfClassifier           WmanIfMaxClassifiers,
        wmanIfBsCapPhsSupport                   WmanIfPhsSupportType,
        wmanIfBsCapBandwidthAllocSupport        WmanIfBwAllocSupport,
        wmanIfBsCapPduConstruction              WmanIfPduConstruction,
        wmanIfBsCapTtgTransitionGap             WmanIfSsTransitionGap,
        wmanIfBsCapRtgTransitionGap             WmanIfSsTransitionGap}

wmanIfBsCapUplinkCidSupport OBJECT-TYPE
        SYNTAX      WmanIfNumOfUplinkCid
        MAX-ACCESS  read-only
        STATUS      current
        DESCRIPTION 
            "This object shows the number of Uplink CIDs the BS can
             support per SS."
        ::= { wmanIfBsBasicCapabilitiesEntry 1 }
        
wmanIfBsCapArqSupport OBJECT-TYPE
        SYNTAX      WmanIfArqSupportType
        MAX-ACCESS  read-only
        STATUS      current
        DESCRIPTION 
            "This object indicates whether the BS supports ARQ."
        ::= { wmanIfBsBasicCapabilitiesEntry 2 }
        
wmanIfBsCapDsxFlowControl OBJECT-TYPE
        SYNTAX      WmanIfMaxDsxFlowType
        MAX-ACCESS  read-only
        STATUS      current
        DESCRIPTION
            "This object specifies the maximum number of concurrent
             DSA, DSC, or DSD transactions that BS allows each SS to
             have outstanding."
        DEFVAL		{ 0 }
        ::= { wmanIfBsBasicCapabilitiesEntry 3 }
        
wmanIfBsCapMacCrcSupport OBJECT-TYPE
        SYNTAX      WmanIfMacCrcSupport
        MAX-ACCESS  read-only
        STATUS      current
        DESCRIPTION 
            "This object indicates whether or not the BS supports MAC
             level CRC."
        DEFVAL		{ macCrcSupport }
        ::= { wmanIfBsBasicCapabilitiesEntry 4 }
        
wmanIfBsCapMcaFlowControl OBJECT-TYPE
        SYNTAX      WmanIfMaxMcaFlowType
        MAX-ACCESS  read-only
        STATUS      current
        DESCRIPTION
            "This object specifies the maximum number of concurrent
             MCA transactions that BS allows each SS to have."
        DEFVAL		{ 0 }
        ::= { wmanIfBsBasicCapabilitiesEntry 5 }
        
wmanIfBsCapMcpGroupCidSupport OBJECT-TYPE
        SYNTAX      WmanIfMaxMcpGroupCid
        MAX-ACCESS  read-only
        STATUS      current
        DESCRIPTION
            "This object indicates the maximum number of simultaneous
             Multicast Polling Groups the BS allows each SS to belong
             to."
        DEFVAL		{ 0 }    
        ::= { wmanIfBsBasicCapabilitiesEntry 6 }
        
wmanIfBsCapPkmFlowControl OBJECT-TYPE
        SYNTAX      WmanIfMaxPkmFlowType
        MAX-ACCESS  read-only
        STATUS      current
        DESCRIPTION
            "This object specifies the maximum number of concurrent
             PKM transactions that BS allows each SS to have."
        DEFVAL		{ 0 }
        ::= { wmanIfBsBasicCapabilitiesEntry 7 }
        
wmanIfBsCapAuthPolicyControl OBJECT-TYPE
        SYNTAX      WmanIfAuthPolicyType
        MAX-ACCESS  read-only
        STATUS      current
        DESCRIPTION
            "This object specifies authorization policy that BS is
             capable of. A bit value of 0 = not supported,
             1 = upported. If this field is omitted, then both SS and
             BS shall use the IEEE 802.16 security, constituting X.509
             digital certificates and the RSA public key encryption
             algorithm, as authorization policy."
        ::= { wmanIfBsBasicCapabilitiesEntry 8 }
                
wmanIfBsCapMaxNumOfSupportedSA OBJECT-TYPE
        SYNTAX      WmanIfMaxNumOfSaType
        MAX-ACCESS  read-only
        STATUS      current
        DESCRIPTION
            "This field specifies maximum number of supported security
             associations per SS that the BS allows."
        DEFVAL		{ 1 }
        ::= { wmanIfBsBasicCapabilitiesEntry 9 }
        
wmanIfBsCapIpVersion OBJECT-TYPE
        SYNTAX      WmanIfIpVersionType
        MAX-ACCESS  read-only
        STATUS      current
        DESCRIPTION
            "This object indicates the version of IP BS allows each SS
             to use on the 2nd Management Connection. The value
             'undefined' should not be used for this field."
        REFERENCE
            "Subclause 11.7.4 in IEEE 802.16-2004"
        ::= { wmanIfBsBasicCapabilitiesEntry 10 }                                                                                

wmanIfBsCapMacCsSupportBitMap OBJECT-TYPE
        SYNTAX      WmanIfMacCsBitMap
        MAX-ACCESS  read-only
        STATUS      current
        DESCRIPTION
            "This object indicates BS set of MAC convergence
             sublayer support. When a bit is set, it indicates
             the corresponding CS feature is supported."
        ::= { wmanIfBsBasicCapabilitiesEntry 11 }
                                                                                
wmanIfBsCapMaxNumOfClassifier OBJECT-TYPE
        SYNTAX      WmanIfMaxClassifiers
        MAX-ACCESS  read-only
        STATUS      current
        DESCRIPTION
            "This object indicates the maximum number of admitted
             Classifiers per SS that the BS allows."
        DEFVAL      { 0 }
        ::= { wmanIfBsBasicCapabilitiesEntry 12 }
                                                                                
wmanIfBsCapPhsSupport OBJECT-TYPE
        SYNTAX      WmanIfPhsSupportType
        MAX-ACCESS  read-only
        STATUS      current
        DESCRIPTION
            "This object indicates the level of BS support for PHS.
             The usage is defined by WmanIfPhsSupportType."
        DEFVAL      { noPhsSupport }
        ::= { wmanIfBsBasicCapabilitiesEntry 13 }

wmanIfBsCapBandwidthAllocSupport OBJECT-TYPE
        SYNTAX      WmanIfBwAllocSupport
        MAX-ACCESS  read-only
        STATUS      current
        DESCRIPTION
            "This field indicates the bandwidth allocation properties
             that the BS permits SSs to use. The usage is defined by
             WmanIfCapBandwidthAllocSupportType."
        ::= { wmanIfBsBasicCapabilitiesEntry 14 }
                                                                        
wmanIfBsCapPduConstruction OBJECT-TYPE
        SYNTAX      WmanIfPduConstruction
        MAX-ACCESS  read-only
        STATUS      current
        DESCRIPTION
            "Specifies the capabilities for construction and
             transmission of MAC PDUs allowed by the BS. The usage is
             defined by WmanIfCapPduConstructionType."
        ::= { wmanIfBsBasicCapabilitiesEntry 15 }

wmanIfBsCapTtgTransitionGap OBJECT-TYPE
        SYNTAX      WmanIfSsTransitionGap
        UNITS       "us"
        MAX-ACCESS  read-only
        STATUS      current
        DESCRIPTION
            "This field indicates the transition speed SSTTG for TDD
             and H-FDD SSs allowed by the BS. The usage is defined by
             WmanIfCapTransitionGapType."
        ::= { wmanIfBsBasicCapabilitiesEntry 16 }

wmanIfBsCapRtgTransitionGap OBJECT-TYPE
        SYNTAX      WmanIfSsTransitionGap
        UNITS       "us"
        MAX-ACCESS  read-only
        STATUS      current
        DESCRIPTION
            "This field indicates the transition speed SSRTG for TDD
             and H-FDD SSs allowed by the BS. The usage is defined
             by WmanIfCapTransitionGapType."
        ::= { wmanIfBsBasicCapabilitiesEntry 17 }

wmanIfBsCapabilitiesConfigTable OBJECT-TYPE
        SYNTAX      SEQUENCE OF WmanIfBsCapabilitiesConfigEntry
        MAX-ACCESS  not-accessible
        STATUS      current
        DESCRIPTION                                                     
            "This table contains the configuration for basic
             capabilities of BS. The table is intended to be used to
             restrict the Capabilities implemented by BS, for example in
             order to comply with local regulatory requirements. The BS
             should use the configuration along with the implemented
             Capabilities (wmanIfBsBasicCapabilitiesTable) for
             negotiation of basic capabilities with SS using RNG-RSP,
             SBC-RSP and REG-RSP messages. The negotiated capabilities
             are obtained by interSubclause of SS reported capabilities,
             BS raw capabilities and BS configured capabilities. The
             objects in the table have read-write access. The rows are
             created by BS as a copy of wmanIfBsBasicCapabilitiesTable
             and can be modified by NMS."
        ::= { wmanIfBsCapabilities 4 }

wmanIfBsCapabilitiesConfigEntry OBJECT-TYPE
        SYNTAX      WmanIfBsCapabilitiesConfigEntry
        MAX-ACCESS  not-accessible
        STATUS      current
        DESCRIPTION
            "This table provides one row for each BS sector and is
             indexed by ifIndex."
        INDEX { ifIndex }
        ::= { wmanIfBsCapabilitiesConfigTable 1 }

WmanIfBsCapabilitiesConfigEntry ::= SEQUENCE {
        wmanIfBsCapCfgUplinkCidSupport          WmanIfNumOfUplinkCid,
        wmanIfBsCapCfgArqSupport                WmanIfArqSupportType,
        wmanIfBsCapCfgDsxFlowControl            WmanIfMaxDsxFlowType,
        wmanIfBsCapCfgMacCrcSupport             WmanIfMacCrcSupport,
        wmanIfBsCapCfgMcaFlowControl            WmanIfMaxMcaFlowType,
        wmanIfBsCapCfgMcpGroupCidSupport        WmanIfMaxMcpGroupCid,
        wmanIfBsCapCfgPkmFlowControl            WmanIfMaxPkmFlowType,
        wmanIfBsCapCfgAuthPolicyControl         WmanIfAuthPolicyType,
        wmanIfBsCapCfgMaxNumOfSupportedSA       WmanIfMaxNumOfSaType,
        wmanIfBsCapCfgIpVersion                 WmanIfIpVersionType,
        wmanIfBsCapCfgMacCsSupportBitMap        WmanIfMacCsBitMap,
        wmanIfBsCapCfgMaxNumOfClassifier        WmanIfMaxClassifiers,
        wmanIfBsCapCfgPhsSupport                WmanIfPhsSupportType,
        wmanIfBsCapCfgBandwidthAllocSupport     WmanIfBwAllocSupport,
        wmanIfBsCapCfgPduConstruction           WmanIfPduConstruction,
        wmanIfBsCapCfgTtgTransitionGap          WmanIfSsTransitionGap,
        wmanIfBsCapCfgRtgTransitionGap          WmanIfSsTransitionGap}

wmanIfBsCapCfgUplinkCidSupport OBJECT-TYPE
        SYNTAX      WmanIfNumOfUplinkCid
        MAX-ACCESS  read-write
        STATUS      current
        DESCRIPTION 
            "This object shows the configured number of Uplink CIDs the
             BS can support per SS."
        ::= { wmanIfBsCapabilitiesConfigEntry 1 }
        
wmanIfBsCapCfgArqSupport OBJECT-TYPE
        SYNTAX      WmanIfArqSupportType
        MAX-ACCESS  read-write
        STATUS      current
        DESCRIPTION 
            "This object indicates whether the BS is configured to
             support ARQ."
        ::= { wmanIfBsCapabilitiesConfigEntry 2 }
        
wmanIfBsCapCfgDsxFlowControl OBJECT-TYPE
        SYNTAX      WmanIfMaxDsxFlowType
        MAX-ACCESS  read-write
        STATUS      current
        DESCRIPTION
            "This object specifies the configured maximum number of
             concurrent DSA, DSC, or DSD transactions that BS allows
             each SS to have outstanding."
        DEFVAL		{ 0 }
        ::= { wmanIfBsCapabilitiesConfigEntry 3 }
        
wmanIfBsCapCfgMacCrcSupport OBJECT-TYPE
        SYNTAX      WmanIfMacCrcSupport
        MAX-ACCESS  read-write
        STATUS      current
        DESCRIPTION 
            "This object indicates whether BS is configured to support
             MAC level CRC."
        DEFVAL		{ macCrcSupport }
        ::= { wmanIfBsCapabilitiesConfigEntry 4 }
        
wmanIfBsCapCfgMcaFlowControl OBJECT-TYPE
        SYNTAX      WmanIfMaxMcaFlowType
        MAX-ACCESS  read-write
        STATUS      current
        DESCRIPTION
            "This object specifies the maximum number of concurrent
             MCA transactions that BS is configured to allow each SS to
             have."
        DEFVAL		{ 0 }
        ::= { wmanIfBsCapabilitiesConfigEntry 5 }
        
wmanIfBsCapCfgMcpGroupCidSupport OBJECT-TYPE
        SYNTAX      WmanIfMaxMcpGroupCid
        MAX-ACCESS  read-write
        STATUS      current
        DESCRIPTION
            "This object indicates the maximum number of simultaneous 
             Multicast Polling Groups the BS is configured to allow
             each SS to belong to."
        DEFVAL		{ 0 }    
        ::= { wmanIfBsCapabilitiesConfigEntry 6 }
        
wmanIfBsCapCfgPkmFlowControl OBJECT-TYPE
        SYNTAX      WmanIfMaxPkmFlowType
        MAX-ACCESS  read-write
        STATUS      current
        DESCRIPTION
            "This object specifies the maximum number of concurrent
             PKM transactions that BS is configured to allow each SS
             to have."
        DEFVAL		{ 0 }
        ::= { wmanIfBsCapabilitiesConfigEntry 7 }
        
wmanIfBsCapCfgAuthPolicyControl OBJECT-TYPE
        SYNTAX      WmanIfAuthPolicyType
        MAX-ACCESS  read-write
        STATUS      current
        DESCRIPTION
            "This object specifies authorization policy that BS is
             configured to be capable of. A bit value of 0 = not
             supported, 1 = upported. If this field is omitted, then
             both SS and BS shall use the IEEE 802.16 security,
             constituting X.509 digital certificates and the RSA
             public key encryption algorithm, as authorization policy."
        ::= { wmanIfBsCapabilitiesConfigEntry 8 }
                
wmanIfBsCapCfgMaxNumOfSupportedSA OBJECT-TYPE
        SYNTAX      WmanIfMaxNumOfSaType
        MAX-ACCESS  read-write
        STATUS      current
        DESCRIPTION
            "This field specifies configured maximum number of supported
             security association per SS."
        DEFVAL		{ 1 }
        ::= { wmanIfBsCapabilitiesConfigEntry 9 }
        
wmanIfBsCapCfgIpVersion OBJECT-TYPE
        SYNTAX      WmanIfIpVersionType
        MAX-ACCESS  read-write
        STATUS      current
        DESCRIPTION
            "This object indicates the configured version of IP that the
             BS allows each SS to use on the 2nd Management Connection. 
             The value 'undefined' should not be used in this field."
        ::= { wmanIfBsCapabilitiesConfigEntry 10 }                                                                                

wmanIfBsCapCfgMacCsSupportBitMap OBJECT-TYPE
        SYNTAX      WmanIfMacCsBitMap
        MAX-ACCESS  read-write
        STATUS      current
        DESCRIPTION
            "This object indicates BS configured set of MAC convergence
             sublayer support. When a bit is set, it indicates
             the corresponding CS feature is supported."
        ::= { wmanIfBsCapabilitiesConfigEntry 11 }
                                                                                
wmanIfBsCapCfgMaxNumOfClassifier OBJECT-TYPE
        SYNTAX      WmanIfMaxClassifiers
        MAX-ACCESS  read-write
        STATUS      current
        DESCRIPTION
            "This object indicates the configured maximum number of
             admitted Classifiers per SS that the BS can support."
        DEFVAL      { 0 }
        ::= { wmanIfBsCapabilitiesConfigEntry 12 }
                                                                                
wmanIfBsCapCfgPhsSupport OBJECT-TYPE
        SYNTAX      WmanIfPhsSupportType
        MAX-ACCESS  read-write
        STATUS      current
        DESCRIPTION
            "This object indicates the configured level of BS support
             for PHS."
        DEFVAL      { noPhsSupport }
        ::= { wmanIfBsCapabilitiesConfigEntry 13 }

wmanIfBsCapCfgBandwidthAllocSupport OBJECT-TYPE
        SYNTAX      WmanIfBwAllocSupport
        MAX-ACCESS  read-write
        STATUS      current
        DESCRIPTION
            "This field indicates configured properties of the BS for
             bandwidth allocation purposes. The usage is defined by
             WmanIfCapBandwidthAllocSupportType."
        ::= { wmanIfBsCapabilitiesConfigEntry 14 }
                                                                        
wmanIfBsCapCfgPduConstruction OBJECT-TYPE
        SYNTAX      WmanIfPduConstruction
        MAX-ACCESS  read-write
        STATUS      current
        DESCRIPTION
            "Specifies configured capabilities for construction and
             transmission of MAC PDUs. The usage is defined by
             WmanIfCapPduConstructionType."
        ::= { wmanIfBsCapabilitiesConfigEntry 15 }

wmanIfBsCapCfgTtgTransitionGap OBJECT-TYPE
        SYNTAX      WmanIfSsTransitionGap
        UNITS       "us"
        MAX-ACCESS  read-write
        STATUS      current
        DESCRIPTION
            "This field indicates the configured transition speed
             SSTTG for TDD and H-FDD SSs. The usage is defined by
             WmanIfCapTransitionGapType."
        ::= { wmanIfBsCapabilitiesConfigEntry 16 }

wmanIfBsCapCfgRtgTransitionGap OBJECT-TYPE
        SYNTAX      WmanIfSsTransitionGap
        UNITS       "us"
        MAX-ACCESS  read-write
        STATUS      current
        DESCRIPTION
            "This field indicates the configured transition speed
             SSRTG for TDD and H-FDD SSs. The usage is defined by
             WmanIfCapTransitionGapType."
        ::= { wmanIfBsCapabilitiesConfigEntry 17 }
        
wmanIfBsSsActionsTable OBJECT-TYPE
        SYNTAX      SEQUENCE OF WmanIfBsSsActionsEntry
        MAX-ACCESS  not-accessible
        STATUS      current
        DESCRIPTION
            "This table contains all the actions specified for SSs in
             the standard. The actions are routed down to SS using
             unsolicited MAC messages: REG-RSP, DREG-REQ and RES-CMD.
             The table also contains the parameters of the actions in
             cases where they are specified by the standard."
        ::= { wmanIfBsCps 5 }

wmanIfBsSsActionsEntry OBJECT-TYPE
        SYNTAX      WmanIfBsSsActionsEntry
        MAX-ACCESS  not-accessible
        STATUS      current
        DESCRIPTION
            "This table is indexed by wmanIfBsSsActionsMacAddress. The
             action can be requested for SS in any state not only those
             registered. However BS will decide whether the action is
             applicable to the SS based on its current state and execute
             it or skip it as defined in each action definition."
        INDEX { wmanIfBsSsActionsMacAddress }
        ::= { wmanIfBsSsActionsTable 1 }

WmanIfBsSsActionsEntry ::= SEQUENCE {
        wmanIfBsSsActionsMacAddress             MacAddress,
        wmanIfBsSsActionsResetSs                INTEGER,
        wmanIfBsSsActionsAbortSs                INTEGER,
        wmanIfBsSsActionsOverrideDnFreq         Unsigned32,
        wmanIfBsSsActionsOverrideChannelId      INTEGER,
        wmanIfBsSsActionsDeReRegSs              INTEGER,
        wmanIfBsSsActionsDeReRegSsCode          INTEGER,
        wmanIfBsSsActionsRowStatus              RowStatus}

wmanIfBsSsActionsMacAddress OBJECT-TYPE
        SYNTAX      MacAddress
        MAX-ACCESS  not-accessible
        STATUS      current
        DESCRIPTION
            "This object uniquely identifies the SS as an action
             target."
        ::= { wmanIfBsSsActionsEntry 1 }

wmanIfBsSsActionsResetSs OBJECT-TYPE
        SYNTAX      INTEGER {actionsResetSsNoAction(0),
                             actionsResetSs(1)}
        MAX-ACCESS  read-create
        STATUS      current
        DESCRIPTION
            "This object should be implemented as follows:
             - When set to actionsResetSs value, instructs BS to send
               RES-CMD to SS
             - When set to value different than actionsResetSs it
               should be ignored
             - When read it should return actionsResetSsNoAction
             The RES-CMD message shall be transmitted by the BS on an
             SS Basic CID to force the SS to reset itself,
             reinitialize its MAC, and repeat initial system access."
        REFERENCE
            "Subclause 6.3.2.3.22 in IEEE 802.16-2004"
        ::= { wmanIfBsSsActionsEntry 2 }

wmanIfBsSsActionsAbortSs OBJECT-TYPE
        SYNTAX      INTEGER {actionsAbortSsNoAction(0),
                             actionsAbortSs(1),
                             actionAbortSsParams(2)}

        MAX-ACCESS  read-create
        STATUS      current
        DESCRIPTION
            "This object should be implemented as follows:
             - When set to actionsAbortSs value, it instructs BS to send
               unsolicited RNG-RSP with Ranging Status equal to 'abort'
               without override parameters
             - When set to actionAbortSsParams value, it instructs BS to
               send unsolicited RNG-RSP with Ranging Status equal to
               'abort' and with 'Downlink Frequency Override' and
               'Uplink Channel ID Override' parameters.
             - When set to any other value it should be ignored
             - When read it should returned actionsAbortSsNoAction"
        REFERENCE
            "Subclause 11.6, table 365 in IEEE 802.16-2004"
        ::= { wmanIfBsSsActionsEntry 3 }

wmanIfBsSsActionsOverrideDnFreq OBJECT-TYPE
        SYNTAX      Unsigned32
        UNITS       "kHz"
        MAX-ACCESS  read-create
        STATUS      current
        DESCRIPTION
            "This object is used as a parmeter of the AbortSs action
             with the code actionAbortSsParams. It is used for licensed
             bands only. It defines the Center frequency, in kHz, of
             new downlink channel where the SS should redo initial
             ranging."
        REFERENCE
            "Subclause 11.6, table 365 in IEEE 802.16-2004"
        ::= { wmanIfBsSsActionsEntry 4 }

wmanIfBsSsActionsOverrideChannelId OBJECT-TYPE
        SYNTAX      INTEGER (0..199)
        MAX-ACCESS  read-create
        STATUS      current
        DESCRIPTION
            "This object is used as a parmeter of the AbortSs action
             with the code actionAbortSsParams. It is coded as follows:
             - Licensed bands: The identifier of the uplink channel
               with which the SS is to redo initial ranging (not used
               with PHYs without channelized uplinks).
             - License-exempt bands: The Channel Nr (see 8.5.1) where
               the SS should redo initial ranging."
        REFERENCE
            "Subclause 11.6, table 365 in IEEE 802.16-2004"
        ::= { wmanIfBsSsActionsEntry 5 }

wmanIfBsSsActionsDeReRegSs OBJECT-TYPE
        SYNTAX      INTEGER {actionsDeReRegSsNoAction(0),
                             actionsDeReRegSs(1)}
        MAX-ACCESS  read-create
        STATUS      current
        DESCRIPTION
            "This object should be implemented as follows:
             - When set to actionsDeReRegSs value, instructs BS to
               send DREG-CMD to SS with specified action code
             - When set to value different than actionsDeReRegSs it
               should be ignored
             - When read it should return actionsDeReRegSsNoAction
             The DREG-CMD message shall be transmitted by the BS on an
             SS Basic CID to force the SS to change its access state.
             Upon receiving a DREG-CMD, the SS shall take the action
             indicated by the action code defined by
             wmanIfBsSsActionsDeReRegSsCode."
        REFERENCE
            "Subclause 6.3.2.3.26 in IEEE 802.16-2004"
        ::= { wmanIfBsSsActionsEntry 6 }

wmanIfBsSsActionsDeReRegSsCode OBJECT-TYPE
        SYNTAX      INTEGER {actionsDeReRegSsCodeChangeChan(0),
                             actionsDeReRegSsCodeNoTransmit(1),
                             actionsDeReRegSsCodeLtdTransmit(2),
                             actionsDeReRegSsCodeResume(3)}
        MAX-ACCESS  read-create
        STATUS      current
        DESCRIPTION
            "This object defines the action code for
             wmanIfBsSsActionsDeReRegSs action. The codes are defined
             as follows:
             actionsDeReRegSsCodeChangeChan - SS shall leave the
                 current channel and attempt to access another channel.
             actionsDeReRegSsCodeNoTransmit - SS shall listen to the
                 current channel but shall not transmit until an
                 RES-CMD message or DREG_CMD with an Action Code that
                 allows transmission is received.
             actionsDeReRegSsCodeLtdTransmit - SS shall listen to the
                 current channel but only transmit on the Basic,
                 Primary Management and 2nd Management Connections.
             actionsDeReRegSsCodeResume - SS shall return to normal
                 operation and may transmit on any of its active
                 connections."
        REFERENCE
            "Subclause 6.3.2.3.26, table 55 in IEEE 802.16-2004"
        ::= { wmanIfBsSsActionsEntry 7 }

wmanIfBsSsActionsRowStatus OBJECT-TYPE
        SYNTAX      RowStatus
        MAX-ACCESS  read-create
        STATUS      current
        DESCRIPTION
            "This object is used to ensure that the write operation to
             multiple columns is guaranteed to be treated as atomic
             operation by agent."
        ::= { wmanIfBsSsActionsEntry 8 }
                                             
--
-- Base station PKM group
-- wmanIfBsPkmObjects contain the Base Station Privacy Sublayer objects
--
wmanIfBsPkmObjects OBJECT IDENTIFIER ::= { wmanIfBsObjects  3 }

--
-- Table wmanIfBsPkmBaseTable
--
wmanIfBsPkmBaseTable OBJECT-TYPE
        SYNTAX      SEQUENCE OF   WmanIfBsPkmBaseEntry
        MAX-ACCESS  not-accessible
        STATUS      current
        DESCRIPTION
            "This table describes the basic PKM attributes of each Base
             Station wireless interface."
        ::= { wmanIfBsPkmObjects  1 }

wmanIfBsPkmBaseEntry OBJECT-TYPE
        SYNTAX      WmanIfBsPkmBaseEntry
        MAX-ACCESS  not-accessible
        STATUS      current
        DESCRIPTION
            "Each entry contains objects describing attributes of one
             BS wireless interface."
        INDEX       { ifIndex }
        ::= { wmanIfBsPkmBaseTable  1 }

WmanIfBsPkmBaseEntry ::= SEQUENCE {
        wmanIfBsPkmDefaultAuthLifetime          Integer32,
        wmanIfBsPkmDefaultTekLifetime           Integer32,
        wmanIfBsPkmDefaultSelfSigManufCertTrust INTEGER,
        wmanIfBsPkmCheckCertValidityPeriods     TruthValue,
        wmanIfBsPkmAuthentInfos                 Counter32,
        wmanIfBsPkmAuthRequests                 Counter32,
        wmanIfBsPkmAuthReplies                  Counter32,
        wmanIfBsPkmAuthRejects                  Counter32,
        wmanIfBsPkmAuthInvalids                 Counter32}

wmanIfBsPkmDefaultAuthLifetime OBJECT-TYPE
        SYNTAX      Integer32 (86400..6048000)
        UNITS       "seconds"
        MAX-ACCESS  read-write
        STATUS      current
        DESCRIPTION
            "The value of this object is the default lifetime, in
             seconds, the BS assigns to a new authorization key."
        REFERENCE
             "Table 341 in IEEE 802.16-2004"
        DEFVAL         { 604800 }
        ::= { wmanIfBsPkmBaseEntry 1 }
                                            
wmanIfBsPkmDefaultTekLifetime OBJECT-TYPE
        SYNTAX      Integer32 (1800..604800)
        UNITS       "seconds"
        MAX-ACCESS  read-write
        STATUS      current
        DESCRIPTION
            "The value of this object is the default lifetime, in
             seconds, the BS assigns to a new Traffic Encryption
             Key(TEK)."
        REFERENCE
             "Table 341 in IEEE 802.16-2004"
        DEFVAL         { 43200 }
        ::= { wmanIfBsPkmBaseEntry 2 }


wmanIfBsPkmDefaultSelfSigManufCertTrust OBJECT-TYPE
        SYNTAX      INTEGER {trusted (1),
                             untrusted (2)}
        MAX-ACCESS  read-write
        STATUS      current
        DESCRIPTION
            "This object determines the default trust of all (new)
             self-signed manufacturer certificates obtained after
             setting the object."
        ::= { wmanIfBsPkmBaseEntry 3 }

wmanIfBsPkmCheckCertValidityPeriods OBJECT-TYPE
        SYNTAX      TruthValue 
        MAX-ACCESS  read-write
        STATUS      current
        DESCRIPTION
            "Setting this object to TRUE causes all certificates
             received thereafter to have their validity periods (and
             their chain's validity periods) checked against the current
             time of day. A FALSE setting will cause all certificates
             received Thereafter to not have their validity periods
             (nor their chain's validity periods) checked against the
             current time of day."
        ::= { wmanIfBsPkmBaseEntry 4 }

wmanIfBsPkmAuthentInfos OBJECT-TYPE
        SYNTAX      Counter32 
        MAX-ACCESS  read-only
        STATUS      current
        DESCRIPTION
            "The value of this object is the count of times the BS has
             received an Authentication Information message from any
             SS."
        ::= { wmanIfBsPkmBaseEntry 5 }

wmanIfBsPkmAuthRequests OBJECT-TYPE
        SYNTAX      Counter32 
        MAX-ACCESS  read-only
        STATUS      current
        DESCRIPTION
            "The value of this object is the count of times the BS has
             received an Authorization Request message from any SS"
        ::= { wmanIfBsPkmBaseEntry 6 }

wmanIfBsPkmAuthReplies OBJECT-TYPE
        SYNTAX      Counter32 
        MAX-ACCESS  read-only
        STATUS      current
        DESCRIPTION
            "The value of this object is the count of times the BS has
             transmitted an Authorization Reply message to any SS."
        ::= { wmanIfBsPkmBaseEntry 7 }

wmanIfBsPkmAuthRejects OBJECT-TYPE
        SYNTAX      Counter32 
        MAX-ACCESS  read-only
        STATUS      current
        DESCRIPTION
            "The value of this object is the count of times the BS has
             transmitted an Authorization Reject message to any SS."
        ::= { wmanIfBsPkmBaseEntry 8 }

wmanIfBsPkmAuthInvalids OBJECT-TYPE
        SYNTAX      Counter32 
        MAX-ACCESS  read-only
        STATUS      current
        DESCRIPTION
            "The value of this object is the count of times the BS has
             transmitted an Authorization Invalid message to any SS."
        ::= { wmanIfBsPkmBaseEntry 9 }

--
-- Table wmanIfBsSsPkmAuthTable
--
wmanIfBsSsPkmAuthTable OBJECT-TYPE
        SYNTAX      SEQUENCE OF   WmanIfBsSsPkmAuthEntry
        MAX-ACCESS  not-accessible
        STATUS      current
        DESCRIPTION
            "This table describes PKM attributes related
             to the authorization for each SS. The BS maintains one
             Primary Security Association with each Baseline 
             Privacy-enabled SS on each BS wireless interface."
        ::= { wmanIfBsPkmObjects  2 }

wmanIfBsSsPkmAuthEntry OBJECT-TYPE
        SYNTAX      WmanIfBsSsPkmAuthEntry
        MAX-ACCESS  not-accessible
        STATUS      current
        DESCRIPTION
            "The BS MUST create one entry per SS per wireless
             interface, based on the receipt of an Authorization
             Request message and MUST not delete the entry before
             the SS authorization permanently expires."
        INDEX       { ifIndex, wmanIfBsSsPkmAuthMacAddress }
        ::= { wmanIfBsSsPkmAuthTable  1 }

WmanIfBsSsPkmAuthEntry ::= SEQUENCE {
        wmanIfBsSsPkmAuthMacAddress             MacAddress,
        wmanIfBsSsPkmAuthKeySequenceNumber      Integer32,
        wmanIfBsSsPkmAuthExpiresOld             DateAndTime,
        wmanIfBsSsPkmAuthExpiresNew             DateAndTime,
        wmanIfBsSsPkmAuthLifetime               Integer32,
        wmanIfBsSsPkmAuthReset                  INTEGER,
        wmanIfBsSsPkmAuthInfos                  Counter64,
        wmanIfBsSsPkmAuthRequests               Counter64,
        wmanIfBsSsPkmAuthReplies                Counter64,
        wmanIfBsSsPkmAuthRejects                Counter64,
        wmanIfBsSsPkmAuthInvalids               Counter64,
        wmanIfBsSsPkmAuthRejectErrorCode        INTEGER,
        wmanIfBsSsPkmAuthRejectErrorString      SnmpAdminString,
        wmanIfBsSsPkmAuthInvalidErrorCode       INTEGER,
        wmanIfBsSsPkmAuthInvalidErrorString     SnmpAdminString,
        wmanIfBsSsPkmAuthPrimarySAId            INTEGER,
        wmanIfBsSsPkmAuthValidStatus            INTEGER}

wmanIfBsSsPkmAuthMacAddress OBJECT-TYPE
        SYNTAX      MacAddress 
        MAX-ACCESS  not-accessible
        STATUS      current
        DESCRIPTION
            "The value of this object is the physical address of the SS
             to which the authorization association applies."
        ::= { wmanIfBsSsPkmAuthEntry 1 }

wmanIfBsSsPkmAuthKeySequenceNumber OBJECT-TYPE
        SYNTAX      Integer32 (0..15)
        MAX-ACCESS  read-only
        STATUS      current
        DESCRIPTION
            "The value of this object is the most recent authorization
             key sequence number for this SS."
        ::= { wmanIfBsSsPkmAuthEntry 2 }

wmanIfBsSsPkmAuthExpiresOld OBJECT-TYPE
        SYNTAX      DateAndTime 
        MAX-ACCESS  read-only
        STATUS      current
        DESCRIPTION
            "The value of this object is the actual clock time for
             expiration of the immediate predecessor of the most recent
             authorization key for this FSM. If this FSM has only one
             authorization key, then the value is the time of activation
             of this FSM."
        ::= { wmanIfBsSsPkmAuthEntry 3 }

wmanIfBsSsPkmAuthExpiresNew OBJECT-TYPE
        SYNTAX      DateAndTime 
        MAX-ACCESS  read-only
        STATUS      current
        DESCRIPTION
            "The value of this object is the actual clock time for
             expiration of the most recent authorization key for this
             FSM"
        ::= { wmanIfBsSsPkmAuthEntry 4 }

wmanIfBsSsPkmAuthLifetime OBJECT-TYPE
        SYNTAX      Integer32 (86400..6048000)
        UNITS       "seconds"
        MAX-ACCESS  read-only
        STATUS      current
        DESCRIPTION
            "The vaue of this object is the lifetime, in seconds, the
             BS assigns to an authorization key for this SS."
        REFERENCE
             "Table 341 in IEEE 802.16-2004"
        DEFVAL      { 604800 }
        ::= { wmanIfBsSsPkmAuthEntry 5 }

wmanIfBsSsPkmAuthReset OBJECT-TYPE
        SYNTAX      INTEGER {noResetRequested(1),
                             invalidateAuth(2),
                             sendAuthInvalid(3),
                             invalidateTeks(4)}
        MAX-ACCESS  read-write
        STATUS      current
        DESCRIPTION
            "Setting this object to invalidateAuth(2) causes the BS to
             invalidate the current SS authorization key(s), but not to
             transmit an Authorization Invalid message nor to invalidate
             unicast TEKs. Setting this object to sendAuthInvalid(3)
             causes the BS to invalidate the current SS authorization
             key(s), and to transmit an Authorization Invalid message to
             the SS, but not to invalidate unicast TEKs. Setting this
             object to invalidateTeks(4) causes the BS to invalidate the
             current SS authorization key(s), to transmit an
             Authorization Invalid message to the SS, and to
             invalidate all unicast TEKs associated with this SS
             authorization. Reading this object returns the 
             most-recently-set value of this object, or returns
             noResetRequested(1) if the object has not been set since
             the last BS reboot."
        ::= { wmanIfBsSsPkmAuthEntry 6 }

wmanIfBsSsPkmAuthInfos OBJECT-TYPE
        SYNTAX      Counter64 
        MAX-ACCESS  read-only
        STATUS      current
        DESCRIPTION
            "The value of this object is the count of times the BS has
             received an Authentication Information message from this 
             SS."
        ::= { wmanIfBsSsPkmAuthEntry 7 }

wmanIfBsSsPkmAuthRequests OBJECT-TYPE
        SYNTAX      Counter64 
        MAX-ACCESS  read-only
        STATUS      current
        DESCRIPTION
            "The value of this object is the count of times the BS has
             received an Authorization Request message from this SS."
        ::= { wmanIfBsSsPkmAuthEntry 8 }

wmanIfBsSsPkmAuthReplies OBJECT-TYPE
        SYNTAX      Counter64 
        MAX-ACCESS  read-only
        STATUS      current
        DESCRIPTION
            "The value of this object is the count of times the BS has
             transmitted an Authorization Reply message to this SS."
        ::= { wmanIfBsSsPkmAuthEntry 9 }

wmanIfBsSsPkmAuthRejects OBJECT-TYPE
        SYNTAX      Counter64 
        MAX-ACCESS  read-only
        STATUS      current
        DESCRIPTION
            "The value of this object is the count of times the BS has
             transmitted an Authorization Reject message to this SS."
        ::= { wmanIfBsSsPkmAuthEntry 10 }

wmanIfBsSsPkmAuthInvalids OBJECT-TYPE
        SYNTAX      Counter64 
        MAX-ACCESS  read-only
        STATUS      current
        DESCRIPTION
            "The value of this object is the count of times the BS has
             transmitted an Authorization Invalid message to this SS."
        ::= { wmanIfBsSsPkmAuthEntry 11 }

wmanIfBsSsPkmAuthRejectErrorCode OBJECT-TYPE
        SYNTAX      INTEGER {noInformation(0),
                             unauthorizedSs(1),
                             unauthorizedSaid(2),
                             permanentAuthorizationFailure(6)}
        MAX-ACCESS  read-only
        STATUS      current
        DESCRIPTION
            "The value of this object is the enumerated description of
             the Error-Code in most recent Authorization Reject message
             transmitted to the SS."
        REFERENCE
             "IEEE 802.16-2004; Table 371"
        ::= { wmanIfBsSsPkmAuthEntry 12 }

wmanIfBsSsPkmAuthRejectErrorString OBJECT-TYPE
        SYNTAX      SnmpAdminString (SIZE (0..128))
        MAX-ACCESS  read-only
        STATUS      current
        DESCRIPTION
            "The value of this object is the Display-String in most
             recent Authorization Reject message transmitted to the SS.
             This is a zero length string if no Authorization Reject
             message has been transmitted to the SS."
        ::= { wmanIfBsSsPkmAuthEntry 13 }

wmanIfBsSsPkmAuthInvalidErrorCode OBJECT-TYPE
        SYNTAX      INTEGER {noInformation(0),
                             unauthorizedSs(1),
                             unsolicited(3),
                             invalidKeySequence(4),
                             keyRequestAuthenticationFailure(5)}
        MAX-ACCESS  read-only
        STATUS      current
        DESCRIPTION 
            "The value of this object is the enumerated description of
             the Error-Code in most recent Authorization Invalid message
             transmitted to the SS."
        REFERENCE
             "IEEE 802.16-2004; Table 371"
        ::= { wmanIfBsSsPkmAuthEntry 14 }

wmanIfBsSsPkmAuthInvalidErrorString OBJECT-TYPE
        SYNTAX      SnmpAdminString (SIZE (0..128))
        MAX-ACCESS  read-only
        STATUS      current
        DESCRIPTION
            "The value of this object is the Display-String in most
             recent Authorization Invalid message transmitted to the SS.
             This is a zero length string if no Authorization Invalid
             message has been transmitted to the SS."
        ::= { wmanIfBsSsPkmAuthEntry 15 }

wmanIfBsSsPkmAuthPrimarySAId OBJECT-TYPE
        SYNTAX      INTEGER (0..65535)
        MAX-ACCESS  read-only
        STATUS      current
        DESCRIPTION
            "The value of this object is the Primary Security
             Association identifier."             
        REFERENCE
             "IEEE 802.16-2004; 11.9.7"
        ::= { wmanIfBsSsPkmAuthEntry 16 }

wmanIfBsSsPkmAuthValidStatus OBJECT-TYPE
        SYNTAX      INTEGER {unknown (0),
                             validSsChained (1),
                             validSsTrusted (2),
                             invalidSsUntrusted (3),
                             invalidCAUntrusted (4),
                             invalidSsOther (5),
                             invalidCAOther (6)}
        MAX-ACCESS  read-only
        STATUS      current
        DESCRIPTION
            "Contains the reason why a SS's certificate is deemed valid
             or invalid. Return unknown if the SS is running PKM mode.
             ValidSsChained means the certificate is valid because it
             chains to a valid certificate. ValidSsTrusted means the
             certificate is valid because it has been provisioned to be
             trusted. InvalidSsUntrusted means the certificate is
             invalid because it has been provisioned to be untrusted.
             InvalidCAUntrusted means the certificate is invalid
             because   it chains to an untrusted certificate.
             InvalidSsOther and InvalidCAOther refer to errors in
             parsing, validity periods, etc, which are attributable to
             the SS certificate or its chain respectively."
        ::= { wmanIfBsSsPkmAuthEntry 17 }

--
-- Table wmanIfBsPkmTekTable
--
wmanIfBsPkmTekTable OBJECT-TYPE
        SYNTAX      SEQUENCE OF   WmanIfBsPkmTekEntry
        MAX-ACCESS  not-accessible
        STATUS      current
        DESCRIPTION 
            "This table describes the attributes of each Traffic
             Encryption Key (TEK) association. The BS maintains one TEK
             association per SAID on each BS wireless interface."
        ::= { wmanIfBsPkmObjects  3 }

wmanIfBsPkmTekEntry OBJECT-TYPE
        SYNTAX      WmanIfBsPkmTekEntry
        MAX-ACCESS  not-accessible
        STATUS      current
        DESCRIPTION
            "Each entry contains objects describing attributes of one
             TEK association on a particular BS wireless interface. The
             BS MUST create one entry per SAID per wireless interface,
             based on the receipt of a Key Request message, and MUST not
             delete the entry before the SS authorization for the SAID
             permanently expires."
        INDEX       { ifIndex, wmanIfBsPkmTekSAId }
        ::= { wmanIfBsPkmTekTable  1 }

WmanIfBsPkmTekEntry ::= SEQUENCE {
        wmanIfBsPkmTekSAId                      INTEGER,
        wmanIfBsPkmTekSAType                    INTEGER,
        wmanIfBsPkmTekDataEncryptAlg            WmanIfDataEncryptAlgId,
        wmanIfBsPkmTekDataAuthentAlg            WmanIfDataAuthAlgId,
        wmanIfBsPkmTekEncryptAlg                WmanIfTekEncryptAlgId,
        wmanIfBsPkmTekLifetime                  Integer32,
        wmanIfBsPkmTekKeySequenceNumber         Integer32,
        wmanIfBsPkmTekExpiresOld                DateAndTime,
        wmanIfBsPkmTekExpiresNew                DateAndTime,
        wmanIfBsPkmTekReset                     TruthValue,
        wmanIfBsPkmKeyRequests                  Counter32,
        wmanIfBsPkmKeyReplies                   Counter32,
        wmanIfBsPkmKeyRejects                   Counter32,
        wmanIfBsPkmTekInvalids                  Counter32,
        wmanIfBsPkmKeyRejectErrorCode           INTEGER,
        wmanIfBsPkmKeyRejectErrorString         SnmpAdminString,
        wmanIfBsPkmTekInvalidErrorCode          INTEGER,
        wmanIfBsPkmTekInvalidErrorString        SnmpAdminString}
        
wmanIfBsPkmTekSAId OBJECT-TYPE
        SYNTAX      INTEGER (0..65535) 
        MAX-ACCESS  not-accessible
        STATUS      current
        DESCRIPTION
            "The value of this object is the Security Association
             ID (SAID)."
        REFERENCE
             "IEEE 802.16-2004; 11.9.7"
        ::= { wmanIfBsPkmTekEntry 1 }

wmanIfBsPkmTekSAType OBJECT-TYPE
        SYNTAX      INTEGER {primarySA(0),
                             staticSA(1),
                             dynamicSA(2)}
        MAX-ACCESS  read-only
        STATUS      current
        DESCRIPTION
            "The value of this object is the type of security
             association. Dynamic does not apply to SSs running in PKM
             mode."
        REFERENCE
             "IEEE 802.16-2004; 11.9.18"             
        ::= { wmanIfBsPkmTekEntry 2 }

wmanIfBsPkmTekDataEncryptAlg OBJECT-TYPE
        SYNTAX      WmanIfDataEncryptAlgId
        MAX-ACCESS  read-only
        STATUS      current
        DESCRIPTION
            "The value of this object is the data encryption algorithm
             being utilized."
        REFERENCE
             "Table 375, IEEE 802.16-2004"
        ::= { wmanIfBsPkmTekEntry 3 }

wmanIfBsPkmTekDataAuthentAlg OBJECT-TYPE
        SYNTAX      WmanIfDataAuthAlgId
        MAX-ACCESS  read-only
        STATUS      current
        DESCRIPTION
            "The value of this object is the data authentication
             algorithm being utilized."
        REFERENCE
             "Table 376, IEEE 802.16-2004"
        ::= { wmanIfBsPkmTekEntry 4 }

wmanIfBsPkmTekEncryptAlg OBJECT-TYPE
        SYNTAX      WmanIfTekEncryptAlgId
        MAX-ACCESS  read-only
        STATUS      current
        DESCRIPTION
            "The value of this object is the TEK key encryption
             algorithm being utilized."
        REFERENCE
             "Table 377, IEEE 802.16-2004"
        ::= { wmanIfBsPkmTekEntry 5 }

wmanIfBsPkmTekLifetime OBJECT-TYPE
        SYNTAX      Integer32 (1800..604800)
        UNITS       "seconds"
        MAX-ACCESS  read-only
        STATUS      current
        DESCRIPTION
            "The value of this object is the lifetime, in seconds, the
             BS assigns to keys for this TEK association."
        REFERENCE
             "Table 341 in IEEE 802.16-2004"
        DEFVAL      { 43200 }
        ::= { wmanIfBsPkmTekEntry 6 }

wmanIfBsPkmTekKeySequenceNumber OBJECT-TYPE
        SYNTAX      Integer32 (0..3)
        MAX-ACCESS  read-only
        STATUS      current
        DESCRIPTION 
            "The value of this object is the most recent TEK key
             sequence number for this SAID."
        REFERENCE
             "IEEE 802.16-2004; 11.9.5"
        ::= { wmanIfBsPkmTekEntry 7 }

wmanIfBsPkmTekExpiresOld OBJECT-TYPE
        SYNTAX      DateAndTime 
        MAX-ACCESS  read-only
        STATUS      current
        DESCRIPTION
            "The value of this object is the actual clock time for
             expiration of the immediate predecessor of the most recent
             TEK for this FSM. If this FSM has only one TEK, then the
             value is the time of activation of this FSM."
        ::= { wmanIfBsPkmTekEntry 8 }

wmanIfBsPkmTekExpiresNew OBJECT-TYPE
        SYNTAX      DateAndTime 
        MAX-ACCESS  read-only
        STATUS      current
        DESCRIPTION
            "The value of this object is the actual clock time for
             expiration of the most recent TEK for this FSM."
        ::= { wmanIfBsPkmTekEntry 9 }

wmanIfBsPkmTekReset OBJECT-TYPE
        SYNTAX      TruthValue 
        MAX-ACCESS  read-write
        STATUS      current
        DESCRIPTION
            "Setting this object to TRUE causes the BS to invalidate
             the current active TEK(s) (plural due to key transition
             periods), and to generate a new TEK for the associated
             SAID; the BS MAY also generate an unsolicited TEK Invalid
             message, to optimize the TEK synchronization between the BS
             and the SS. Reading this object always returns   FALSE."
        ::= { wmanIfBsPkmTekEntry 10 }

wmanIfBsPkmKeyRequests OBJECT-TYPE
        SYNTAX      Counter32 
        MAX-ACCESS  read-only
        STATUS      current
        DESCRIPTION 
            "The value of this object is the count of times the BS has
             received a Key Request message."
        ::= { wmanIfBsPkmTekEntry 11 }

wmanIfBsPkmKeyReplies OBJECT-TYPE
        SYNTAX      Counter32 
        MAX-ACCESS  read-only
        STATUS      current
        DESCRIPTION
            "The value of this object is the count of times the BS has
             transmitted a Key Reply message."
        ::= { wmanIfBsPkmTekEntry 12 }

wmanIfBsPkmKeyRejects OBJECT-TYPE
        SYNTAX      Counter32 
        MAX-ACCESS  read-only
        STATUS      current
        DESCRIPTION
            "The value of this object is the count of times the BS has
             transmitted a Key Reject message."
        ::= { wmanIfBsPkmTekEntry 13 }

wmanIfBsPkmTekInvalids OBJECT-TYPE
        SYNTAX      Counter32 
        MAX-ACCESS  read-only
        STATUS      current
        DESCRIPTION
            "The value of this object is the count of times the BS has
             transmitted a TEK Invalid message."
        ::= { wmanIfBsPkmTekEntry 14 }

wmanIfBsPkmKeyRejectErrorCode OBJECT-TYPE
        SYNTAX      INTEGER {noInformation(0),
                             unauthorizedSaid(2)}
        MAX-ACCESS  read-only
        STATUS      current
        DESCRIPTION
            "The value of this object is the enumerated; description of
             the Error-Code in the most recent Key Reject message sent
             in response to a Key Request for this SAID."
        REFERENCE
             "IEEE 802.16-2004; Table 371"
        ::= { wmanIfBsPkmTekEntry 15 }

wmanIfBsPkmKeyRejectErrorString OBJECT-TYPE
        SYNTAX      SnmpAdminString (SIZE (0..128))
        MAX-ACCESS  read-only
        STATUS      current
        DESCRIPTION
            "The value of this object is the Display-String in the most
             recent Key Reject message sent in response to a Key Request
             for this SAID. This is a zero length string if no Key
             Reject message has been received since reboot."
        ::= { wmanIfBsPkmTekEntry 16 }

wmanIfBsPkmTekInvalidErrorCode OBJECT-TYPE
        SYNTAX      INTEGER  {noInformation(0),
                              invalidKeySequence(4)}
        MAX-ACCESS  read-only
        STATUS      current
        DESCRIPTION 
            "The value of this object is the enumerated description of
             the Error-Code in the most recent TEK Invalid message sent
             in association with this SAID."
        REFERENCE
             "IEEE 802.16-2004; Table 371"
        ::= { wmanIfBsPkmTekEntry 17 }

wmanIfBsPkmTekInvalidErrorString OBJECT-TYPE
        SYNTAX      SnmpAdminString (SIZE (0..128))
        MAX-ACCESS  read-only
        STATUS      current
        DESCRIPTION
            "The value of this object is the Display-String in the most
             recent TEK Invalid message sent in association with this
             SAID.  This is a zero length string if no TEK Invalid
             message has been received since reboot."
        ::= { wmanIfBsPkmTekEntry 18 }

--
-- Base station Notification Group
-- wmanIfBsNotificationObjects contains the BS SNMP Trap objects
--
wmanIfBsNotification OBJECT IDENTIFIER ::= { wmanIfBsObjects  4 }
wmanIfBsTrapControl     OBJECT IDENTIFIER ::= { wmanIfBsNotification 1 }
wmanIfBsTrapDefinitions OBJECT IDENTIFIER ::= { wmanIfBsNotification 2 }

-- This object groups all NOTIFICATION-TYPE objects for BS. 
-- It is defined following RFC2758 sections 8.5 and 8.6 
-- for the compatibility with SNMPv1.
wmanIfBsTrapPrefix OBJECT IDENTIFIER ::= { wmanIfBsTrapDefinitions 0 }
	
wmanIfBsTrapControlRegister    OBJECT-TYPE
        SYNTAX      BITS {wmanIfBsSsStatusNotification    (0),
                          wmanIfBsSsDynamicServiceFail    (1),
                          wmanIfBsSsRssiStatusChange      (2),
                          wmanIfBsSsRegistrer             (3),
                          wmanIfBsSsPkmFail               (4)}
        MAX-ACCESS read-write
        STATUS     current
        DESCRIPTION
            "The object is used to enable or disable Base Station traps.
             From left to right, the set bit indicates the corresponding
             Base Station trap is enabled."
        ::= { wmanIfBsTrapControl 1 }

wmanIfBsStatusTrapControlRegister    OBJECT-TYPE
        SYNTAX      BITS {unused(0),
                          ssInitRangingSucc(1),
                          ssInitRangingFail(2),
                          ssRegistered(3),
                          ssRegistrationFail(4),
                          ssDeregistered(5),
                          ssBasicCapabilitySucc(6),
                          ssBasicCapabilityFail(7),
                          ssAuthorizationSucc(8),
                          ssAuthorizationFail(9),
                          tftpSucc(10),
                          tftpFail(11),
                          sfCreationSucc(12),
                          sfCreationFail(13)}
        MAX-ACCESS read-write
        STATUS     current
        DESCRIPTION
            "The object is used to enable or disable Base Station status
             notification traps. The set bit indicates the corresponding
             Base Station trap is enabled."
        ::= { wmanIfBsTrapControl 2 }
        
--
-- BS threshold Definitions
--
wmanIfBsThresholdConfigTable OBJECT-TYPE
        SYNTAX      SEQUENCE OF WmanIfBsThresholdConfigEntry
        MAX-ACCESS  not-accessible
        STATUS      current
        DESCRIPTION
            "This table contains threshold objects that can be set
             to detect the threshold crossing events."
        ::= { wmanIfBsTrapControl 3 }

wmanIfBsThresholdConfigEntry OBJECT-TYPE
        SYNTAX      WmanIfBsThresholdConfigEntry
        MAX-ACCESS  not-accessible
        STATUS      current
        DESCRIPTION
            "This table provides one row for each BS sector, and is
             indexed by ifIndex."
        INDEX       { ifIndex }
        ::= { wmanIfBsThresholdConfigTable 1 }

WmanIfBsThresholdConfigEntry ::= SEQUENCE {        
        wmanIfBsRssiLowThreshold                Integer32,
        wmanIfBsRssiHighThreshold               Integer32}

wmanIfBsRssiLowThreshold OBJECT-TYPE
        SYNTAX      Integer32
        UNITS       "dBm"
        MAX-ACCESS  read-write
        STATUS      current
        DESCRIPTION
        	"Low threshold for generating the RSSI alarm."
        ::= { wmanIfBsThresholdConfigEntry 1 }

wmanIfBsRssiHighThreshold OBJECT-TYPE
        SYNTAX      Integer32
        UNITS       "dBm"
        MAX-ACCESS  read-write
        STATUS      current
        DESCRIPTION
        	"High threshold for clearing the RSSI alarm."
        ::= { wmanIfBsThresholdConfigEntry 2 }

--
-- Subscriber station Notification Objects Definitions
--
wmanIfBsSsNotificationObjectsTable OBJECT-TYPE
        SYNTAX      SEQUENCE OF WmanIfBsSsNotificationObjectsEntry
        MAX-ACCESS  not-accessible
        STATUS      current
        DESCRIPTION
            "This table contains SS notification objects that have been
             reported by the trap."
        ::= { wmanIfBsTrapDefinitions 1 }

wmanIfBsSsNotificationObjectsEntry OBJECT-TYPE
        SYNTAX      WmanIfBsSsNotificationObjectsEntry
        MAX-ACCESS  not-accessible
        STATUS      current
        DESCRIPTION
            "This table provides one row for each SS that has
             generated traps, and is double indexed by
             wmanIfBsSsNotificationMacAddr and ifIndex for BS sector."
        INDEX       { ifIndex, wmanIfBsSsNotificationMacAddr }
        ::= { wmanIfBsSsNotificationObjectsTable 1 }

WmanIfBsSsNotificationObjectsEntry ::= SEQUENCE {        
        wmanIfBsSsNotificationMacAddr           MacAddress,
        wmanIfBsSsStatusValue                   INTEGER,
        wmanIfBsSsStatusInfo                    OCTET STRING,
        wmanIfBsDynamicServiceType              INTEGER,
        wmanIfBsDynamicServiceFailReason        OCTET STRING,
        wmanIfBsSsRssiStatus                    INTEGER,
        wmanIfBsSsRssiStatusInfo                OCTET STRING,
        wmanIfBsSsRegisterStatus                INTEGER}
       
wmanIfBsSsNotificationMacAddr OBJECT-TYPE
        SYNTAX      MacAddress
        MAX-ACCESS  read-only
        STATUS      current
        DESCRIPTION
            "The MAC address of the SS, reporing the notofiation."
        ::= { wmanIfBsSsNotificationObjectsEntry 1 }
        
wmanIfBsSsStatusValue  OBJECT-TYPE
        SYNTAX      INTEGER {ssInitRangingSucc(1),
                             ssInitRangingFail(2),
                             ssRegistered(3),
                             ssRegistrationFail(4),
                             ssDeregistered(5),
                             ssBasicCapabilitySucc(6),
                             ssBasicCapabilityFail(7),
                             ssAuthorizationSucc(8),
                             ssAuthorizationFail(9),
                             tftpSucc(10),
                             tftpFail(11),
                             sfCreationSucc(12),
                             sfCreationFail(13)} 
        MAX-ACCESS  read-only
        STATUS      current
        DESCRIPTION
            "This object indicates the status of a SS, as it goes 
             through network entry and initialization procedure."
        ::= { wmanIfBsSsNotificationObjectsEntry 2 }
                
wmanIfBsSsStatusInfo  OBJECT-TYPE
        SYNTAX      OCTET STRING (SIZE(0..255))
        MAX-ACCESS  read-only
        STATUS      current
        DESCRIPTION
            "This object indicates the reason of SS's status change."
        ::= { wmanIfBsSsNotificationObjectsEntry 3 }
                                     
wmanIfBsDynamicServiceType  OBJECT-TYPE
        SYNTAX      INTEGER {bsSfCreationReq(1),
                             bsSfCreationRsp(2),
                             bsSfCreationAck(3)} 
        MAX-ACCESS  read-only
        STATUS      current
        DESCRIPTION
            "This object indicates the dynamic service flow
             creation command type."
        ::= { wmanIfBsSsNotificationObjectsEntry 4 }
                
wmanIfBsDynamicServiceFailReason  OBJECT-TYPE
        SYNTAX      OCTET STRING (SIZE(0..255))
        MAX-ACCESS  read-only
        STATUS      current
        DESCRIPTION
            "This object indicates the reason why the service flow
             creation has failed."
        ::= { wmanIfBsSsNotificationObjectsEntry 5 }
                                                          
wmanIfBsSsRssiStatus  OBJECT-TYPE
        SYNTAX      INTEGER {bsRssiAlarm(1),
                             bsRssiNoAlarm(2)} 
        MAX-ACCESS  read-only
        STATUS      current
        DESCRIPTION
            "A RSSI alarm is generated when RSSI becomes lower than
             wmanIfBsLowRssiThreshold and is cleared when RSSI becomes
             higher than wmanIfBsLowRssiThreshold."
        ::= { wmanIfBsSsNotificationObjectsEntry 6 }
                
wmanIfBsSsRssiStatusInfo  OBJECT-TYPE
        SYNTAX      OCTET STRING (SIZE(0..255))
        MAX-ACCESS  read-only
        STATUS      current
        DESCRIPTION
            "This object indicates the reason why RSSI alarm is
             generated."
        ::= { wmanIfBsSsNotificationObjectsEntry 7 }

wmanIfBsSsRegisterStatus OBJECT-TYPE
        SYNTAX      INTEGER {ssRegister(1),
                             ssDeregister(2)}
        MAX-ACCESS  read-only
        STATUS      current
        DESCRIPTION
            "This object indicates the status of SS registration."
        ::= { wmanIfBsSsNotificationObjectsEntry 8 }
                                     
--
-- Subscriber station Notification Trap Definitions        
--
wmanIfBsSsStatusNotificationTrap NOTIFICATION-TYPE
        OBJECTS     {ifIndex,
                     wmanIfBsSsNotificationMacAddr,
                     wmanIfBsSsStatusValue,
                     wmanIfBsSsStatusInfo}
        STATUS      current
        DESCRIPTION
            "This trap reports the status of a SS. Based on this
             notification the NMS will issue an alarm with certain
             severity depending on the status and the reason received."
        ::= { wmanIfBsTrapPrefix 1 }

wmanIfBsSsDynamicServiceFailTrap NOTIFICATION-TYPE
        OBJECTS     {ifIndex,
                     wmanIfBsSsNotificationMacAddr,
                     wmanIfBsDynamicServiceType,
                     wmanIfBsDynamicServiceFailReason}
        STATUS      current
        DESCRIPTION
            "An event to report the failure of a dynamic service
             operation happened during the dynamic services process
             and detected in the Bs side."
        ::= { wmanIfBsTrapPrefix 2 }

wmanIfBsSsRssiStatusChangeTrap NOTIFICATION-TYPE
        OBJECTS     {ifIndex,
                     wmanIfBsSsNotificationMacAddr,
                     wmanIfBsSsRssiStatus,
                     wmanIfBsSsRssiStatusInfo}
        STATUS      current
        DESCRIPTION
            "An event to report that the uplink RSSI is below
             wmanIfBsLowRssiThreshold, or above
             wmanIfBsHighRssiThreshold after restore."
        ::= { wmanIfBsTrapPrefix 3 }

wmanIfBsSsPkmFailTrap NOTIFICATION-TYPE
        OBJECTS     {wmanIfBsSsNotificationMacAddr}
        STATUS      current
        DESCRIPTION
            "An event to report the failure of a Pkm operation."
        ::= { wmanIfBsTrapPrefix 4 }

wmanIfBsSsRegistrerTrap NOTIFICATION-TYPE
        OBJECTS     {wmanIfBsSsNotificationMacAddr,
                     wmanIfBsSsRegisterStatus}
        STATUS      current
        DESCRIPTION
            "An event to report SS registration status."
        ::= { wmanIfBsTrapPrefix 5 }
        
--
-- Base station PHY Group 
--
wmanIfBsPhy OBJECT IDENTIFIER ::= { wmanIfBsObjects  6 }

--
-- BS OFDM PHY objects    
--
wmanIfBsOfdmPhy OBJECT IDENTIFIER ::= { wmanIfBsPhy 1 }

wmanIfBsOfdmUplinkChannelTable OBJECT-TYPE
        SYNTAX      SEQUENCE OF WmanIfBsOfdmUplinkChannelEntry
        MAX-ACCESS  not-accessible
        STATUS      current
        DESCRIPTION
            "This table contains UCD channel attributes, defining the
             transmission characteristics of uplink channels"
        REFERENCE
            "Table 349 and table 352, in IEEE 802.16-2004"
        ::= { wmanIfBsOfdmPhy 1 }

wmanIfBsOfdmUplinkChannelEntry OBJECT-TYPE
        SYNTAX      WmanIfBsOfdmUplinkChannelEntry
        MAX-ACCESS  not-accessible
        STATUS      current
        DESCRIPTION
             "This table provides one row for each uplink channel of
              multi-sector BS, and is indexed by BS ifIndex. An entry
              in this table exists for each ifEntry of BS with an
              ifType of propBWAp2Mp."
        INDEX { ifIndex }
        ::= { wmanIfBsOfdmUplinkChannelTable 1 }

WmanIfBsOfdmUplinkChannelEntry ::= SEQUENCE {
        wmanIfBsOfdmCtBasedResvTimeout          INTEGER,
        wmanIfBsOfdmBwReqOppSize                INTEGER,
        wmanIfBsOfdmRangReqOppSize              INTEGER,
        wmanIfBsOfdmUplinkCenterFreq            Unsigned32,
        wmanIfBsOfdmNumSubChReqRegionFull       INTEGER,
        wmanIfBsOfdmNumSymbolsReqRegionFull     INTEGER,
        wmanIfBsOfdmSubChFocusCtCode            INTEGER,
        wmanIfBsOfdmUpLinkChannelId             INTEGER}

wmanIfBsOfdmCtBasedResvTimeout OBJECT-TYPE
        SYNTAX      INTEGER (1..255)
        MAX-ACCESS  read-write
        STATUS      current
        DESCRIPTION
            "The number of UL-MAPs to receive before contention-based
             reservation is attempted again for the same connection."
        REFERENCE
            "Table 349, in IEEE 802.16-2004"
        ::= { wmanIfBsOfdmUplinkChannelEntry 1 }

wmanIfBsOfdmBwReqOppSize OBJECT-TYPE
        SYNTAX      INTEGER (1..65535)
        UNITS       "PS"
        MAX-ACCESS  read-write
        STATUS      current
        DESCRIPTION
            "Size (in units of PS) of PHY payload that SS may use to
             format and transmit a bandwidth request message in a
             contention request opportunity. The value includes all
             PHY overhead as well as allowance for the MAC data the
             message may hold."
        REFERENCE
            "Table 349, in IEEE 802.16-2004"
        ::= { wmanIfBsOfdmUplinkChannelEntry 2 }

wmanIfBsOfdmRangReqOppSize OBJECT-TYPE
        SYNTAX      INTEGER (1..65535)
        UNITS       "PS"
        MAX-ACCESS  read-write
        STATUS      current
        DESCRIPTION
            "Size (in units of PS) of PHY payload that SS may use to
             format and transmit a RNG-REQ message in a contention
             request opportunity. The value includes all PHY overhead
             as well as allowance for the MAC data the message may
             hold and the maxiumum SS/BS roundtrip propagation delay."
        REFERENCE
            "Table 349, in IEEE 802.16-2004"
        ::= { wmanIfBsOfdmUplinkChannelEntry 3 }

wmanIfBsOfdmUplinkCenterFreq OBJECT-TYPE
        SYNTAX      Unsigned32
        UNITS       "kHz"
        MAX-ACCESS  read-write
        STATUS      current
        DESCRIPTION
            " Uplink center frequency (kHz)"
        REFERENCE
            "Table 349, in IEEE 802.16-2004"
        ::= { wmanIfBsOfdmUplinkChannelEntry 4 }
        
wmanIfBsOfdmNumSubChReqRegionFull OBJECT-TYPE
        SYNTAX      INTEGER {oneSubchannel(0),
                             twoSubchannels(1),
                             fourSubchannels(2),
                             eightSubchannels(3),
                             sixteenSubchannels(4)}
        MAX-ACCESS  read-write
        STATUS      current
        DESCRIPTION
            "Number of subchannels used by each transmit
             opportunity when REQ Region-Full is allocated in
             subchannelization region."
        REFERENCE
             "Table 352, in IEEE 802.16-2004"
        ::= { wmanIfBsOfdmUplinkChannelEntry 5 }

wmanIfBsOfdmNumSymbolsReqRegionFull OBJECT-TYPE
        SYNTAX      INTEGER (0..31)
        MAX-ACCESS  read-write
        STATUS      current
        DESCRIPTION
            "Number of OFDM symbols used by each transmit
             opportunity when REQ Region-Full is allocated in
             subchannelization region."
        REFERENCE
             "Table 352, in IEEE 802.16-2004"
        ::= { wmanIfBsOfdmUplinkChannelEntry 6 }

wmanIfBsOfdmSubChFocusCtCode OBJECT-TYPE
        SYNTAX      INTEGER (0..8)
        MAX-ACCESS  read-write
        STATUS      current
        DESCRIPTION
            "Number of contention codes (CSE) that shall only be used to
             request a subchannelized allocation. Default value 0.
             Allowed values 0-8."
        REFERENCE
            "Table 352, in IEEE 802.16-2004"
        DEFVAL         { 0 }
        ::= { wmanIfBsOfdmUplinkChannelEntry 7 }

wmanIfBsOfdmUpLinkChannelId OBJECT-TYPE
        SYNTAX      INTEGER (0..255)
        MAX-ACCESS  read-write
        STATUS      current
        DESCRIPTION
            "The identifier of the uplink channel to which the relevant
             RNG-RSP or RNG-REQ message refers."
        REFERENCE
            "Subclause 6.3.2.3.4. Table 16, in IEEE 802.16-2004"
        ::= { wmanIfBsOfdmUplinkChannelEntry 8 }
        
wmanIfBsOfdmDownlinkChannelTable OBJECT-TYPE
        SYNTAX      SEQUENCE OF WmanIfBsOfdmDownlinkChannelEntry
        MAX-ACCESS  not-accessible
        STATUS      current
        DESCRIPTION
            "This table contains DCD channel attributes, defining the
             transmission characteristics of downlink channels"
        REFERENCE
            "Table 358, in IEEE 802.16-2004"
        ::= { wmanIfBsOfdmPhy 2 }

wmanIfBsOfdmDownlinkChannelEntry OBJECT-TYPE
        SYNTAX      WmanIfBsOfdmDownlinkChannelEntry
        MAX-ACCESS  not-accessible
        STATUS      current
        DESCRIPTION
            "This table provides one row for each downlink channel of
             multi-sector BS, and is indexed by BS ifIndex. An entry
             in this table exists for each ifEntry of BS with an
             ifType of propBWAp2Mp."
        INDEX { ifIndex }
        ::= { wmanIfBsOfdmDownlinkChannelTable 1 }

WmanIfBsOfdmDownlinkChannelEntry ::= SEQUENCE {   
        wmanIfBsOfdmBsEIRP                      INTEGER,
        wmanIfBsOfdmChannelNumber               WmanIfChannelNumber,
        wmanIfBsOfdmTTG                         INTEGER,
        wmanIfBsOfdmRTG                         INTEGER,
        wmanIfBsOfdmInitRngMaxRSS               INTEGER,
        wmanIfBsOfdmDownlinkCenterFreq          Unsigned32,
        wmanIfBsOfdmBsId                        WmanIfBsIdType,
        wmanIfBsOfdmMacVersion                  WmanIfMacVersion,
        wmanIfBsOfdmFrameDurationCode           INTEGER,
        wmanIfBsOfdmDownLinkChannelId           INTEGER}

wmanIfBsOfdmBsEIRP OBJECT-TYPE
        SYNTAX      INTEGER (0..65535)
        UNITS       "dBm"
        MAX-ACCESS  read-write
        STATUS      current
        DESCRIPTION
            "The EIRP is the equivalent isotropic radiated power of
             the base station, which is computed for a simple
             single-antenna transmitter."
        REFERENCE
            "Table 358, in IEEE 802.16-2004"
        ::= { wmanIfBsOfdmDownlinkChannelEntry 1 }

wmanIfBsOfdmChannelNumber OBJECT-TYPE
        SYNTAX      WmanIfChannelNumber
        MAX-ACCESS  read-write
        STATUS      current
        DESCRIPTION
            "Downlink channel number as defined in 8.5.
             Used for license-exempt operation only."
        REFERENCE
            "Table 358, in IEEE 802.16-2004"
        ::= { wmanIfBsOfdmDownlinkChannelEntry 2 }

wmanIfBsOfdmTTG OBJECT-TYPE
        SYNTAX      INTEGER (0..255)
        MAX-ACCESS  read-write
        STATUS      current
        DESCRIPTION
            "Transmit / Receive Transition Gap."
        REFERENCE
            "Table 358, in IEEE 802.16-2004"
        ::= { wmanIfBsOfdmDownlinkChannelEntry 3 }

wmanIfBsOfdmRTG OBJECT-TYPE
        SYNTAX      INTEGER (0..255)
        MAX-ACCESS  read-write
        STATUS      current
        DESCRIPTION
            "Receive / Transmit Transition Gap."
        REFERENCE
            "Table 358, in IEEE 802.16-2004"
        ::= { wmanIfBsOfdmDownlinkChannelEntry 4 }

wmanIfBsOfdmInitRngMaxRSS OBJECT-TYPE
        SYNTAX      INTEGER (0..65535)
        UNITS       "dBm"
        MAX-ACCESS  read-write
        STATUS      current
        DESCRIPTION
            "Initial Ranging Max. Received Signal Strength at BS
             Signed in units of 1 dBm."
        REFERENCE
            "Table 358, in IEEE 802.16-2004"
        ::= { wmanIfBsOfdmDownlinkChannelEntry 5 }

wmanIfBsOfdmDownlinkCenterFreq OBJECT-TYPE
        SYNTAX      Unsigned32
        UNITS       "kHz"
        MAX-ACCESS  read-write
        STATUS      current
        DESCRIPTION
            "Downlink center frequency (kHz)."
        REFERENCE
            "Table 358, in IEEE 802.16-2004"
        ::= { wmanIfBsOfdmDownlinkChannelEntry 6 }

wmanIfBsOfdmBsId OBJECT-TYPE
        SYNTAX      WmanIfBsIdType
        MAX-ACCESS  read-write
        STATUS      current
        DESCRIPTION
            "Base station ID."
        REFERENCE
            "Table 358, in IEEE 802.16-2004"
        ::= { wmanIfBsOfdmDownlinkChannelEntry 7 }
        
wmanIfBsOfdmMacVersion OBJECT-TYPE
        SYNTAX      WmanIfMacVersion
        MAX-ACCESS  read-write
        STATUS      current
        DESCRIPTION
            "This parameter specifies the version of 802.16 to which
             the message originator conforms."
        REFERENCE
            "Table 358, in IEEE 802.16-2004"
        ::= { wmanIfBsOfdmDownlinkChannelEntry 8 }

wmanIfBsOfdmFrameDurationCode OBJECT-TYPE
        SYNTAX      INTEGER {duration2dot5ms(0),
                             duration4ms(1),
                             duration5ms(2),
                             duration8ms(3),
                             duration10ms(4),
                             duration12dot5ms(5),
                             duration20ms(6)}
        MAX-ACCESS  read-write
        STATUS      current
        DESCRIPTION
            "The duration of the frame. The frame duration code
             values are specified in Table 230."
        REFERENCE
            "Subclause 11.4.1, table 230, in IEEE 802.16/2004"
        ::= { wmanIfBsOfdmDownlinkChannelEntry 9 }

wmanIfBsOfdmDownLinkChannelId OBJECT-TYPE
        SYNTAX      INTEGER (0..255)
        MAX-ACCESS  read-write
        STATUS      current
        DESCRIPTION
            "The identifier of the downlink channel to which this
             message refers."
        REFERENCE
            "Subclause 6.3.2.3.1. Table 15, in IEEE 802.16-2004"
        ::= { wmanIfBsOfdmDownlinkChannelEntry 10 }
        
wmanIfBsOfdmUcdBurstProfileTable OBJECT-TYPE
        SYNTAX      SEQUENCE OF WmanIfBsOfdmUcdBurstProfileEntry
        MAX-ACCESS  not-accessible
        STATUS      current
        DESCRIPTION
            "This table contains UCD burst profiles for each uplink
             channel"
        REFERENCE
            "Table 356, in IEEE 802.16-2004"
        ::= { wmanIfBsOfdmPhy 3 }

wmanIfBsOfdmUcdBurstProfileEntry OBJECT-TYPE
        SYNTAX      WmanIfBsOfdmUcdBurstProfileEntry
        MAX-ACCESS  not-accessible
        STATUS      current
        DESCRIPTION
            "This table provides one row for each UCD burst profile.
             This table is double indexed. The primary index is an
             ifIndex with an ifType of propBWAp2Mp. The secondary index
             is wmanIfBsOfdmUiucIndex."
        INDEX { ifIndex, wmanIfBsOfdmUiucIndex }
        ::= { wmanIfBsOfdmUcdBurstProfileTable 1 }

WmanIfBsOfdmUcdBurstProfileEntry ::= SEQUENCE {
        wmanIfBsOfdmUiucIndex                   INTEGER,
        wmanIfBsOfdmUcdFecCodeType              WmanIfOfdmFecCodeType,
        wmanIfBsOfdmFocusCtPowerBoost           INTEGER,
        wmanIfBsOfdmUcdTcsEnable                INTEGER,
        wmanIfBsOfdmUcdBurstProfileRowStatus    RowStatus}

wmanIfBsOfdmUiucIndex OBJECT-TYPE
        SYNTAX      INTEGER (5 .. 12)
        MAX-ACCESS  not-accessible
        STATUS      current
        DESCRIPTION
            "The Uplink Interval Usage Code indicates the uplink burst
             profile in the UCD message, and is used along with ifIndex
             to identify an entry in the
             wmanIfBsOfdmUcdBurstProfileTable."
        REFERENCE
            "Subclause 8.3.6.3.1, in IEEE 802.16-2004"
        ::= { wmanIfBsOfdmUcdBurstProfileEntry 1 }

wmanIfBsOfdmUcdFecCodeType OBJECT-TYPE
        SYNTAX      WmanIfOfdmFecCodeType
        MAX-ACCESS  read-create
        STATUS      current
        DESCRIPTION
            "Uplink FEC code type and modulation type"
        REFERENCE
            "Table 356, in IEEE 802.16-2004"
        ::= { wmanIfBsOfdmUcdBurstProfileEntry 2 }

wmanIfBsOfdmFocusCtPowerBoost OBJECT-TYPE
        SYNTAX      INTEGER (0 .. 255)
        MAX-ACCESS  read-create
        STATUS      current
        DESCRIPTION
            "The power boost in dB of focused contention carriers, as
           described in 8.3.6.3.3."
        REFERENCE
            "Table 356, in IEEE 802.16-2004"
        ::= { wmanIfBsOfdmUcdBurstProfileEntry 3 }

wmanIfBsOfdmUcdTcsEnable OBJECT-TYPE
        SYNTAX      INTEGER {tcsDisabled(0),
                             tcsEnabled(1)}
        MAX-ACCESS  read-create
        STATUS      current
        DESCRIPTION
            "This parameter determines the transmission convergence
             sublayer, as described in 8.1.4.3, can be enabled on a
             per-burst basis for both uplink and downlink. through
             DIUC/UIUC messages."
        REFERENCE
            "Table 356, in IEEE 802.16-2004"
        ::= { wmanIfBsOfdmUcdBurstProfileEntry 4 }
        
wmanIfBsOfdmUcdBurstProfileRowStatus OBJECT-TYPE
        SYNTAX      RowStatus
        MAX-ACCESS  read-create
        STATUS      current
        DESCRIPTION
            "This object is used to create a new row or modify or
             delete an existing row in this table.

             If the implementator of this MIB has choosen not
             to implement 'dynamic assignment' of profiles, this
             object is not useful and should return noSuchName
             upon SNMP request."
        ::= { wmanIfBsOfdmUcdBurstProfileEntry 5 }
        
wmanIfBsOfdmDcdBurstProfileTable OBJECT-TYPE
        SYNTAX      SEQUENCE OF WmanIfBsOfdmDcdBurstProfileEntry
        MAX-ACCESS  not-accessible
        STATUS      current
        DESCRIPTION
            "This table provides one row for each DCD burst profile.
             This table is double indexed. The primary index is an
             ifIndex with an ifType of propBWAp2Mp. The secondary
             index is wmanIfBsOfdmDiucIndex."
        REFERENCE
            "Table 362, in IEEE 802.16-2004"
        ::= { wmanIfBsOfdmPhy 4 }

wmanIfBsOfdmDcdBurstProfileEntry OBJECT-TYPE
        SYNTAX      WmanIfBsOfdmDcdBurstProfileEntry
        MAX-ACCESS  not-accessible
        STATUS      current
        DESCRIPTION
            "This table provides one row for each DCD burst profile.
             This table is double indexed. The primary index is an
             ifIndex with an ifType of propBWAp2Mp. The secondary index
             is wmanIfBsOfdmDiucIndex."
        INDEX { ifIndex, wmanIfBsOfdmDiucIndex }
        ::= { wmanIfBsOfdmDcdBurstProfileTable 1 }

WmanIfBsOfdmDcdBurstProfileEntry ::= SEQUENCE {
        wmanIfBsOfdmDiucIndex                   INTEGER,
        wmanIfBsOfdmDownlinkFrequency           Unsigned32,
        wmanIfBsOfdmDcdFecCodeType              WmanIfOfdmFecCodeType,
        wmanIfBsOfdmDiucMandatoryExitThresh     INTEGER,
        wmanIfBsOfdmDiucMinEntryThresh          INTEGER,
        wmanIfBsOfdmTcsEnable                   INTEGER,
        wmanIfBsOfdmDcdBurstProfileRowStatus    RowStatus}

wmanIfBsOfdmDiucIndex OBJECT-TYPE
        SYNTAX      INTEGER (1..11)
        MAX-ACCESS  not-accessible
        STATUS      current
        DESCRIPTION
            "The Downlink Interval Usage Code indicates the downlink
             burst profile in the DCD message, and is used along with
             ifIndex to identify an entry in the
             wmanIfBsOfdmDcdBurstProfileTable."
        REFERENCE
            "Subclause 8.3.6.3.1, in IEEE 802.16-2004"
        ::= { wmanIfBsOfdmDcdBurstProfileEntry 1 }
        
wmanIfBsOfdmDownlinkFrequency OBJECT-TYPE
        SYNTAX      Unsigned32
        UNITS       "kHz"
        MAX-ACCESS  read-create
        STATUS      current
        DESCRIPTION
            "Downlink Frequency (kHz)."
        REFERENCE
            "Table 359, in IEEE 802.16-2004"
        ::= { wmanIfBsOfdmDcdBurstProfileEntry 2 }

wmanIfBsOfdmDcdFecCodeType OBJECT-TYPE
        SYNTAX      WmanIfOfdmFecCodeType
        MAX-ACCESS  read-create
        STATUS      current
        DESCRIPTION
            "Downlink FEC code type and modulation type"
        REFERENCE
            "Table 362, in IEEE 802.16-2004"
        ::= { wmanIfBsOfdmDcdBurstProfileEntry 3 }

wmanIfBsOfdmDiucMandatoryExitThresh OBJECT-TYPE
        SYNTAX      INTEGER (0..255)
        MAX-ACCESS  read-create
        STATUS      current
        DESCRIPTION
            "DIUC mandatory exit threshold: 0 - 63.75 dB CINR at or
             below where this DIUC can no longer be used and where this
             change to a more robust DIUC is required in 0.25 dB units."
        REFERENCE
            "Table 362, in IEEE 802.16-2004"
        ::= { wmanIfBsOfdmDcdBurstProfileEntry 4 }

wmanIfBsOfdmDiucMinEntryThresh OBJECT-TYPE
        SYNTAX      INTEGER (0..255)
        MAX-ACCESS  read-create
        STATUS      current
        DESCRIPTION
            "DIUC minimum entry threshold: 0 - 63.75 dB The minimum CINR
            required to start using this DIUC when changing from a more
            robust DIUC is required, in 0.25 dB units."
        REFERENCE
            "Table 362, in IEEE 802.16-2004"
        ::= { wmanIfBsOfdmDcdBurstProfileEntry 5 }

wmanIfBsOfdmTcsEnable OBJECT-TYPE
        SYNTAX      INTEGER {tcsDisabled (0),
                             tcsEnabled (1)}
        MAX-ACCESS  read-create
        STATUS      current
        DESCRIPTION
            "Indicates whether Transmission COnvergence Sublayer
             is enabled or disabled."
        REFERENCE
            "Table 362, in IEEE 802.16-2004"
        ::= { wmanIfBsOfdmDcdBurstProfileEntry 6 }
        
wmanIfBsOfdmDcdBurstProfileRowStatus OBJECT-TYPE
        SYNTAX      RowStatus
        MAX-ACCESS  read-create
        STATUS      current
        DESCRIPTION
            "This object is used to create a new row or modify or
            delete an existing row in this table.

            If the implementator of this MIB has choosen not
            to implement 'dynamic assignment' of profiles, this
            object is not useful and should return noSuchName
            upon SNMP request."
        ::= { wmanIfBsOfdmDcdBurstProfileEntry 7 }

wmanIfBsOfdmConfigurationTable OBJECT-TYPE
        SYNTAX      SEQUENCE OF WmanIfBsOfdmConfigurationEntry
        MAX-ACCESS  not-accessible
        STATUS      current
        DESCRIPTION
            "This table contains BS configuration objects, specific to
             OFDM PHY."
        ::= { wmanIfBsOfdmPhy 5 }

wmanIfBsOfdmConfigurationEntry OBJECT-TYPE
        SYNTAX      WmanIfBsOfdmConfigurationEntry
        MAX-ACCESS  not-accessible
        STATUS      current
        DESCRIPTION
            "This table is indexed by ifIndex with an ifType of
               propBWAp2Mp."
        INDEX { ifIndex }
        ::= { wmanIfBsOfdmConfigurationTable 1 }

WmanIfBsOfdmConfigurationEntry ::= SEQUENCE {
        wmanIfBsOfdmMinReqRegionFullTxOpp       INTEGER,
        wmanIfBsOfdmMinFocusedCtTxOpp           INTEGER,
        wmanIfBsOfdmMaxRoundTripDelay           INTEGER,
        wmanIfBsOfdmRangeAbortTimingThold       INTEGER,
        wmanIfBsOfdmRangeAbortPowerThold        INTEGER,
        wmanIfBsOfdmRangeAbortFreqThold         INTEGER,
        wmanIfBsOfdmDnlkRateId                  INTEGER,
        wmanIfBsOfdmRatioG                      INTEGER}

wmanIfBsOfdmMinReqRegionFullTxOpp OBJECT-TYPE
        SYNTAX      INTEGER (1..65535)
        UNITS       "1/sec"
        MAX-ACCESS  read-write
        STATUS      current
        DESCRIPTION
            "The minimum number of Full bandwidth Req-Region Full
             Transmit opportunities scheduled in the UL per second."
        REFERENCE
            "Subclause 6.3.7.4.3 in IEEE 802.16-2004"
        ::= { wmanIfBsOfdmConfigurationEntry 1 }

wmanIfBsOfdmMinFocusedCtTxOpp OBJECT-TYPE
        SYNTAX      INTEGER (0..65535)
        UNITS       "1/sec"
        MAX-ACCESS  read-write
        STATUS      current
        DESCRIPTION
            "The minimum number of focused contention Transmit
             opportunities scheduled in the UL per second. The value may
             be 0 if the focused contention is not implemented."
        REFERENCE
            "Subclause 6.3.6.4 and 8.3.7.3.3 in IEEE 802.16-2004"
        ::= { wmanIfBsOfdmConfigurationEntry 2 }

wmanIfBsOfdmMaxRoundTripDelay OBJECT-TYPE
        SYNTAX      INTEGER (1..65535)
        UNITS       "us"
        MAX-ACCESS  read-write
        STATUS      current
        DESCRIPTION
            "Maximum supported round trip delay.
             It is required to limit the cell size."
        REFERENCE
            "Subclause 8.3.5.1 in IEEE 802.16-2004"
        ::= { wmanIfBsOfdmConfigurationEntry 3 }

wmanIfBsOfdmRangeAbortTimingThold OBJECT-TYPE
        SYNTAX      INTEGER (0..255)
        UNITS       "1/Fs"
        MAX-ACCESS  read-write
        STATUS      current
        DESCRIPTION
            "This object defines Tolerable Timing Offset. BS performs
             Initial Ranging until the SS transmissions are within 
             limits that are deemed tolerable by the BS. If the SS does
             not transmit within these limits after a number of
             correction attempts then the BS aborts Initial Ranging."
        REFERENCE
            "Figure 63 and Table 365 in IEEE 802.16-2004"
        ::= { wmanIfBsOfdmConfigurationEntry 4 }
        
wmanIfBsOfdmRangeAbortPowerThold OBJECT-TYPE
        SYNTAX      INTEGER (0..255)
        UNITS       "0.25dB"
        MAX-ACCESS  read-write
        STATUS      current
        DESCRIPTION
            "This object defines Tolerable Power Offset. BS performs
             Initial Ranging until the SS transmissions are within 
             limits that are deemed tolerable by the BS. If the SS does
             not transmit within these limits after a number of
             correction attempts then the BS aborts Initial Ranging."
        REFERENCE
            "Figure 63 and Table 365 in IEEE 802.16-2004"
        ::= { wmanIfBsOfdmConfigurationEntry 5 }
        
wmanIfBsOfdmRangeAbortFreqThold OBJECT-TYPE
        SYNTAX      INTEGER (0..255)
        UNITS       "Hz"
        MAX-ACCESS  read-write
        STATUS      current
        DESCRIPTION
            "This object defines Tolerable Frequency Offset. BS performs
             Initial Ranging until the SS transmissions are within
             limits that are deemed tolerable by the BS. If the SS does
             not transmit within these limits after a number of
             correction attempts then the BS aborts Initial Ranging."
        REFERENCE
            "Figure 63 and Table 365 in IEEE 802.16-2004"
        ::= { wmanIfBsOfdmConfigurationEntry 6 }
        
wmanIfBsOfdmDnlkRateId OBJECT-TYPE
        SYNTAX      INTEGER {dnlkRateIdBpsk1Over2(0),
                             dnlkRateIdQpsk1Over2(1),
                             dnlkRateIdQpsk3Over4(2),
                             dnlkRateId16Qam1Over2(3),
                             dnlkRateId16Qam3Over4(4),
                             dnlkRateId64Qam2Over3(5),
                             dnlkRateId64Qam3Over4(6)}
        MAX-ACCESS  read-write
        STATUS      current
        DESCRIPTION
            "The Rate ID to be used in the first downlink burst
             immediately following the FCH. The Rate ID encoding is
             static and cannot be changed during system operation. The
             change of the Rate ID should be applied on system
             re-intialisation (e.g. following sector or BS reset)."
        REFERENCE
            "Subclause 8.3.3.4.3 in IEEE 802.16-2004"
        DEFVAL      { dnlkRateIdBpsk1Over2 }
        ::= { wmanIfBsOfdmConfigurationEntry 7 }

wmanIfBsOfdmRatioG OBJECT-TYPE
        SYNTAX INTEGER {ratio1To4(0),
                        ratio1To8(1),
                        ratio1To16(2),
                        ratio1To32(3)}
        MAX-ACCESS  read-write
        STATUS      current
        DESCRIPTION
            "The ratio of CP time to 'useful' time.Values
             are 1/4, 1/8, 1/16 or 1/32."
        REFERENCE
            "Section 8.3.1.1.1 in IEEE 802.16-2004"
        DEFVAL      { ratio1To4 }
        ::= { wmanIfBsOfdmConfigurationEntry 8 }
		
wmanIfBsSsOfdmReqCapabilitiesTable OBJECT-TYPE
        SYNTAX      SEQUENCE OF WmanIfBsSsOfdmReqCapabilitiesEntry
        MAX-ACCESS  not-accessible
        STATUS      current
        DESCRIPTION
            "This table contains the basic capability information,
             specific to OFDM Phy, of SSs that have been reported by
             SSs to BS using RNG-REQ, SBC-REQ and REG-REQ messages. 
             Entries in this table should be created when an SS
             registers with a BS."
        ::= { wmanIfBsOfdmPhy 6 }

wmanIfBsSsOfdmReqCapabilitiesEntry OBJECT-TYPE
        SYNTAX      WmanIfBsSsOfdmReqCapabilitiesEntry
        MAX-ACCESS  not-accessible
        STATUS      current
        DESCRIPTION
            "This table provides one row for each SS that has been
             registered in the BS. This table augments the table 
             wmanIfBsRegisteredSsTable."
        AUGMENTS { wmanIfBsRegisteredSsEntry }
        ::= { wmanIfBsSsOfdmReqCapabilitiesTable 1 }

WmanIfBsSsOfdmReqCapabilitiesEntry ::= SEQUENCE {        
        wmanIfBsSsOfdmReqCapFftSizes            WmanIfOfdmFftSizes,
        wmanIfBsSsOfdmReqCapSsDemodulator       WmanIfOfdmSsDeModType,
        wmanIfBsSsOfdmReqCapSsModulator         WmanIfOfdmSsModType,
        wmanIfBsSsOfdmReqCapFocusedCtSupport    WmanIfOfdmFocusedCt,
        wmanIfBsSsOfdmReqCapTcSublayerSupport   WmanIfOfdmTcSublayer}

wmanIfBsSsOfdmReqCapFftSizes OBJECT-TYPE
        SYNTAX      WmanIfOfdmFftSizes
        MAX-ACCESS  read-only
        STATUS      current
        DESCRIPTION
            "This field indicates the FFT sizes supported by SS.
             The usage is defined by WmanIfCapOfdmFftSizesType."
        ::= { wmanIfBsSsOfdmReqCapabilitiesEntry 1 }

wmanIfBsSsOfdmReqCapSsDemodulator OBJECT-TYPE
        SYNTAX      WmanIfOfdmSsDeModType
        MAX-ACCESS  read-only
        STATUS      current
        DESCRIPTION
            "This field indicates the different demodulator options
             supported by SS for downlink. 
             The usage is defined by WmanIfCapOfdmSsDemodulatorType."
        ::= { wmanIfBsSsOfdmReqCapabilitiesEntry 2 }

wmanIfBsSsOfdmReqCapSsModulator OBJECT-TYPE
        SYNTAX      WmanIfOfdmSsModType
        MAX-ACCESS  read-only
        STATUS      current
        DESCRIPTION
            "This field indicates the different modulator options
             supported by SS for uplink. 
             The usage is defined by WmanIfCapOfdmSsModulatorType."
        ::= { wmanIfBsSsOfdmReqCapabilitiesEntry 3 }

wmanIfBsSsOfdmReqCapFocusedCtSupport OBJECT-TYPE
        SYNTAX      WmanIfOfdmFocusedCt
        MAX-ACCESS  read-only
        STATUS      current
        DESCRIPTION
            "This field indicates whether the SS supports Focused
             Contention. The usage is defined by
             WmanIfCapOfdmFocusedCtSupportType."
        ::= { wmanIfBsSsOfdmReqCapabilitiesEntry 4 }

wmanIfBsSsOfdmReqCapTcSublayerSupport OBJECT-TYPE
        SYNTAX      WmanIfOfdmTcSublayer
        MAX-ACCESS  read-only
        STATUS      current
        DESCRIPTION
            "This field indicates whether or not the SS supports
             the TC sublayer. The usage is defined by
             WmanIfCapOfdmTcSublayerSupportType."
        ::= { wmanIfBsSsOfdmReqCapabilitiesEntry 5 }

wmanIfBsSsOfdmRspCapabilitiesTable OBJECT-TYPE
        SYNTAX      SEQUENCE OF WmanIfBsSsOfdmRspCapabilitiesEntry
        MAX-ACCESS  not-accessible
        STATUS      current
        DESCRIPTION
            "This table contains the basic capability information,
             specific to OFDM Phy, of SSs that have been negotiated
             and agreed between BS and SS via RNG-REQ/RSP,
             SBC-REQ/RSP and REG-REQ/RSP messages. This table
             augments the wmanIfBsRegisteredSsTable."
        REFERENCE
            "Subclause 6.3.2.3.7 in IEEE 802.16-2004"
        ::= { wmanIfBsOfdmPhy 7 }

wmanIfBsSsOfdmRspCapabilitiesEntry OBJECT-TYPE
        SYNTAX      WmanIfBsSsOfdmRspCapabilitiesEntry
        MAX-ACCESS  not-accessible
        STATUS      current
        DESCRIPTION
            "This table provides one row for each SS that has been
             registered in the BS. This table augments the
              wmanIfBsRegisteredSsTable. "
        AUGMENTS { wmanIfBsRegisteredSsEntry }
        ::= { wmanIfBsSsOfdmRspCapabilitiesTable 1 }

WmanIfBsSsOfdmRspCapabilitiesEntry ::= SEQUENCE {        
        wmanIfBsSsOfdmRspCapFftSizes            WmanIfOfdmFftSizes,
        wmanIfBsSsOfdmRspCapSsDemodulator       WmanIfOfdmSsDeModType,
        wmanIfBsSsOfdmRspCapSsModulator         WmanIfOfdmSsModType,
        wmanIfBsSsOfdmRspCapFocusedCtSupport    WmanIfOfdmFocusedCt,
        wmanIfBsSsOfdmRspCapTcSublayerSupport   WmanIfOfdmTcSublayer}

wmanIfBsSsOfdmRspCapFftSizes OBJECT-TYPE
        SYNTAX      WmanIfOfdmFftSizes
        MAX-ACCESS  read-only
        STATUS      current
        DESCRIPTION
            "This field indicates the FFT sizes negotiated with the
             SS. The usage is defined by WmanIfCapOfdmFftSizesType."
        ::= { wmanIfBsSsOfdmRspCapabilitiesEntry 1 }

wmanIfBsSsOfdmRspCapSsDemodulator OBJECT-TYPE
        SYNTAX      WmanIfOfdmSsDeModType
        MAX-ACCESS  read-only
        STATUS      current
        DESCRIPTION
            "This field indicates the different demodulator options
             negotiated for SS for downlink. The usage is defined by
             WmanIfCapOfdmSsDemodulatorType."
        ::= { wmanIfBsSsOfdmRspCapabilitiesEntry 2 }

wmanIfBsSsOfdmRspCapSsModulator OBJECT-TYPE
        SYNTAX      WmanIfOfdmSsModType
        MAX-ACCESS  read-only
        STATUS      current
        DESCRIPTION
            "This field indicates the different modulator options
             negotiated for SS for uplink. The usage is defined by
             WmanIfCapOfdmSsModulatorType."
        ::= { wmanIfBsSsOfdmRspCapabilitiesEntry 3 }

wmanIfBsSsOfdmRspCapFocusedCtSupport OBJECT-TYPE
        SYNTAX      WmanIfOfdmFocusedCt
        MAX-ACCESS  read-only
        STATUS      current
        DESCRIPTION
            "This field indicates whether the SS has negotiated the
             support for Focused Contention. The usage is defined by
             WmanIfCapOfdmFocusedCtSupportType."
        ::= { wmanIfBsSsOfdmRspCapabilitiesEntry 4 }

wmanIfBsSsOfdmRspCapTcSublayerSupport OBJECT-TYPE
        SYNTAX      WmanIfOfdmTcSublayer
        MAX-ACCESS  read-only
        STATUS      current
        DESCRIPTION
            "This field indicates whether the SS has negotiated
             support for the TC sublayer. The usage is defined by
             WmanIfCapOfdmTcSublayerSupportType."
        ::= { wmanIfBsSsOfdmRspCapabilitiesEntry 5 }

wmanIfBsOfdmCapabilitiesTable OBJECT-TYPE
        SYNTAX      SEQUENCE OF WmanIfBsOfdmCapabilitiesEntry
        MAX-ACCESS  not-accessible
        STATUS      current
        DESCRIPTION
            "This table contains the basic capabilities, specific to
             OFDM Phy, of the BS as implemented in BS hardware and
             software. These capabilities along with the configuration
             for them (wmanIfBsOfdmCapabilitiesConfigTable) are used
             for negotiation of basic capabilities with SS using
             RNG-RSP, SBC-RSP and REG-RSP messages. The negotiated
             capabilities are obtained by interSubclause of SS raw
             reported capabilities, BS raw capabilities and BS
             configured capabilities. The objects in the table have
             read-only access. The table is maintained by BS."
        ::= { wmanIfBsOfdmPhy 8 }

wmanIfBsOfdmCapabilitiesEntry OBJECT-TYPE
        SYNTAX      WmanIfBsOfdmCapabilitiesEntry
        MAX-ACCESS  not-accessible
        STATUS      current
        DESCRIPTION
            "This table provides one row for each BS sector and is
             indexed by ifIndex."
        INDEX { ifIndex }
        ::= { wmanIfBsOfdmCapabilitiesTable 1 }

WmanIfBsOfdmCapabilitiesEntry ::= SEQUENCE {
        wmanIfBsOfdmCapFftSizes                 WmanIfOfdmFftSizes,
        wmanIfBsOfdmCapSsDemodulator            WmanIfOfdmSsDeModType,
        wmanIfBsOfdmCapSsModulator              WmanIfOfdmSsModType,
        wmanIfBsOfdmCapFocusedCtSupport         WmanIfOfdmFocusedCt,
        wmanIfBsOfdmCapTcSublayerSupport        WmanIfOfdmTcSublayer}

wmanIfBsOfdmCapFftSizes OBJECT-TYPE
        SYNTAX      WmanIfOfdmFftSizes
        MAX-ACCESS  read-only
        STATUS      current
        DESCRIPTION
            "This field indicates the FFT sizes supported by the BS.
             The usage is defined by WmanIfOfdmCapFftSizes."
        ::= { wmanIfBsOfdmCapabilitiesEntry 1 }

wmanIfBsOfdmCapSsDemodulator OBJECT-TYPE
        SYNTAX      WmanIfOfdmSsDeModType
        MAX-ACCESS  read-only
        STATUS      current
        DESCRIPTION
            "This field indicates the different BS demodulator options
             for uplink supported by the BS. The usage is defined by
             WmanIfOfdmSsDeModType."
        ::= { wmanIfBsOfdmCapabilitiesEntry 2 }
        
wmanIfBsOfdmCapSsModulator OBJECT-TYPE
        SYNTAX      WmanIfOfdmSsModType
        MAX-ACCESS  read-only
        STATUS      current
        DESCRIPTION
            "This field indicates the different BS modulator options
             for downlink supported by the BS. The usage is defined by
             WmanIfOfdmSsModType."
        ::= { wmanIfBsOfdmCapabilitiesEntry 3 }

wmanIfBsOfdmCapFocusedCtSupport OBJECT-TYPE
        SYNTAX      WmanIfOfdmFocusedCt
        MAX-ACCESS  read-only
        STATUS      current
        DESCRIPTION
            "This field indicates the BS support for Focused
             Contention. The usage is defined by
             WmanIfOfdmFocusedCt."
        ::= { wmanIfBsOfdmCapabilitiesEntry 4 }

wmanIfBsOfdmCapTcSublayerSupport OBJECT-TYPE
        SYNTAX      WmanIfOfdmTcSublayer
        MAX-ACCESS  read-only
        STATUS      current
        DESCRIPTION
            "This field indicates the BS supports for TC sublayer. The
             usage is defined by WmanIfOfdmTcSublayer."
        ::= { wmanIfBsOfdmCapabilitiesEntry 5 }

wmanIfBsOfdmCapabilitiesConfigTable OBJECT-TYPE
        SYNTAX      SEQUENCE OF WmanIfBsOfdmCapabilitiesConfigEntry
        MAX-ACCESS  not-accessible
        STATUS      current
        DESCRIPTION
            "This table contains the configuration for basic
             capabilities of BS, specific to OFDM Phy. The table is
             intended to be used to restrict the Capabilities
             implemented by BS, for example in order to comply with
             local regulatory requirements. The BS should use the
             configuration along with the implemented Capabilities 
             (wmanIfBsOfdmPhyTable) for negotiation of basic
             capabilities with SS using RNG-RSP, SBC-RSP and REG-RSP
             messages. The negotiated capabilities are obtained by
             interSubclause of SS reported capabilities, BS raw
             capabilities and BS configured capabilities. The objects
             in the table have read-write access. The rows are created
             by BS as a copy of wmanIfBsBasicCapabilitiesTable
             and can be modified by NMS."
        ::= { wmanIfBsOfdmPhy 9 }

wmanIfBsOfdmCapabilitiesConfigEntry OBJECT-TYPE
        SYNTAX      WmanIfBsOfdmCapabilitiesConfigEntry
        MAX-ACCESS  not-accessible
        STATUS      current
        DESCRIPTION
            "This table provides one row for each BS sector and is
             indexed by ifIndex."
        INDEX { ifIndex }
        ::= { wmanIfBsOfdmCapabilitiesConfigTable 1 }

WmanIfBsOfdmCapabilitiesConfigEntry ::= SEQUENCE {
        wmanIfBsOfdmCapCfgFftSizes              WmanIfOfdmFftSizes,
        wmanIfBsOfdmCapCfgSsDemodulator         WmanIfOfdmSsDeModType,
        wmanIfBsOfdmCapCfgSsModulator           WmanIfOfdmSsModType,
        wmanIfBsOfdmCapCfgFocusedCtSupport      WmanIfOfdmFocusedCt,
        wmanIfBsOfdmCapCfgTcSublayerSupport     WmanIfOfdmTcSublayer}

wmanIfBsOfdmCapCfgFftSizes OBJECT-TYPE
        SYNTAX      WmanIfOfdmFftSizes
        MAX-ACCESS  read-write
        STATUS      current
        DESCRIPTION
            "This field indicates the FFT sizes support configured for
             the BS. The usage is defined by
             WmanIfOfdmCapFftSizes."
        ::= { wmanIfBsOfdmCapabilitiesConfigEntry 1 }

wmanIfBsOfdmCapCfgSsDemodulator OBJECT-TYPE
        SYNTAX      WmanIfOfdmSsDeModType
        MAX-ACCESS  read-write
        STATUS      current
        DESCRIPTION
            "This field indicates the different BS demodulator options
             configured for uplink. The usage is defined by
             WmanIfOfdmSsDeModType."
        ::= { wmanIfBsOfdmCapabilitiesConfigEntry 2 }
        
wmanIfBsOfdmCapCfgSsModulator OBJECT-TYPE
        SYNTAX      WmanIfOfdmSsModType
        MAX-ACCESS  read-write
        STATUS      current
        DESCRIPTION
            "This field indicates the different BS modulator options
             configured for downlink. The usage is defined by
             WmanIfOfdmSsModType."
        ::= { wmanIfBsOfdmCapabilitiesConfigEntry 3 }

wmanIfBsOfdmCapCfgFocusedCtSupport OBJECT-TYPE
        SYNTAX      WmanIfOfdmFocusedCt
        MAX-ACCESS  read-write
        STATUS      current
        DESCRIPTION
            "This field indicates the BS support configured for
             Focused Contention. The usage is defined by
             WmanIfOfdmFocusedCt."
        ::= { wmanIfBsOfdmCapabilitiesConfigEntry 4 }

wmanIfBsOfdmCapCfgTcSublayerSupport OBJECT-TYPE
        SYNTAX      WmanIfOfdmTcSublayer
        MAX-ACCESS  read-write
        STATUS      current
        DESCRIPTION
            "This field indicates the BS support configured for TC
             sublayer. The usage is defined by
             WmanIfOfdmTcSublayer."
        ::= { wmanIfBsOfdmCapabilitiesConfigEntry 5 }        

--
-- BS OFDMA PHY objects    
--
wmanIfBsOfdmaPhy OBJECT IDENTIFIER ::= { wmanIfBsPhy 2 }

wmanIfBsOfdmaUplinkChannelTable OBJECT-TYPE
        SYNTAX      SEQUENCE OF WmanIfBsOfdmaUplinkChannelEntry
        MAX-ACCESS  not-accessible
        STATUS      current
        DESCRIPTION
            "This table contains UCD channel attributes, defining the
             transmission characteristics of uplink channels"
        REFERENCE
            "Table 349 and 353, in IEEE 802.16-2004"
        ::= { wmanIfBsOfdmaPhy 1 }

wmanIfBsOfdmaUplinkChannelEntry OBJECT-TYPE
        SYNTAX      WmanIfBsOfdmaUplinkChannelEntry
        MAX-ACCESS  not-accessible
        STATUS      current
        DESCRIPTION
            "This table provides one row for each uplink channel of
             multi-sector BS, and is indexed by BS ifIndex. An entry
             in this table exists for each ifEntry of BS with an
             ifType of propBWAp2Mp."
        INDEX       { ifIndex }
        ::= { wmanIfBsOfdmaUplinkChannelTable 1 }

WmanIfBsOfdmaUplinkChannelEntry ::= SEQUENCE {
        wmanIfBsOfdmaCtBasedResvTimeout         INTEGER,
        wmanIfBsOfdmaBwReqOppSize               INTEGER,
        wmanIfBsOfdmaRangReqOppSize             INTEGER,
        wmanIfBsOfdmaUplinkCenterFreq           Unsigned32,
        wmanIfBsOfdmaInitRngCodes               INTEGER,
        wmanIfBsOfdmaPeriodicRngCodes           INTEGER,
        wmanIfBsOfdmaBWReqCodes                 INTEGER,
        wmanIfBsOfdmaPerRngBackoffStart         INTEGER,
        wmanIfBsOfdmaPerRngBackoffEnd           INTEGER,
        wmanIfBsOfdmaStartOfRngCodes            INTEGER,
        wmanIfBsOfdmaPermutationBase            INTEGER,
        wmanIfBsOfdmaULAllocSubchBitmap         OCTET STRING,
        wmanIfBsOfdmaOptPermULAllocSubchBitmap  OCTET STRING,
        wmanIfBsOfdmaBandAMCAllocThreshold      INTEGER,
        wmanIfBsOfdmaBandAMCReleaseThreshold    INTEGER,
        wmanIfBsOfdmaBandAMCAllocTimer          INTEGER,
        wmanIfBsOfdmaBandAMCReleaseTimer        INTEGER,
        wmanIfBsOfdmaBandStatRepMAXPeriod       INTEGER,
        wmanIfBsOfdmaBandAMCRetryTimer          INTEGER,
        wmanIfBsOfdmaSafetyChAllocThreshold     INTEGER,
        wmanIfBsOfdmaSafetyChReleaseThreshold   INTEGER,
        wmanIfBsOfdmaSafetyChAllocTimer         INTEGER,
        wmanIfBsOfdmaSafetyChReleaseTimer       INTEGER,
        wmanIfBsOfdmaBinStatRepMAXPeriod        INTEGER,
        wmanIfBsOfdmaSafetyChaRetryTimer        INTEGER,
        wmanIfBsOfdmaHARQAackDelayULBurst       INTEGER,
        wmanIfBsOfdmaCQICHBandAMCTranaDelay     INTEGER}

wmanIfBsOfdmaCtBasedResvTimeout OBJECT-TYPE
        SYNTAX      INTEGER (1..255)
        MAX-ACCESS  read-write
        STATUS      current
        DESCRIPTION
            "The number of UL-MAPs to receive before contention-based
             reservation is attempted again for the same connection."
        REFERENCE
            "Table 349, in IEEE 802.16-2004"
        ::= { wmanIfBsOfdmaUplinkChannelEntry 1 }

wmanIfBsOfdmaBwReqOppSize OBJECT-TYPE
        SYNTAX      INTEGER (1..65535)
        UNITS       "PS"
        MAX-ACCESS  read-write
        STATUS      current
        DESCRIPTION
            "Size (in units of PS) of PHY payload that SS may use to
             format and transmit a bandwidth request message in a
             contention request opportunity. The value includes all
             PHY overhead as well as allowance for the MAC data the
             message may hold."
        REFERENCE
            "Table 349, in IEEE 802.16-2004"
        ::= { wmanIfBsOfdmaUplinkChannelEntry 2 }

wmanIfBsOfdmaRangReqOppSize OBJECT-TYPE
        SYNTAX      INTEGER (1..65535)
        UNITS       "PS"
        MAX-ACCESS  read-write
        STATUS      current
        DESCRIPTION
            "Size (in units of PS) of PHY payload that SS may use to
             format and transmit a RNG-REQ message in a contention
             request opportunity. The value includes all PHY overhead
             as well as allowance for the MAC data the message may
             hold and the maxiumum SS/BS roundtrip propagation delay."
        REFERENCE
            "Table 349, in IEEE 802.16-2004"
        ::= { wmanIfBsOfdmaUplinkChannelEntry 3 }

wmanIfBsOfdmaUplinkCenterFreq OBJECT-TYPE
        SYNTAX      Unsigned32 
        UNITS       "kHz"
        MAX-ACCESS  read-write
        STATUS      current
        DESCRIPTION
            " Uplink center frequency (kHz)"
        REFERENCE
            "Table 349, in IEEE 802.16-2004"
        ::= { wmanIfBsOfdmaUplinkChannelEntry 4 }

wmanIfBsOfdmaInitRngCodes OBJECT-TYPE
        SYNTAX      INTEGER (0..255)
        MAX-ACCESS  read-write
        STATUS      current
        DESCRIPTION
            "Number of initial ranging CDMA codes. Possible values are
             0..255. The total number of wmanIfBsOfdmaInitRngCodes,
             wmanIfBsOfdmaPeriodicRngCodes and wmanIfBsOfdmaBWReqCodes
             shall be equal or less than 256."
        REFERENCE
            "Subclause 11.3.1, table 353, in IEEE 802.16-2004"
        DEFVAL      { 30 }
        ::= { wmanIfBsOfdmaUplinkChannelEntry 5 }
        
wmanIfBsOfdmaPeriodicRngCodes OBJECT-TYPE
        SYNTAX      INTEGER (0..255)
        MAX-ACCESS  read-write
        STATUS      current
        DESCRIPTION
            "Number of periodic ranging CDMA codes. Possible values are
             0..255. The total number of wmanIfBsOfdmaInitRngCodes,
             wmanIfBsOfdmaPeriodicRngCodes and wmanIfBsOfdmaBWReqCodes
             shall be equal or less than 256."
        REFERENCE
            "Subclause 11.3.1, table 353, in IEEE 802.16-2004"
        DEFVAL 	    { 30 }
        ::= { wmanIfBsOfdmaUplinkChannelEntry 6 }

wmanIfBsOfdmaBWReqCodes OBJECT-TYPE
        SYNTAX      INTEGER (0..255)
        MAX-ACCESS  read-write
        STATUS      current
        DESCRIPTION
            "Number of bandwidth request codes. Possible values are
             0..255. The total number of wmanIfBsOfdmaInitRngCodes,
             wmanIfBsOfdmaPeriodicRngCodes and wmanIfBsOfdmaBWReqCodes
             shall be equal or less than 256."
        REFERENCE
            "Subclause 11.3.1, table 353, in IEEE 802.16-2004"
        DEFVAL 	    { 30 }
            ::= { wmanIfBsOfdmaUplinkChannelEntry 7 }

wmanIfBsOfdmaPerRngBackoffStart OBJECT-TYPE
        SYNTAX      INTEGER (0..15)
        MAX-ACCESS 	read-write
        STATUS      current
        DESCRIPTION
            "Initial backoff window size for periodic ranging contention,
             , expressed as a power of 2. Range: 0..15 (the highest order
             bits shall be unused and set to 0)."
        REFERENCE
            "Subclause 11.3.1, table 353, in IEEE 802.16-2004"
        DEFVAL 	    { 0 }
        ::= { wmanIfBsOfdmaUplinkChannelEntry 8 }

wmanIfBsOfdmaPerRngBackoffEnd OBJECT-TYPE
        SYNTAX      INTEGER (0 .. 15)
        MAX-ACCESS  read-write
        STATUS      current
        DESCRIPTION
            "Final backoff window size for periodic ranging contention,
             expressed as a power of 2. Range: 0..15 (the highest order
             bits shall be unused and set to 0)."
        REFERENCE
            "Subclause 11.3.1, table 353, in IEEE 802.16-2004"
        DEFVAL 	    { 15 }
        ::= { wmanIfBsOfdmaUplinkChannelEntry 9 }

wmanIfBsOfdmaStartOfRngCodes OBJECT-TYPE
        SYNTAX      INTEGER (0..255)
        MAX-ACCESS  read-write
        STATUS      current
        DESCRIPTION
            "Indicates the starting number, S, of the group of codes
             used for this uplink.All the ranging codes used on this
             uplink will be between S and ((S+N+M+L) mod 256). Where,
             N is the number of initial-ranging codes M is the number
             of periodic-ranging codes L is the number of
             bandwidth-request codes The range of values is 0 S255"
        REFERENCE
            "Subclause 11.3.1, table 353, in IEEE 802.16-2004"
        DEFVAL 	    { 0 }
        ::= { wmanIfBsOfdmaUplinkChannelEntry 10 }

wmanIfBsOfdmaPermutationBase OBJECT-TYPE
        SYNTAX      INTEGER (0..255)
        MAX-ACCESS  read-write
        STATUS      current
        DESCRIPTION
            "Determines the UL_IDcell parameter for the subcarrier
             permutation to be used on this uplink channel"
        REFERENCE
            "Subclause 11.3.1, table 353, in IEEE 802.16-2004"
        DEFVAL 	    { 0 }
        ::= { wmanIfBsOfdmaUplinkChannelEntry 11 }

wmanIfBsOfdmaULAllocSubchBitmap OBJECT-TYPE
        SYNTAX      OCTET STRING (SIZE (9))
        MAX-ACCESS  read-write
        STATUS      current
        DESCRIPTION
            "This is a bitmap describing the sub-channels allocated
             to the segment in the UL, when using the uplink PUSC
             permutation. The LSB of the first byte shall corrspond to
             subchannel 0. For any bit that is not set,
             the corresponding subchannel shall not be used by the SS
             on that segment"
        REFERENCE
            "Subclause 11.3.1, table 353, in IEEE 802.16-2004"
        ::= { wmanIfBsOfdmaUplinkChannelEntry 12 }

wmanIfBsOfdmaOptPermULAllocSubchBitmap OBJECT-TYPE
        SYNTAX      OCTET STRING (SIZE (13))
        MAX-ACCESS  read-write
        STATUS      current
        DESCRIPTION
            "This is a bitmap describing the sub-channels allocated to
             the segment in the UL, when using the uplink optional PUSC
             permutation (see 8.4.6.2.5 in IEEE 802.16-2004). The LSB of
             the first byte shall correspond to subchannel 0. For any
             bit that is not set, the corresponding subchannel shall not
             be used by the SS on that segment"
        REFERENCE
            "Subclause 11.3.1, table 353, in IEEE 802.16-2004"
        ::= { wmanIfBsOfdmaUplinkChannelEntry 13 }

wmanIfBsOfdmaBandAMCAllocThreshold OBJECT-TYPE
        SYNTAX      INTEGER (0 .. 255)
        UNITS       "dB"
        MAX-ACCESS  read-write
        STATUS      current
        DESCRIPTION
            "dB unit"
        REFERENCE
            "Subclause 11.3.1, table 353, in IEEE 802.16-2004"
        ::= { wmanIfBsOfdmaUplinkChannelEntry 14 }

wmanIfBsOfdmaBandAMCReleaseThreshold OBJECT-TYPE
        SYNTAX      INTEGER (0 .. 255)
        UNITS       "dB"
        MAX-ACCESS  read-write
        STATUS      current
        DESCRIPTION
            "This object defines the OFDMA band AMC release
             threshold."
        REFERENCE
            "Subclause 11.3.1, table 353, in IEEE 802.16-2004"
        ::= { wmanIfBsOfdmaUplinkChannelEntry 15 }

wmanIfBsOfdmaBandAMCAllocTimer OBJECT-TYPE
        SYNTAX      INTEGER (0 .. 255)
        UNITS       "Frame"
        MAX-ACCESS  read-write
        STATUS      current
        DESCRIPTION
            "This object defines the OFDMA band AMC allocation
             timer."
        REFERENCE
            "Subclause 11.3.1, table 353, in IEEE 802.16-2004"
        ::= { wmanIfBsOfdmaUplinkChannelEntry 16 }

wmanIfBsOfdmaBandAMCReleaseTimer OBJECT-TYPE
        SYNTAX      INTEGER (0 .. 255)
        UNITS       "Frame"
        MAX-ACCESS  read-write
        STATUS      current
        DESCRIPTION
            "This object defines the OFDMA band AMC release
             timer."
        REFERENCE
            "Subclause 11.3.1, table 353, in IEEE 802.16-2004"
        ::= { wmanIfBsOfdmaUplinkChannelEntry 17 }

wmanIfBsOfdmaBandStatRepMAXPeriod OBJECT-TYPE
        SYNTAX      INTEGER (0 .. 255)
        UNITS       "Frame"
        MAX-ACCESS  read-write
        STATUS      current
        DESCRIPTION
            "This object defines the OFDMA band status reporting
             maximum period."
        REFERENCE
            "Subclause 11.3.1, table 353, in IEEE 802.16-2004"
        ::= { wmanIfBsOfdmaUplinkChannelEntry 18 }

wmanIfBsOfdmaBandAMCRetryTimer OBJECT-TYPE
        SYNTAX      INTEGER (0 .. 255)
        UNITS       "Frame"
        MAX-ACCESS  read-write
        STATUS      current
        DESCRIPTION
            "This object defines the OFDMA band AMC retry
             timer."
        REFERENCE
            "Subclause 11.3.1, table 353, in IEEE 802.16-2004"
        ::= { wmanIfBsOfdmaUplinkChannelEntry 19 }

wmanIfBsOfdmaSafetyChAllocThreshold OBJECT-TYPE
        SYNTAX      INTEGER (0 .. 255)
        UNITS       "dB"
        MAX-ACCESS  read-write
        STATUS      current
        DESCRIPTION
            "This object defines the OFDMA safety channel allocation
             threshold."
        REFERENCE
            "Subclause 11.3.1, table 353, in IEEE 802.16-2004"
        ::= { wmanIfBsOfdmaUplinkChannelEntry 20 }

wmanIfBsOfdmaSafetyChReleaseThreshold OBJECT-TYPE
        SYNTAX      INTEGER (0 .. 255)
        UNITS       "dB"
        MAX-ACCESS  read-write
        STATUS      current
        DESCRIPTION
            "This object defines the OFDMA safety channel release
             threshold."
        REFERENCE
            "Subclause 11.3.1, table 353, in IEEE 802.16-2004"
        ::= { wmanIfBsOfdmaUplinkChannelEntry 21 }

wmanIfBsOfdmaSafetyChAllocTimer OBJECT-TYPE
        SYNTAX      INTEGER (0 .. 255)
        UNITS       "Frame"
        MAX-ACCESS 	read-write
        STATUS      current
        DESCRIPTION
            "This object defines the OFDMA safety channel allocation
             timer."
        REFERENCE
            "Subclause 11.3.1, table 353, in IEEE 802.16-2004"
        ::= { wmanIfBsOfdmaUplinkChannelEntry 22 }

wmanIfBsOfdmaSafetyChReleaseTimer OBJECT-TYPE
        SYNTAX      INTEGER (0 .. 255)
        UNITS       "Frame"
        MAX-ACCESS  read-write
        STATUS      current
        DESCRIPTION
            "This object defines the OFDMA safety channel release
             timer."
        REFERENCE
            "Subclause 11.3.1, table 353, in IEEE 802.16-2004"
        ::= { wmanIfBsOfdmaUplinkChannelEntry 23 }

wmanIfBsOfdmaBinStatRepMAXPeriod OBJECT-TYPE
        SYNTAX      INTEGER (0 .. 255)
        UNITS       "Frame"
        MAX-ACCESS  read-write
        STATUS      current
        DESCRIPTION
            "This object defines the OFDMA bin status reporting
             maximum period."
        REFERENCE
            "Subclause 11.3.1, table 353, in IEEE 802.16-2004"
        ::= { wmanIfBsOfdmaUplinkChannelEntry 24 }

wmanIfBsOfdmaSafetyChaRetryTimer OBJECT-TYPE
        SYNTAX      INTEGER (0 .. 255)
        UNITS       "Frame"
        MAX-ACCESS  read-write
        STATUS      current
        DESCRIPTION
            "This object defines the OFDMA safety channel retry
             timer."
        REFERENCE
            "Subclause 11.3.1, table 353, in IEEE 802.16-2004"
        ::= { wmanIfBsOfdmaUplinkChannelEntry 25 }

wmanIfBsOfdmaHARQAackDelayULBurst OBJECT-TYPE
        SYNTAX      INTEGER {oneframeoffset(1),
                             twoframesoffset(2),
                             threeframesoffset(3)}
        MAX-ACCESS  read-write
        STATUS      current
        DESCRIPTION
            "This object defines the OFDMA H-ARQ ACK delay for UL burst. 
             1 = one frame offset
             2 = two frames offset
             3 = three frames offset"
        REFERENCE 
            "Subclause 11.3.1, table 353, in IEEE 802.16-2004"
	    ::= { wmanIfBsOfdmaUplinkChannelEntry 26 }

wmanIfBsOfdmaCQICHBandAMCTranaDelay OBJECT-TYPE
        SYNTAX      INTEGER (0 .. 255)
        UNITS       "Frame"
        MAX-ACCESS  read-write
        STATUS      current
        DESCRIPTION
            "This object defines the OFDMA CQICH band AMC transition
             delay."
        REFERENCE
            "Subclause 11.3.1, table 353, in IEEE 802.16-2004"
        ::= { wmanIfBsOfdmaUplinkChannelEntry 27 }

wmanIfBsOfdmaDownlinkChannelTable OBJECT-TYPE
        SYNTAX      SEQUENCE OF WmanIfBsOfdmaDownlinkChannelEntry
        MAX-ACCESS  not-accessible
        STATUS      current
        DESCRIPTION
            "This table contains DCD channel attributes, defining the
             transmission characteristics of downlink channels"
        REFERENCE
            "Subclause 11.4.1, Table 358, in IEEE 802.16-2004"
        ::= { wmanIfBsOfdmaPhy 2 }

wmanIfBsOfdmaDownlinkChannelEntry OBJECT-TYPE
        SYNTAX      WmanIfBsOfdmaDownlinkChannelEntry
        MAX-ACCESS  not-accessible
        STATUS      current
        DESCRIPTION
            "This table provides one row for each downlink channel of
             multi-sector BS, and is indexed by BS ifIndex. An entry in
             this table exists for each ifEntry of BS with an ifType of
             propBWAp2Mp."
        INDEX       { ifIndex }
        ::= { wmanIfBsOfdmaDownlinkChannelTable 1 }

WmanIfBsOfdmaDownlinkChannelEntry ::= SEQUENCE {
        wmanIfBsOfdmaBsEIRP                     INTEGER,
        wmanIfBsOfdmaChannelNumber              WmanIfChannelNumber,
        wmanIfBsOfdmaTTG                        INTEGER,
        wmanIfBsOfdmaRTG                        INTEGER,
        wmanIfBsOfdmaInitRngMaxRSS              INTEGER,
        wmanIfBsOfdmaDownlinkCenterFreq         Unsigned32,
        wmanIfBsOfdmaBsId                       WmanIfBsIdType,
        wmanIfBsOfdmaMacVersion                 WmanIfMacVersion,
        wmanIfBsOfdmaFrameDurationCode          INTEGER,
        wmanIfBsOfdmaSizeCqichIdField           INTEGER,
        wmanIfBsOfdmaHARQAackDelayBurst         INTEGER}

wmanIfBsOfdmaBsEIRP OBJECT-TYPE
        SYNTAX      INTEGER (0..65535)
        UNITS       "dBm"
        MAX-ACCESS  read-write
        STATUS      current
        DESCRIPTION
            "The EIRP is the equivalent isotropic radiated power of
             the base station, which is computed for a simple
             single-antenna transmitter."
        REFERENCE
            "Subclause 11.4.1, table 358, in IEEE 802.16-2004"
        ::= { wmanIfBsOfdmaDownlinkChannelEntry 1 }

wmanIfBsOfdmaChannelNumber OBJECT-TYPE
        SYNTAX      WmanIfChannelNumber
        MAX-ACCESS  read-write
        STATUS      current
        DESCRIPTION
            "Downlink channel number as defined in 8.5. Used for
             license-exempt operation only."
        REFERENCE
            "Subclause 11.4.1, table 358, in IEEE 802.16-2004"
        ::= { wmanIfBsOfdmaDownlinkChannelEntry 2 }

wmanIfBsOfdmaTTG OBJECT-TYPE
        SYNTAX      INTEGER (0..255)
        MAX-ACCESS  read-write
        STATUS      current
        DESCRIPTION
            "Transmit / Receive Transition Gap."
        REFERENCE
            "Subclause 11.4.1, table 358, in IEEE 802.16-2004"
        ::= { wmanIfBsOfdmaDownlinkChannelEntry 3 }

wmanIfBsOfdmaRTG OBJECT-TYPE
        SYNTAX      INTEGER (0..255)
        MAX-ACCESS  read-write
        STATUS      current
        DESCRIPTION
            "Receive / Transmit Transition Gap."
        REFERENCE
            "Subclause 11.4.1, table 358, in IEEE 802.16-2004"
        ::= { wmanIfBsOfdmaDownlinkChannelEntry 4 }

wmanIfBsOfdmaInitRngMaxRSS OBJECT-TYPE
        SYNTAX      INTEGER (0..65535)
        UNITS       "dBm"
        MAX-ACCESS  read-write
        STATUS      current
        DESCRIPTION
            "Initial Ranging Max. Received Signal Strength at BS
             Signed in units of 1 dBm."
        REFERENCE
            "Subclause 11.4.1, table 358, in IEEE 802.16-2004"
        ::= { wmanIfBsOfdmaDownlinkChannelEntry 5 }

wmanIfBsOfdmaDownlinkCenterFreq OBJECT-TYPE
        SYNTAX      Unsigned32
        UNITS       "kHz"
        MAX-ACCESS  read-write
        STATUS      current
        DESCRIPTION
            "Downlink center frequency (kHz)."
        REFERENCE
            "Subclause 11.4.1, table 358, in IEEE 802.16-2004"
        ::= { wmanIfBsOfdmaDownlinkChannelEntry 6 }

wmanIfBsOfdmaBsId OBJECT-TYPE
        SYNTAX      WmanIfBsIdType
        MAX-ACCESS  read-write
        STATUS      current
        DESCRIPTION
            "Base station ID."
        REFERENCE
            "Subclause 11.4.1, table 358, in IEEE 802.16-2004"
        ::= { wmanIfBsOfdmaDownlinkChannelEntry 7 }

wmanIfBsOfdmaMacVersion OBJECT-TYPE
        SYNTAX      WmanIfMacVersion
        MAX-ACCESS  read-write
        STATUS      current
        DESCRIPTION
            "This parameter specifies the version of 802.16 to which
             the message originator conforms."
        REFERENCE
            "Subclause 11.4.1, table 358, in IEEE 802.16-2004"
        ::= { wmanIfBsOfdmaDownlinkChannelEntry 8 }

wmanIfBsOfdmaFrameDurationCode OBJECT-TYPE
        SYNTAX      INTEGER {aASGap(0),
                             duration2ms(1),
                             duration2dot5ms(2),
                             duration4ms(3),
                             duration5ms(4),
                             duration8ms(5),
                             duration10ms(6),
                             duration12dot5ms(7),
                             duration20ms(8)}
        MAX-ACCESS  read-write
        STATUS      current
        DESCRIPTION
            "The duration of the frame. The frame duration code values
             are specified in Table 274."
        REFERENCE
            "Table 273, in IEEE 802.16-2004"
        ::= { wmanIfBsOfdmaDownlinkChannelEntry 9 }

wmanIfBsOfdmaSizeCqichIdField OBJECT-TYPE
        SYNTAX      INTEGER {threebits(1),
                             fourbits(2),
                             fivebits(3),
                             sixbits(4),
                             sevenbits(5),
                             eightbits(6),
                             ninebits(7)}
        MAX-ACCESS  read-write
        STATUS      current
        DESCRIPTION
            "This object defines the size of CQICH ID field.
             0 = Reserved
             1 = 3 bits
             2 = 4 bits
             3 = 5 bits
             4 = 6 bits
             5 = 7 bits
             6 = 8 bits
             7 = 9 bits
             8...255 = Reserved"
        REFERENCE
            "Subclause 11.3.1, table 358, in IEEE 802.16-2004"
        ::= { wmanIfBsOfdmaDownlinkChannelEntry 10 }

wmanIfBsOfdmaHARQAackDelayBurst OBJECT-TYPE
        SYNTAX      INTEGER {oneframeoffset(1),
                             twoframesoffset(2),
                             threeframesoffset(3)}
        MAX-ACCESS  read-write
        STATUS      current
        DESCRIPTION
            "This object defines the OFDMA H-ARQ ACK delay for DL burst. 
             1 = one frame offset
             2 = two frames offset
             3 = three frames offset"
        REFERENCE
            "Subclause 11.3.1, table 358, in IEEE 802.16-2004"
        ::= { wmanIfBsOfdmaDownlinkChannelEntry 11 }

wmanIfBsOfdmaUcdBurstProfileTable OBJECT-TYPE
        SYNTAX      SEQUENCE OF WmanIfBsOfdmaUcdBurstProfileEntry
        MAX-ACCESS  not-accessible
        STATUS      current
        DESCRIPTION
            "This table contains UCD burst profiles for each uplink
             channel"
        REFERENCE
            "Table 356, in IEEE 802.16-2004"
        ::= { wmanIfBsOfdmaPhy 3 }

wmanIfBsOfdmaUcdBurstProfileEntry OBJECT-TYPE
        SYNTAX      WmanIfBsOfdmaUcdBurstProfileEntry
        MAX-ACCESS  not-accessible
        STATUS      current
        DESCRIPTION
            "This table provides one row for each UCD burst profile.
             This table is double indexed. The primary index is an
             ifIndex with an ifType of propBWAp2Mp. The secondary index
             is wmanIfBsOfdmaUiucIndex."
        INDEX       { ifIndex, wmanIfBsOfdmaUiucIndex }
        ::= { wmanIfBsOfdmaUcdBurstProfileTable 1 }

WmanIfBsOfdmaUcdBurstProfileEntry ::= SEQUENCE {
        wmanIfBsOfdmaUiucIndex                  INTEGER,
        wmanIfBsOfdmaUcdFecCodeType             WmanIfOfdmaFecCodeType,
        wmanIfBsOfdmaRangingDataRatio           INTEGER,
        wmanIfBsOfdmaNorCOverNOverride          OCTET STRING,
        wmanIfBsOfdmaUcdBurstProfileRowStatus   RowStatus}

wmanIfBsOfdmaUiucIndex OBJECT-TYPE
        SYNTAX      INTEGER (1 .. 10)
        MAX-ACCESS 	not-accessible
        STATUS      current
        DESCRIPTION
            "The Uplink Interval Usage Code indicates the uplink burst
             profile in the UCD message, and is used along with ifIndex
             to identify an entry in the
             wmanIfBsOfdmaUcdBurstProfileTable."
        REFERENCE
            "Subclause 8.4.5.4.1, in IEEE 802.16-2004"
        ::= { wmanIfBsOfdmaUcdBurstProfileEntry 1 }

wmanIfBsOfdmaUcdFecCodeType OBJECT-TYPE
        SYNTAX      WmanIfOfdmaFecCodeType
        MAX-ACCESS  read-create
        STATUS      current
        DESCRIPTION
            "Uplink FEC code type and modulation type"
        REFERENCE
            "Subclause 11.3.1.1, table 357, in IEEE 802.16-2004"
        ::= { wmanIfBsOfdmaUcdBurstProfileEntry 2 }

wmanIfBsOfdmaRangingDataRatio OBJECT-TYPE
        SYNTAX      INTEGER (0 .. 255)
        MAX-ACCESS  read-create
        STATUS      current
        DESCRIPTION
            "Reducing factor in units of 1 dB, between the power used
             for this burst and power should be used for CDMA Ranging."
        REFERENCE
        "Subclause 11.3.1.1, table 357, in IEEE 802.16-2004"
        ::= { wmanIfBsOfdmaUcdBurstProfileEntry 3 }

wmanIfBsOfdmaNorCOverNOverride OBJECT-TYPE
        SYNTAX 	OCTET STRING (SIZE (5))
        MAX-ACCESS 	read-create
        STATUS 	current
        DESCRIPTION
            "This is a list of numbers, where each number is encoded by
             one nibble, and interpeted as a signed integer. The nibbles
             correspond in order to the list define by Table 334 in
             IEEE 802.16-2004 starting from the second line, such that
             the LS nibble of the first byte corresponds to the second
             line in the table. The number encoded by each nibble
             represents the difference in normalized C/N relative to the
             previous line in the table"
        REFERENCE
            "Subclause 11.3.1.1, table 357, in IEEE 802.16-2004"
        ::= { wmanIfBsOfdmaUcdBurstProfileEntry 4 }

wmanIfBsOfdmaUcdBurstProfileRowStatus OBJECT-TYPE
        SYNTAX      RowStatus
        MAX-ACCESS  read-create
        STATUS      current
        DESCRIPTION
            "This object is used to create a new row or modify or delete
             an existing row in this table. If the implementator of this
             MIB has choosen not to implement 'dynamic assignment' of
             profiles, this object is not useful and should return
             noSuchName upon SNMP request."
        ::= { wmanIfBsOfdmaUcdBurstProfileEntry 5 }

wmanIfBsOfdmaDcdBurstProfileTable OBJECT-TYPE
        SYNTAX      SEQUENCE OF WmanIfBsOfdmaDcdBurstProfileEntry
        MAX-ACCESS  not-accessible
        STATUS      current
        DESCRIPTION
            "This table provides one row for each DCD burst profile.
             This table is double indexed. The primary index is an
             ifIndex with an ifType of propBWAp2Mp. The secondary index
             is wmanIfBsOfdmaDiucIndex."
        ::= { wmanIfBsOfdmaPhy 4 }

wmanIfBsOfdmaDcdBurstProfileEntry OBJECT-TYPE
        SYNTAX      WmanIfBsOfdmaDcdBurstProfileEntry
        MAX-ACCESS  not-accessible
        STATUS      current
        DESCRIPTION
            "This table provides one row for each DCD burst profile.
             This table is double indexed. The primary index is an
             ifIndex with an ifType of propBWAp2Mp. The secondary index
             is wmanIfBsOfdmaDiucIndex."
        INDEX       { ifIndex, wmanIfBsOfdmaDiucIndex }
        ::= { wmanIfBsOfdmaDcdBurstProfileTable 1 }

WmanIfBsOfdmaDcdBurstProfileEntry ::= SEQUENCE {
        wmanIfBsOfdmaDiucIndex                  INTEGER,
        wmanIfBsOfdmaDownlinkFrequency          Unsigned32,
        wmanIfBsOfdmaDcdFecCodeType             WmanIfOfdmaFecCodeType,
        wmanIfBsOfdmaDiucMandatoryExitThresh    INTEGER,
        wmanIfBsOfdmaDiucMinEntryThresh         INTEGER,
        wmanIfBsOfdmaDcdBurstProfileRowStatus   RowStatus}
                                                
wmanIfBsOfdmaDiucIndex OBJECT-TYPE
        SYNTAX      INTEGER (0 .. 12)
        MAX-ACCESS  not-accessible
        STATUS      current
        DESCRIPTION
            "The Downlink Interval Usage Code indicates the downlink
             burst profile in the DCD message, and is used along with
             ifIndex to identify an entry in the
             wmanIfBsOfdmaDcdBurstProfileTable."
        REFERENCE
            "Subclause 8.4.5.3.1, in IEEE 802.16-2004"
        ::= { wmanIfBsOfdmaDcdBurstProfileEntry 1 }

wmanIfBsOfdmaDownlinkFrequency OBJECT-TYPE
        SYNTAX      Unsigned32
        UNITS       "kHz"
        MAX-ACCESS  read-create
        STATUS      current
        DESCRIPTION
            "Downlink Frequency (kHz)."
        REFERENCE
            "Subclause 11.4.2, table 359, in IEEE 802.16-2004"
        ::= { wmanIfBsOfdmaDcdBurstProfileEntry 2 }

wmanIfBsOfdmaDcdFecCodeType OBJECT-TYPE
        SYNTAX      WmanIfOfdmaFecCodeType
        MAX-ACCESS  read-create
        STATUS      current
        DESCRIPTION
            "Downlink FEC code type and modulation type"
        REFERENCE
            "Subclause 11.4.2, table 363, in IEEE 802.16-2004"
        ::= { wmanIfBsOfdmaDcdBurstProfileEntry 3 }

wmanIfBsOfdmaDiucMandatoryExitThresh OBJECT-TYPE
        SYNTAX      INTEGER (0..255)
        MAX-ACCESS  read-create
        STATUS      current
        DESCRIPTION
            "DIUC mandatory exit threshold: 0 - 63.75 dB CINR at or
             below where this DIUC can no longer be used and where
             this change to a more robust DIUC is required, in 0.25
             dB units."
        REFERENCE
            "Subclause 11.4.2, table 363, in IEEE 802.16-2004"
        ::= { wmanIfBsOfdmaDcdBurstProfileEntry 4 }

wmanIfBsOfdmaDiucMinEntryThresh OBJECT-TYPE
        SYNTAX      INTEGER (0..255)
        MAX-ACCESS  read-create
        STATUS      current
        DESCRIPTION
            "DIUC minimum entry threshold: 0 - 63.75 dB The minimum
             CINR required to start using this DIUC when changing from
             a more robust DIUC is required, in 0.25 dB units."
        REFERENCE
            "Subclause 11.4.2, table 363, in IEEE 802.16-2004"
        ::= { wmanIfBsOfdmaDcdBurstProfileEntry 5 }
        
wmanIfBsOfdmaDcdBurstProfileRowStatus OBJECT-TYPE
        SYNTAX      RowStatus
        MAX-ACCESS  read-create
        STATUS      current
        DESCRIPTION
            "This object is used to create a new row or modify or delete
             an existing row in this table. If the implementator of this
             MIB has choosen not to implement 'dynamic assignment' of
             profiles, this object is not useful and should return
             noSuchName upon SNMP request."
        ::= { wmanIfBsOfdmaDcdBurstProfileEntry 6 }
                
--
-- SS object group – containing tables and objects to be implemented in 
-- the Subscriber station

--
-- wmanIfSsCps contain the SS Common Part Sublayer objects
--
wmanIfSsCps OBJECT IDENTIFIER ::= { wmanIfSsObjects 1 } 
        
--
-- wmanIfSsConfigurationTable contains global parameters for SS      
--
wmanIfSsConfigurationTable OBJECT-TYPE
        SYNTAX      SEQUENCE OF WmanIfSsConfigurationEntry
        MAX-ACCESS  not-accessible
        STATUS      current
        DESCRIPTION
            "This table contains one row for the SS system
             parameters."
        REFERENCE
            "Subclause 10.1 in IEEE 802.16-2004"
        ::= { wmanIfSsCps 1 }

wmanIfSsConfigurationEntry OBJECT-TYPE
        SYNTAX      WmanIfSsConfigurationEntry
        MAX-ACCESS  not-accessible
        STATUS      current
        DESCRIPTION
            "This table is indexed by ifIndex."
        INDEX { ifIndex }
        ::= { wmanIfSsConfigurationTable 1 }

WmanIfSsConfigurationEntry ::= SEQUENCE {
        wmanIfSsLostDLMapInterval               INTEGER,
        wmanIfSsLostULMapInterval               INTEGER,
        wmanIfSsContentionRangRetries           INTEGER,
        wmanIfSsRequestRetries                  INTEGER,
        wmanIfSsRegRequestRetries               INTEGER,
        wmanIfSsTftpBackoffStart                INTEGER,
        wmanIfSsTftpBackoffEnd                  INTEGER,
        wmanIfSsTftpRequestRetries              INTEGER,
        wmanIfSsTftpDownloadRetries             INTEGER,
        wmanIfSsTftpWait                        INTEGER,
        wmanIfSsToDRetries                      INTEGER,
        wmanIfSsToDRetryPeriod                  INTEGER,
        wmanIfSsT1Timeout                       INTEGER,
        wmanIfSsT2Timeout                       INTEGER,
        wmanIfSsT3Timeout                       INTEGER,
        wmanIfSsT4Timeout                       INTEGER,
        wmanIfSsT6Timeout                       INTEGER,
        wmanIfSsT12Timeout                      INTEGER,
        wmanIfSsT14Timeout                      INTEGER,
        wmanIfSsT16Timeout                      INTEGER,
        wmanIfSsT18Timeout                      INTEGER,
        wmanIfSsT19Timeout                      INTEGER,
        wmanIfSsT20Timeout                      INTEGER,
        wmanIfSsT21Timeout                      INTEGER,
        wmanIfSsSBCRequestRetries               INTEGER,
        wmanIfSsTftpCpltRetries                 INTEGER,
        wmanIfSsT26Timeout                      INTEGER,
        wmanIfSsDLManagProcTime                 INTEGER}
                    
wmanIfSsLostDLMapInterval OBJECT-TYPE
        SYNTAX      INTEGER (0..600)
        UNITS       "milliseconds"
        MAX-ACCESS  read-write
        STATUS      current
        DESCRIPTION
        	"Time since last received DL-MAP message before downlink
             synchronization is considered lost in ms."
        ::= { wmanIfSsConfigurationEntry 1 }

wmanIfSsLostULMapInterval OBJECT-TYPE
        SYNTAX      INTEGER (0..600)
        UNITS       "milliseconds"
        MAX-ACCESS  read-write
        STATUS      current
        DESCRIPTION
        	"Time since last received UL-MAP message before uplink
        	 synchronization is considered lost in ms."
        ::= { wmanIfSsConfigurationEntry 2 }

wmanIfSsContentionRangRetries OBJECT-TYPE
        SYNTAX      INTEGER (16..65535)
        MAX-ACCESS  read-write
        STATUS      current
        DESCRIPTION
        	"Number of retries on contention Ranging Requests."
        ::= { wmanIfSsConfigurationEntry 3 }

wmanIfSsRequestRetries OBJECT-TYPE
        SYNTAX      INTEGER (16..65535)
        MAX-ACCESS  read-write
        STATUS      current
        DESCRIPTION
        	"Number of retries on bandwidth allocation requests."
        ::= { wmanIfSsConfigurationEntry 4 }

wmanIfSsRegRequestRetries OBJECT-TYPE
        SYNTAX      INTEGER (3..65535)
        MAX-ACCESS  read-write
        STATUS      current
        DESCRIPTION
        	"Number of retries on registration requests."
        ::= { wmanIfSsConfigurationEntry 5 }

wmanIfSsTftpBackoffStart OBJECT-TYPE
        SYNTAX      INTEGER (1..65535)
        UNITS       "seconds"
        MAX-ACCESS  read-write
        STATUS      current
        DESCRIPTION
        	"Initial value for TFTP backoff in second."
        ::= { wmanIfSsConfigurationEntry 6 }

wmanIfSsTftpBackoffEnd OBJECT-TYPE
        SYNTAX      INTEGER (16..65535)
        UNITS       "seconds"
        MAX-ACCESS  read-write
        STATUS      current
        DESCRIPTION
        	"Last value for TFTP backoff in second."
        ::= { wmanIfSsConfigurationEntry 7 }

wmanIfSsTftpRequestRetries OBJECT-TYPE
        SYNTAX      INTEGER (16..65535)
        MAX-ACCESS  read-write
        STATUS      current
        DESCRIPTION
        	"Number of retries on TFTP request."
        ::= { wmanIfSsConfigurationEntry 8 }

wmanIfSsTftpDownloadRetries OBJECT-TYPE
        SYNTAX      INTEGER (3..65535)
        MAX-ACCESS  read-write
        STATUS      current
        DESCRIPTION
        	"Number of retries on entire TFTP downloads."
        ::= { wmanIfSsConfigurationEntry 9 }

wmanIfSsTftpWait OBJECT-TYPE
        SYNTAX      INTEGER (2..65535)
        UNITS       "minutes"
        MAX-ACCESS  read-write
        STATUS      current
        DESCRIPTION
        	"The duration between two consecutive Transfer
        	 operational parameters (TFTP) retries in min."
        ::= { wmanIfSsConfigurationEntry 10 }

wmanIfSsToDRetries OBJECT-TYPE
        SYNTAX      INTEGER (3..65535)
        MAX-ACCESS  read-write
        STATUS      current
        DESCRIPTION
        	"Number of Retries to establisg the Time of Day."
        ::= { wmanIfSsConfigurationEntry 11 }

wmanIfSsToDRetryPeriod OBJECT-TYPE
        SYNTAX      INTEGER (5..65535)
        UNITS       "minutes"
        MAX-ACCESS  read-write
        STATUS      current
        DESCRIPTION
        	"The retry period to re-establisg the Time of Day, as
        	 describe in the network entry procedure."
        ::= { wmanIfSsConfigurationEntry 12 }

wmanIfSsT1Timeout OBJECT-TYPE
        SYNTAX      INTEGER (0..50000)
        UNITS       "milliseconds"
        MAX-ACCESS  read-write
        STATUS      current
        DESCRIPTION
        	"Wait for DCD timeout in ms."
        ::= { wmanIfSsConfigurationEntry 13 }

wmanIfSsT2Timeout OBJECT-TYPE
        SYNTAX      INTEGER (0..10000)
        UNITS       "milliseconds"
        MAX-ACCESS  read-write
        STATUS      current
        DESCRIPTION
        	"Wait for broadcast ranging timeout in ms."
        ::= { wmanIfSsConfigurationEntry 14 }

wmanIfSsT3Timeout OBJECT-TYPE
        SYNTAX      INTEGER (0..200)
        UNITS       "milliseconds"
        MAX-ACCESS  read-write
        STATUS      current
        DESCRIPTION
        	"Ranging Response reception timeout following the 
        	 transmission of a Ranging Request in ms."
        ::= { wmanIfSsConfigurationEntry 15 }

wmanIfSsT4Timeout OBJECT-TYPE
        SYNTAX      INTEGER (30..35)
        UNITS       "seconds"
        MAX-ACCESS  read-write
        STATUS      current
        DESCRIPTION
        	"Wait for unicast ranging opportunity. If the pending until
        	 complete field was used earlier by this SS, then the value
        	 of that field shall be added to this interval in second."
        ::= { wmanIfSsConfigurationEntry 16 }

wmanIfSsT6Timeout OBJECT-TYPE
        SYNTAX      INTEGER (0..3000)
        UNITS       "milliseconds"
        MAX-ACCESS  read-write
        STATUS      current
        DESCRIPTION
        	"Wait for registration response in ms."
        ::= { wmanIfSsConfigurationEntry 17 }

wmanIfSsT12Timeout OBJECT-TYPE
        SYNTAX      INTEGER (0..50000)
        UNITS       "milliseconds"
        MAX-ACCESS  read-write
        STATUS      current
        DESCRIPTION
        	"Wait for UCD descriptor in ms."
        ::= { wmanIfSsConfigurationEntry 18 }

wmanIfSsT14Timeout OBJECT-TYPE
        SYNTAX      INTEGER (0..200)
        UNITS       "milliseconds"
        MAX-ACCESS  read-write
        STATUS      current
        DESCRIPTION
        	"Wait for DSX-RVD Timeout in ms."
        ::= { wmanIfSsConfigurationEntry 19 }

wmanIfSsT16Timeout OBJECT-TYPE
        SYNTAX      INTEGER (10..65535)
        UNITS       "milliseconds"
        MAX-ACCESS  read-write
        STATUS      current
        DESCRIPTION
        	"wait for bandwidth request grant in ms."
        ::= { wmanIfSsConfigurationEntry 20 }

wmanIfSsT18Timeout OBJECT-TYPE
        SYNTAX      INTEGER (0..65535)
        UNITS       "milliseconds"
        MAX-ACCESS  read-write
        STATUS      current
        DESCRIPTION
        	"wait for SBC-RSP timeout in ms."
        ::= { wmanIfSsConfigurationEntry 21 }

wmanIfSsT19Timeout OBJECT-TYPE
        SYNTAX      INTEGER (0..1048575)
        UNITS       "milliseconds"
        MAX-ACCESS  read-write
        STATUS      current
        DESCRIPTION
        	"Time DL-channel remains unusable in ms."
        ::= { wmanIfSsConfigurationEntry 22 }

wmanIfSsT20Timeout OBJECT-TYPE
        SYNTAX      INTEGER (0..65535)
        UNITS       "milliseconds"
        MAX-ACCESS  read-write
        STATUS      current
        DESCRIPTION
        	"Time SS searches for preambles on a given channel in ms."
        ::= { wmanIfSsConfigurationEntry 23 }

wmanIfSsT21Timeout OBJECT-TYPE
        SYNTAX      INTEGER (0..10000)
        UNITS       "milliseconds"
        MAX-ACCESS  read-write
        STATUS      current
        DESCRIPTION
        	"Time SS searches for DL-MAP on a given channel in ms."
        ::= { wmanIfSsConfigurationEntry 24 }

wmanIfSsSBCRequestRetries OBJECT-TYPE
        SYNTAX      INTEGER (3..16)
        MAX-ACCESS  read-write
        STATUS      current
        DESCRIPTION
        	"Number of retries on SBC Request."
        ::= { wmanIfSsConfigurationEntry 25 }

wmanIfSsTftpCpltRetries OBJECT-TYPE
        SYNTAX      INTEGER (3..16)
        MAX-ACCESS  read-write
        STATUS      current
        DESCRIPTION
        	"Number of retries on TFTP-CPLT."
        ::= { wmanIfSsConfigurationEntry 26 }

wmanIfSsT26Timeout OBJECT-TYPE
        SYNTAX      INTEGER (10..200)
        UNITS       "milliseconds"
        MAX-ACCESS  read-write
        STATUS      current
        DESCRIPTION
        	"Wait for TFTP-RSP in ms."
        ::= { wmanIfSsConfigurationEntry 27 }

wmanIfSsDLManagProcTime OBJECT-TYPE
        SYNTAX      INTEGER (0..200)
        UNITS       "micro seconds"
        MAX-ACCESS  read-write
        STATUS      current
        DESCRIPTION
        	"Max. time between reception of Fast Power Control 
        	 management message and compliance to its instructions
        	 by SS in us."
        ::= { wmanIfSsConfigurationEntry 28 }        

--
-- Subscriber Channel Measurement Table         
--
wmanIfSsChannelMeasurementTable OBJECT-TYPE
        SYNTAX      SEQUENCE OF   WmanIfSsChannelMeasurementEntry
        MAX-ACCESS  not-accessible
        STATUS      current
        DESCRIPTION
            "This table contains downlink channel measurement
             information for each SS."
        REFERENCE
            "6.3.2.3.33 in IEEE 802.16-2004"
        ::= { wmanIfSsCps 2 }

wmanIfSsChannelMeasurementEntry OBJECT-TYPE
        SYNTAX      WmanIfSsChannelMeasurementEntry
        MAX-ACCESS  not-accessible
        STATUS      current
        DESCRIPTION
            "Each entry in the table contains RSSI and CINR
             signal quality measurement taken from the SS. The primary
             index is the ifIndex pointing to SS.
             wmanIfCmnHistogramIndex is the index to histogram
             samples. Since there is no time stamp in the table,
             wmanIfCmnHistogramIndex should be increased monotonically,
             and wraps around when it reaches the limit.
             When the measurement entry for a SS reaches the limit,
             the oldest entry shall be deleted as the new entry is
             added to the table."
        INDEX       { ifIndex, wmanIfSsHistogramIndex }
        ::= { wmanIfSsChannelMeasurementTable  1 }

WmanIfSsChannelMeasurementEntry ::= SEQUENCE {
        wmanIfSsHistogramIndex                  Unsigned32,
        wmanIfSsChannelNumber                   WmanIfChannelNumber,
        wmanIfSsStartFrame                      INTEGER,
        wmanIfSsDuration                        INTEGER,
        wmanIfSsBasicReport                     BITS,
        wmanIfSsMeanCinrReport                  INTEGER,
        wmanIfSsStdDeviationCinrReport          INTEGER,
        wmanIfSsMeanRssiReport                  INTEGER,
        wmanIfSsStdDeviationRssiReport          INTEGER}
               
wmanIfSsHistogramIndex OBJECT-TYPE
        SYNTAX      Unsigned32 (1 .. 4294967295) 
        MAX-ACCESS  not-accessible
        STATUS      current
        DESCRIPTION
            "wmanIfSsHistogramIndex identifies the histogram samples
             in the table for each subscriber station."
        ::= { wmanIfSsChannelMeasurementEntry 1 }
                
wmanIfSsChannelNumber OBJECT-TYPE
        SYNTAX      WmanIfChannelNumber 
        MAX-ACCESS  read-only
        STATUS      current
        DESCRIPTION
            "Physical channel number to be reported on."
        REFERENCE
            "Subclause 8.5.1 in IEEE 802.16-2004"
        ::= { wmanIfSsChannelMeasurementEntry 2 }
               
wmanIfSsStartFrame OBJECT-TYPE
        SYNTAX      INTEGER (0 .. 65535) 
        MAX-ACCESS  read-only
        STATUS      current
        DESCRIPTION
            "Frame number in which measurement for this channel
             started."
        REFERENCE
            "Subclause 11.12 in IEEE 802.16-2004"
        ::= { wmanIfSsChannelMeasurementEntry 3 }
                
wmanIfSsDuration OBJECT-TYPE
        SYNTAX      INTEGER (0..16777215) 
        MAX-ACCESS  read-only
        STATUS      current
        DESCRIPTION
            "Cumulative measurement duration on the channel in
             multiples of Ts. For any value exceeding 0xFFFFFF,
             report 0xFFFFFF."
        REFERENCE
            "Subclause 11.12 in IEEE 802.16-2004"
        ::= { wmanIfSsChannelMeasurementEntry 4 }
                        
wmanIfSsBasicReport OBJECT-TYPE
        SYNTAX      BITS {wirelessHuman(0),
                          unknownTransmission(1),
                          primaryUser(2),
                          channelNotMeasured(3)}                          
        MAX-ACCESS  read-only
        STATUS      current
        DESCRIPTION
            "Bit #0: WirelessHUMAN detected on the channel
             Bit #1: Unknown transmissions detected on the channel
             Bit #2: Primary User detected on the channel
             Bit #3: Unmeasured. Channel not measured"
        REFERENCE
            "Subclause 11.12 in IEEE 802.16-2004"
        ::= { wmanIfSsChannelMeasurementEntry 5 }                        
                                          
wmanIfSsMeanCinrReport OBJECT-TYPE
        SYNTAX      INTEGER (0 .. 41)
        UNITS       "dB"         
        MAX-ACCESS  read-only
        STATUS      current
        DESCRIPTION
            "Mean CINR report."
        REFERENCE
            "Subclause 8.2.2, 8.3.9 in IEEE 802.16-2004"
        ::= { wmanIfSsChannelMeasurementEntry 6 }
        
wmanIfSsStdDeviationCinrReport OBJECT-TYPE
        SYNTAX      INTEGER (0 .. 41) 
        UNITS       "dB"
        MAX-ACCESS  read-only
        STATUS      current
        DESCRIPTION
            "Standard deviation CINR report."
        REFERENCE
            "Subclause 8.2.2, 8.3.9 in IEEE 802.16-2004"
        ::= { wmanIfSsChannelMeasurementEntry 7 }
                                          
wmanIfSsMeanRssiReport OBJECT-TYPE
        SYNTAX      INTEGER (0 .. 83)
        UNITS       "dBm" 
        MAX-ACCESS  read-only
        STATUS      current
        DESCRIPTION
            "Mean RSSI report."
        REFERENCE
            "Subclause 8.2.2, 8.3.9 in IEEE 802.16-2004"
        ::= { wmanIfSsChannelMeasurementEntry 8 }
        
wmanIfSsStdDeviationRssiReport OBJECT-TYPE
        SYNTAX      INTEGER (0 .. 83)
        UNITS       "dB" 
        MAX-ACCESS  read-only
        STATUS      current
        DESCRIPTION
            "Standard deviation RSSI report."
        REFERENCE
            "Subclause 8.2.2, 8.3.9 in IEEE 802.16-2004"
        ::= { wmanIfSsChannelMeasurementEntry 9 }
         
--
-- Subscriber station PKM group
-- wmanIfSsPkmObjects contain the Subscriber Station Privacy Sublayer
-- objects
--
wmanIfSsPkmObjects OBJECT IDENTIFIER ::= { wmanIfSsObjects  2 }

--
-- Table wmanIfSsPkmAuthTable
--
wmanIfSsPkmAuthTable OBJECT-TYPE
        SYNTAX      SEQUENCE OF   WmanIfSsPkmAuthEntry
        MAX-ACCESS  not-accessible
        STATUS      current
        DESCRIPTION
            "This table describes the PKM attributes related
             to the authorization for each SS wireless interface."
        ::= { wmanIfSsPkmObjects  1 }

wmanIfSsPkmAuthEntry OBJECT-TYPE
        SYNTAX      WmanIfSsPkmAuthEntry
        MAX-ACCESS  not-accessible
        STATUS      current
        DESCRIPTION
            "Each entry contains objects describing attributes of one
             SS wireless interface."
        INDEX       { ifIndex }
        ::= { wmanIfSsPkmAuthTable  1 }

WmanIfSsPkmAuthEntry ::= SEQUENCE {
        wmanIfSsPkmAuthState                    INTEGER,
        wmanIfSsPkmAuthKeySequenceNumber        Integer32,
        wmanIfSsPkmAuthExpiresOld               DateAndTime,
        wmanIfSsPkmAuthExpiresNew               DateAndTime,
        wmanIfSsPkmAuthReset                    TruthValue,
        wmanIfSsPkmAuthentInfos                 Counter32,
        wmanIfSsPkmAuthRequests                 Counter32,
        wmanIfSsPkmAuthReplies                  Counter32,
        wmanIfSsPkmAuthRejects                  Counter32,
        wmanIfSsPkmAuthInvalids                 Counter32,
        wmanIfSsPkmAuthRejectErrorCode          INTEGER,
        wmanIfSsPkmAuthRejectErrorString        SnmpAdminString,
        wmanIfSsPkmAuthInvalidErrorCode         INTEGER,
        wmanIfSsPkmAuthInvalidErrorString       SnmpAdminString,
        wmanIfSsPkmAuthGraceTime                Integer32,
        wmanIfSsPkmTekGraceTime                 Integer32,
        wmanIfSsPkmAuthWaitTimeout              Integer32,
        wmanIfSsPkmReauthWaitTimeout            Integer32,
        wmanIfSsPkmOpWaitTimeout                Integer32,
        wmanIfSsPkmRekeyWaitTimeout             Integer32,
        wmanIfSsPkmAuthRejectWaitTimeout        Integer32}
                
wmanIfSsPkmAuthState OBJECT-TYPE
        SYNTAX      INTEGER {start(1),
                             authWait(2),
                             authorized(3),
                             reauthWait(4),
                             authRejectWait(5),
                             silent(6)}
        MAX-ACCESS  read-only
        STATUS      current
        DESCRIPTION
            "The value of this object is the state of the SS
             authorization FSM.  The start state indicates that FSM is
             in its initial state."
        ::= { wmanIfSsPkmAuthEntry 1 }

wmanIfSsPkmAuthKeySequenceNumber OBJECT-TYPE
        SYNTAX      Integer32 (0..15)
        MAX-ACCESS  read-only
        STATUS      current
        DESCRIPTION
            "The value of this object is the most recent authorization
             key sequence number for this FSM."
        ::= { wmanIfSsPkmAuthEntry 2 }

wmanIfSsPkmAuthExpiresOld OBJECT-TYPE
        SYNTAX      DateAndTime                       
        MAX-ACCESS  read-only
        STATUS      current
        DESCRIPTION
            "The value of this object is the actual clock time for
             expiration of the immediate predecessor of the most recent
             authorization key for this FSM.  If this FSM has only one
             authorization key, then the value is the time of activation
             of this FSM."
        ::= { wmanIfSsPkmAuthEntry 3 }

wmanIfSsPkmAuthExpiresNew OBJECT-TYPE
        SYNTAX      DateAndTime                        
        MAX-ACCESS  read-only
        STATUS      current
        DESCRIPTION
            "The value of this object is the actual clock time for
             expiration of the most recent authorization key for this
             FSM."
        ::= { wmanIfSsPkmAuthEntry 4 }

wmanIfSsPkmAuthReset OBJECT-TYPE
        SYNTAX      TruthValue                       
        MAX-ACCESS  read-write
        STATUS      current
        DESCRIPTION 
            "Setting this object to TRUE generates a Reauthorize event
             in the authorization FSM. Reading this object always
             returns FALSE."
        ::= { wmanIfSsPkmAuthEntry 5 }
                
wmanIfSsPkmAuthentInfos OBJECT-TYPE
        SYNTAX      Counter32 
        MAX-ACCESS  read-only
        STATUS      current
        DESCRIPTION
            "The value of this object is the count of times the SS has
             transmitted an Authentication Information message."
        ::= { wmanIfSsPkmAuthEntry 6 }

wmanIfSsPkmAuthRequests OBJECT-TYPE
        SYNTAX      Counter32 
        MAX-ACCESS  read-only
        STATUS      current
        DESCRIPTION
            "The value of this object is the count of times the SS has
             transmitted an Authorization Request message."
        ::= { wmanIfSsPkmAuthEntry 7 }

wmanIfSsPkmAuthReplies OBJECT-TYPE
        SYNTAX      Counter32 
        MAX-ACCESS  read-only
        STATUS      current
        DESCRIPTION
            "The value of this object is the count of times the SS has
             received an Authorization Reply message."
        ::= { wmanIfSsPkmAuthEntry 8 }

wmanIfSsPkmAuthRejects OBJECT-TYPE
        SYNTAX      Counter32 
        MAX-ACCESS  read-only
        STATUS      current
        DESCRIPTION
            "The value of this object is the count of times the SS has
             received an Authorization Reject message."
        ::= { wmanIfSsPkmAuthEntry 9 }

wmanIfSsPkmAuthInvalids OBJECT-TYPE
        SYNTAX      Counter32 
        MAX-ACCESS  read-only
        STATUS      current
        DESCRIPTION
            "The value of this object is the count of times the SS has
             received an Authorization Invalid message."
        ::= { wmanIfSsPkmAuthEntry 10 }

wmanIfSsPkmAuthRejectErrorCode OBJECT-TYPE
        SYNTAX      INTEGER {none(1),
                             unknown(2),
                             unauthorizedSs(3),
                             unauthorizedSaid(4),
                             permanentAuthorizationFailure(8),
                             timeOfDayNotAcquired(11)}
        MAX-ACCESS  read-only
        STATUS      current
        DESCRIPTION
            "The value of this object is the enumerated description of
             the Error-Code in most recent Authorization Reject message
             received by the SS.  This has value unknown(2)if the last
             Error-Code value was 0, and none(1) if no Authorization
             Reject message has been received since reboot."
        ::= { wmanIfSsPkmAuthEntry 11 }

wmanIfSsPkmAuthRejectErrorString OBJECT-TYPE
        SYNTAX      SnmpAdminString (SIZE (0..128))
        MAX-ACCESS  read-only
        STATUS      current
        DESCRIPTION 
            "The value of this object is the Display-String in most
             recent Authorization Reject message received by the SS.
             This is a zero length string if no Authorization Reject
             message has been received since reboot."
        ::= { wmanIfSsPkmAuthEntry 12 }

wmanIfSsPkmAuthInvalidErrorCode OBJECT-TYPE
        SYNTAX      INTEGER {none(1),
                             unknown(2),
                             unauthorizedSs(3),
                             unsolicited(5),
                             invalidKeySequence(6),
                             keyRequestAuthenticationFailure(7)}
        MAX-ACCESS  read-only
        STATUS      current
        DESCRIPTION
            "The value of this object is the enumerated description of
             the Error-Code in most recent Authorization Invalid message
             received by the SS.  This has value unknown(2) if the last
             Error-Code value was 0, and none(1) if no Authorization
             Invalid message has been received since reboot."
        ::= { wmanIfSsPkmAuthEntry 13 }

wmanIfSsPkmAuthInvalidErrorString OBJECT-TYPE
        SYNTAX      SnmpAdminString (SIZE (0..128))
        MAX-ACCESS  read-only
        STATUS      current
        DESCRIPTION
            "The value of this object is the Display-String in most
             recent Authorization Invalid message received by the SS.
             This is a zero length string if no Authorization Invalid
             message has been received since reboot."
        ::= { wmanIfSsPkmAuthEntry 14 }        

wmanIfSsPkmAuthGraceTime OBJECT-TYPE
        SYNTAX      Integer32 (300..3024000)
        UNITS       "seconds"
        MAX-ACCESS  read-only
        STATUS      current
        DESCRIPTION
            "The value of this object is the grace time for an
             authorization key.  A SS is expected to start trying to get
             a new authorization key beginning AuthGraceTime seconds
             before the authorization key actually expires."
        REFERENCE
            "Table 341 in IEEE 802.16-2004"
        DEFVAL      { 600 }
        ::= { wmanIfSsPkmAuthEntry 15 }

wmanIfSsPkmTekGraceTime OBJECT-TYPE
        SYNTAX      Integer32 (300..3024000)
        UNITS       "seconds"
        MAX-ACCESS  read-only
        STATUS      current
        DESCRIPTION
            "The value of this object is the grace time for the TEK in
             seconds. The SS is expected to start trying to acquire a
             new TEK beginning TEK GraceTime seconds before the
             expiration of the most recent TEK."
        REFERENCE
            "Table 341 in IEEE 802.16-2004"
        DEFVAL      { 3600 }
        ::= { wmanIfSsPkmAuthEntry 16 }

wmanIfSsPkmAuthWaitTimeout OBJECT-TYPE
        SYNTAX      Integer32 (2..30)
        UNITS       "seconds"
        MAX-ACCESS  read-only
        STATUS      current
        DESCRIPTION
            "The value of this object is the Authorize Wait Timeout."
        REFERENCE
            "Table 341 in IEEE 802.16-2004"
        DEFVAL      { 10 }
        ::= { wmanIfSsPkmAuthEntry 17 }

wmanIfSsPkmReauthWaitTimeout OBJECT-TYPE
        SYNTAX      Integer32 (2..30)
        UNITS       "seconds"
        MAX-ACCESS  read-only
        STATUS      current
        DESCRIPTION
            "The value of this object is the Reauthorize Wait Timeout
             in seconds."
        REFERENCE
            "Table 341 in IEEE 802.16-2004"
        DEFVAL      { 10 }
        ::= { wmanIfSsPkmAuthEntry 18 }

wmanIfSsPkmOpWaitTimeout OBJECT-TYPE
        SYNTAX      Integer32 (1..10)
        UNITS       "seconds"
        MAX-ACCESS  read-only
        STATUS      current
        DESCRIPTION
            "The value of this object is the Operational Wait Timeout
             in seconds."
        REFERENCE
            "Table 341 in IEEE 802.16-2004"
        DEFVAL      { 1 }
        ::= { wmanIfSsPkmAuthEntry 19 }

wmanIfSsPkmRekeyWaitTimeout OBJECT-TYPE
        SYNTAX      Integer32 (1..10)
        UNITS       "seconds"
        MAX-ACCESS  read-only
        STATUS      current
        DESCRIPTION
            "The value of this object is the Rekey Wait Timeout in
             seconds."
        REFERENCE
            "Table 341 in IEEE 802.16-2004"
        DEFVAL      { 1 }
        ::= { wmanIfSsPkmAuthEntry 20 }

wmanIfSsPkmAuthRejectWaitTimeout OBJECT-TYPE
        SYNTAX      Integer32 (10..600)
        UNITS       "seconds"
        MAX-ACCESS  read-only
        STATUS      current
        DESCRIPTION
            "The value of this object is the Authorization Reject Wait
             Timeout in seconds."
        REFERENCE
             "Table 341 in IEEE 802.16-2004"
        DEFVAL      { 60 }
        ::= { wmanIfSsPkmAuthEntry 21 }
                
--
-- Table wmanIfSsPkmTekTable
--
wmanIfSsPkmTekTable OBJECT-TYPE
        SYNTAX      SEQUENCE OF   WmanIfSsPkmTekEntry
        MAX-ACCESS  not-accessible
        STATUS      current
        DESCRIPTION
            "This table describes the attributes of each SS Traffic
             Encryption Key(TEK) association. The SS maintains (no more
             than) one TEK association per SAID per SS wireless
             interface."
        ::= { wmanIfSsPkmObjects  2 }

wmanIfSsPkmTekEntry OBJECT-TYPE
        SYNTAX      WmanIfSsPkmTekEntry
        MAX-ACCESS  not-accessible
        STATUS      current
        DESCRIPTION                    
            "Each entry contains objects describing the TEK association
              attributes of one SAID. The SS MUST create one entry per
              SAID, regardless of whether the SAID was obtained from a
              Registration Response message, from an Authorization Reply
              message, or from any dynamic SAID establishment
              mechanisms."
        INDEX       { ifIndex, wmanIfSsPkmTekSAId }
        ::= { wmanIfSsPkmTekTable  1 }

WmanIfSsPkmTekEntry ::= SEQUENCE {
        wmanIfSsPkmTekSAId                      INTEGER,
        wmanIfSsPkmTekSAType                    INTEGER,
        wmanIfSsPkmTekDataEncryptAlg            WmanIfDataEncryptAlgId,
        wmanIfSsPkmTekDataAuthentAlg            WmanIfDataAuthAlgId,
        wmanIfSsPkmTekEncryptAlg                WmanIfTekEncryptAlgId,
        wmanIfSsPkmTekState                     INTEGER,
        wmanIfSsPkmTekKeySequenceNumber         Integer32,
        wmanIfSsPkmTekExpiresOld                DateAndTime,
        wmanIfSsPkmTekExpiresNew                DateAndTime,
        wmanIfSsPkmTekKeyRequests               Counter32,
        wmanIfSsPkmTekKeyReplies                Counter32,
        wmanIfSsPkmTekKeyRejects                Counter32,
        wmanIfSsPkmTekInvalids                  Counter32,
        wmanIfSsPkmTekAuthPends                 Counter32,
        wmanIfSsPkmTekKeyRejectErrorCode        INTEGER,
        wmanIfSsPkmTekKeyRejectErrorString      SnmpAdminString,
        wmanIfSsPkmTekInvalidErrorCode          INTEGER,
        wmanIfSsPkmTekInvalidErrorString        SnmpAdminString}

wmanIfSsPkmTekSAId OBJECT-TYPE
        SYNTAX      INTEGER (0..65535)
        MAX-ACCESS  not-accessible
        STATUS      current
        DESCRIPTION
            "The value of this object is the Security Association
             ID (SAID)."
        ::= { wmanIfSsPkmTekEntry 1 }

wmanIfSsPkmTekSAType OBJECT-TYPE
        SYNTAX      INTEGER {primarySA(0),
                             staticSA(1),
                             dynamicSA(2)}
        MAX-ACCESS  read-only
        STATUS      current
        DESCRIPTION
            "The value of this object is the type of security
             association."
        REFERENCE
            "IEEE 802.16-2004; 11.9.18"
        ::= { wmanIfSsPkmTekEntry 2 }

wmanIfSsPkmTekDataEncryptAlg OBJECT-TYPE
        SYNTAX      WmanIfDataEncryptAlgId
        MAX-ACCESS  read-only
        STATUS      current
        DESCRIPTION
            "The value of this object is the data encryption algorithm
             being utilized."
        REFERENCE
            "Table 375, IEEE 802.16-2004"
        ::= { wmanIfSsPkmTekEntry 3 }

wmanIfSsPkmTekDataAuthentAlg OBJECT-TYPE
        SYNTAX      WmanIfDataAuthAlgId
        MAX-ACCESS  read-only
        STATUS      current
        DESCRIPTION
            "The value of this object is the data authentication
             algorithm being utilized."
        REFERENCE
            "Table 376, IEEE 802.16-2004"
        ::= { wmanIfSsPkmTekEntry 4 }

wmanIfSsPkmTekEncryptAlg OBJECT-TYPE
        SYNTAX      WmanIfTekEncryptAlgId
        MAX-ACCESS  read-only
        STATUS      current
        DESCRIPTION
            "The value of this object is the TEK key encryption
             algorithm for this cryptographic suite capability."
        REFERENCE
            "Table 377, IEEE 802.16-2004"
        ::= { wmanIfSsPkmTekEntry 5 }

wmanIfSsPkmTekState OBJECT-TYPE
        SYNTAX      INTEGER {start(1),
                             opWait(2),
                             opReauthWait(3),
                             operational(4),
                             rekeyWait(5),
                             rekeyReauthWait(6)}
        MAX-ACCESS  read-only
        STATUS      current
        DESCRIPTION
            "The value of this object is the state of the indicated TEK
             FSM. The start(1) state indicates that FSM is in its
             initial state."
        ::= { wmanIfSsPkmTekEntry 6 }

wmanIfSsPkmTekKeySequenceNumber OBJECT-TYPE
        SYNTAX      Integer32 (0..3)
        MAX-ACCESS  read-only
        STATUS      current
        DESCRIPTION
            "The value of this object is the most recent TEK key
             sequence number for this TEK FSM."             
        REFERENCE
            "IEEE 802.16-2004; 11.9.5"
        ::= { wmanIfSsPkmTekEntry 7 }

wmanIfSsPkmTekExpiresOld OBJECT-TYPE
        SYNTAX      DateAndTime 
        MAX-ACCESS  read-only
        STATUS      current
        DESCRIPTION 
            "The value of this object is the actual clock time for
             expiration of the immediate predecessor of the most recent
             TEK for this FSM.  If this FSM has only one TEK, then the
             value is the time of activation of this FSM."
        ::= { wmanIfSsPkmTekEntry 8 }

wmanIfSsPkmTekExpiresNew OBJECT-TYPE
        SYNTAX      DateAndTime 
        MAX-ACCESS  read-only
        STATUS      current
        DESCRIPTION
            "The value of this object is the actual clock time for
             expiration of the most recent TEK for this FSM."
        ::= { wmanIfSsPkmTekEntry 9 }

wmanIfSsPkmTekKeyRequests OBJECT-TYPE
        SYNTAX      Counter32 
        MAX-ACCESS  read-only
        STATUS      current
        DESCRIPTION
            "The value of this object is the count of times the SS has
             transmitted a Key Request message."
        ::= { wmanIfSsPkmTekEntry 10 }

wmanIfSsPkmTekKeyReplies OBJECT-TYPE
        SYNTAX      Counter32 
        MAX-ACCESS  read-only
        STATUS      current
        DESCRIPTION 
            "The value of this object is the count of times the SS has
             received a Key Reply message, including a message whose
             authentication failed."
        ::= { wmanIfSsPkmTekEntry 11 }

wmanIfSsPkmTekKeyRejects OBJECT-TYPE
        SYNTAX      Counter32 
        MAX-ACCESS  read-only
        STATUS      current
        DESCRIPTION
            "The value of this object is the count of times the SS has
             received a Key Reject message, including a message whose
             authentication failed."
        ::= { wmanIfSsPkmTekEntry 12 }

wmanIfSsPkmTekInvalids OBJECT-TYPE
        SYNTAX      Counter32 
        MAX-ACCESS  read-only
        STATUS      current
        DESCRIPTION
            "The value of this object is the count of times the SS has
             received a TEK Invalid message, including a message whose
             authentication failed."
        ::= { wmanIfSsPkmTekEntry 13 }

wmanIfSsPkmTekAuthPends OBJECT-TYPE
        SYNTAX      Counter32 
        MAX-ACCESS  read-only
        STATUS      current
        DESCRIPTION
            "The value of this object is the count of times an
             Authorization Pending (Auth Pend) event occurred in this
             FSM."
        ::= { wmanIfSsPkmTekEntry 14 }

wmanIfSsPkmTekKeyRejectErrorCode OBJECT-TYPE
        SYNTAX      INTEGER {none(1),
                             unknown(2),
                             unauthorizedSaid(4)}
        MAX-ACCESS  read-only
        STATUS      current
        DESCRIPTION
            "The value of this object is the enumerated description of
             the Error-Code in most recent Key Reject message received
             by the SS. This has value unknown(2) if the last Error-Code
             value was 0, and none(1) if no Key Reject message has been
             received since reboot."
        ::= { wmanIfSsPkmTekEntry 15 }

wmanIfSsPkmTekKeyRejectErrorString OBJECT-TYPE
        SYNTAX      SnmpAdminString (SIZE (0..128))
        MAX-ACCESS  read-only
        STATUS      current
        DESCRIPTION
            "The value of this object is the Display-String in most
             recent Key Reject message received by the SS. This is a
             zero length string if no Key Reject message has been
             received since reboot."
        ::= { wmanIfSsPkmTekEntry 16 }

wmanIfSsPkmTekInvalidErrorCode OBJECT-TYPE
        SYNTAX      INTEGER {none(1),
                             unknown(2),
                             invalidKeySequence(6)}
        MAX-ACCESS  read-only
        STATUS      current
        DESCRIPTION
            "The value of this object is the enumerated description of
             the Error-Code in most recent TEK Invalid message received
             by the SS.  This has value unknown(2) if the last
             Error-Code value was 0, and  none(1) if no TEK Invalid
             message has been received since reboot."
        ::= { wmanIfSsPkmTekEntry 17 }

wmanIfSsPkmTekInvalidErrorString OBJECT-TYPE
        SYNTAX      SnmpAdminString (SIZE (0..128))
        MAX-ACCESS  read-only
        STATUS      current
        DESCRIPTION 
            "The value of this object is the Display-String in most
             recent TEK Invalid message received by the SS. This is a
             zero length string if no TEK Invalid message has been
             received since reboot."
        ::= { wmanIfSsPkmTekEntry 18 }

--
-- Table wmanIfSsDeviceCertTable
--
wmanIfSsDeviceCertTable OBJECT-TYPE
        SYNTAX      SEQUENCE OF   WmanIfSsDeviceCertEntry
        MAX-ACCESS  not-accessible
        STATUS      current
        DESCRIPTION
            "This table describes the PKM device certificates for each
             SS wireless interface."
        ::= { wmanIfSsPkmObjects  3 }

wmanIfSsDeviceCertEntry OBJECT-TYPE
        SYNTAX      WmanIfSsDeviceCertEntry
        MAX-ACCESS  not-accessible
        STATUS      current
        DESCRIPTION
            "Each entry contains the device certificate of one SS."
        INDEX       { ifIndex }
        ::= { wmanIfSsDeviceCertTable  1 }

WmanIfSsDeviceCertEntry ::= SEQUENCE {
        wmanIfSsDeviceCert                      OCTET STRING,
        wmanIfSsDeviceManufCert                 OCTET STRING}

wmanIfSsDeviceCert OBJECT-TYPE
        SYNTAX      OCTET STRING (SIZE(0..65535))  
        MAX-ACCESS  read-only
        STATUS      current
        DESCRIPTION
            "The X509 DER-encoded subscriber station certificate."
        ::= { wmanIfSsDeviceCertEntry 1 }

wmanIfSsDeviceManufCert OBJECT-TYPE
        SYNTAX      OCTET STRING (SIZE(0..65535)) 
        MAX-ACCESS  read-only
        STATUS      current
        DESCRIPTION
            "The X509 DER-encoded manufacturer certificate which is
             signed by the CA root authority certificate."
        ::= { wmanIfSsDeviceCertEntry 2 }

--
-- Subscriber station Notification Group
-- wmanIfSsNotificationObjects contains the SS SNMP Trap objects
--
wmanIfSsNotification OBJECT IDENTIFIER ::= { wmanIfSsObjects  3 }
wmanIfSsTrapControl OBJECT IDENTIFIER ::= { wmanIfSsNotification 1 }
wmanIfSsTrapDefinitions OBJECT IDENTIFIER ::= { wmanIfSsNotification 2 }

-- This object groups all NOTIFICATION-TYPE objects for SS. 
-- It is defined following RFC2758 sections 8.5 and 8.6 
-- for the compatibility with SNMPv1.
wmanIfSsTrapPrefix OBJECT IDENTIFIER ::= { wmanIfSsTrapDefinitions 0 }
	
wmanIfSsTrapControlRegister    OBJECT-TYPE
        SYNTAX      BITS {wmanIfSsTlvUnknown(0),
                          wmanIfSsDynamicServiceFail(1),
                          wmanIfSsDhcpSuccess(2),
                          wmanIfSsRssiStatusChange(3)}
        MAX-ACCESS  read-write
        STATUS      current
        DESCRIPTION
            "The object is used to enable Subscriber Station traps.
             From left to right, the set bit indicates the corresponding
             Subscriber Station trap is enabled."
        ::= { wmanIfSsTrapControl  1 }

wmanIfSsThresholdConfigTable OBJECT-TYPE
        SYNTAX      SEQUENCE OF WmanIfSsThresholdConfigEntry
        MAX-ACCESS  not-accessible
        STATUS      current
        DESCRIPTION
            "This table contains threshold objects that can be set to
             detect the threshold crossing events."
        ::= { wmanIfSsTrapControl 2 }

wmanIfSsThresholdConfigEntry OBJECT-TYPE
        SYNTAX      WmanIfSsThresholdConfigEntry
        MAX-ACCESS  not-accessible
        STATUS      current
        DESCRIPTION
            "This table provides one row for each Ss, and is indexed
             by ifIndex."
        INDEX       { ifIndex }
        ::= { wmanIfSsThresholdConfigTable 1 }

WmanIfSsThresholdConfigEntry ::= SEQUENCE {        
        wmanIfSsRssiLowThreshold                Integer32,
        wmanIfSsRssiHighThreshold               Integer32}

wmanIfSsRssiLowThreshold OBJECT-TYPE
        SYNTAX      Integer32
        UNITS       "dBm"
        MAX-ACCESS  read-write
        STATUS      current
        DESCRIPTION
        	"Low RSSI threshold for generating the RSSI alarm trap."
        ::= { wmanIfSsThresholdConfigEntry 1 }

wmanIfSsRssiHighThreshold OBJECT-TYPE
        SYNTAX      Integer32
        UNITS       "dBm"
        MAX-ACCESS  read-write
        STATUS      current
        DESCRIPTION
            "High RSSI threshold for generating a trap to indicate
             the RSSI is restored."
        ::= { wmanIfSsThresholdConfigEntry 2 }
                        
wmanIfSsTlvUnknownTrap NOTIFICATION-TYPE
        OBJECTS     {ifIndex,
                     wmanIfSsMacAddress,
                     wmanIfSsUnknownTlv}
        STATUS      current
        DESCRIPTION
            "Event that notifies detection of unknown TLV during
             the TLV parsing process."
        ::= { wmanIfSsTrapPrefix 1 }

wmanIfSsDynamicServiceFailTrap NOTIFICATION-TYPE
        OBJECTS     {ifIndex,
                     wmanIfSsMacAddress,
                     wmanIfSsDynamicServiceType,
                     wmanIfSsDynamicServiceFailReason}
        STATUS      current
        DESCRIPTION
            "An event to report the failure of a dynamic service
             operation happened during the dynamic services process
             and detected in the BS side."
        ::= { wmanIfSsTrapPrefix 2 }

wmanIfSsDhcpSuccessTrap    NOTIFICATION-TYPE
        OBJECTS     {ifIndex,
                     wmanIfSsMacAddress}
        STATUS      current
        DESCRIPTION
            "An event to report a successful Handshake to establish IP
             connectivity."
        ::= { wmanIfSsTrapPrefix 3 }

wmanIfSsRssiStatusChangeTrap NOTIFICATION-TYPE
        OBJECTS     {ifIndex,
                     wmanIfSsMacAddress,
                     wmanIfSsRssiStatus,
                     wmanIfSsRssiStatusInfo}
        STATUS      current
        DESCRIPTION
            "An event to report that the downlink RSSI is below
             wmanIfSsRssiLowThreshold, or above
             wmanIfSsRssiHighThreshold after restore."
        ::= { wmanIfSsTrapPrefix 4 }
        
wmanIfSsNotificationObjectsTable OBJECT-TYPE
        SYNTAX      SEQUENCE OF WmanIfSsNotificationObjectsEntry
        MAX-ACCESS  not-accessible
        STATUS      current
        DESCRIPTION
            "This table contains SS notification objects that have been
             reported by the trap."
        ::= { wmanIfSsTrapDefinitions 1 }

wmanIfSsNotificationObjectsEntry OBJECT-TYPE
        SYNTAX      WmanIfSsNotificationObjectsEntry
        MAX-ACCESS  not-accessible
        STATUS      current
        DESCRIPTION
            "This table provides one row for each SS that has
             generated traps, and is indexed by ifIndex."
        INDEX       { ifIndex }
        ::= { wmanIfSsNotificationObjectsTable 1 }

WmanIfSsNotificationObjectsEntry ::= SEQUENCE {        
        wmanIfSsMacAddress                      MacAddress,
        wmanIfSsUnknownTlv                      OCTET STRING,
        wmanIfSsDynamicServiceType              INTEGER,
        wmanIfSsDynamicServiceFailReason        OCTET STRING,
        wmanIfSsRssiStatus                      INTEGER,
        wmanIfSsRssiStatusInfo                  OCTET STRING}
                                                                  
wmanIfSsMacAddress  OBJECT-TYPE
        SYNTAX      MacAddress 
        MAX-ACCESS  read-only
        STATUS      current
        DESCRIPTION
            "The MAC address of the SS generating the trap."
        ::= { wmanIfSsNotificationObjectsEntry 1 }
                                                          
wmanIfSsUnknownTlv  OBJECT-TYPE
        SYNTAX      OCTET STRING (SIZE(0..65535))
        MAX-ACCESS  read-only
        STATUS      current
        DESCRIPTION
            "Indicating the value of the unknown TLV."
        ::= { wmanIfSsNotificationObjectsEntry 2 }
                                             
wmanIfSsDynamicServiceType  OBJECT-TYPE
        SYNTAX      INTEGER {ssSfCreationReq(1),
                             ssSfCreationRsp(2),
                             ssSfCreationAck(3)} 
        MAX-ACCESS  read-only
        STATUS      current
        DESCRIPTION
            "This object indicates the dynamic service flow
             creation command type."
        ::= { wmanIfSsNotificationObjectsEntry 3 }
                
wmanIfSsDynamicServiceFailReason  OBJECT-TYPE
        SYNTAX      OCTET STRING (SIZE(0..255))
        MAX-ACCESS  read-only
        STATUS      current
        DESCRIPTION
            "This object indicates the reason why the service flow
             creation has failed."
        ::= { wmanIfSsNotificationObjectsEntry 4 }
                                                                          
wmanIfSsRssiStatus  OBJECT-TYPE
        SYNTAX      INTEGER {ssRssiAlarm(1),
                             ssRssiNoAlarm(2)} 
        MAX-ACCESS  read-only
        STATUS      current
        DESCRIPTION
            "A RSSI alarm is generated if the RSSI is lower than
             wmanIfSsRssiLowThreshold, or above
             wmanIfSsRssiHighThreshold after alarm is restored."
        ::= { wmanIfSsNotificationObjectsEntry 5 }
                
wmanIfSsRssiStatusInfo  OBJECT-TYPE
        SYNTAX      OCTET STRING (SIZE(0..255))
        MAX-ACCESS  read-only
        STATUS      current
        DESCRIPTION
            "This object provides additional information about RSSI
             alarm. It is implementation specific"
        ::= { wmanIfSsNotificationObjectsEntry 6 }
        
--
-- Subscriber station PHY Group 
--
wmanIfSsPhy OBJECT IDENTIFIER ::= { wmanIfSsObjects  5 }

--
-- SS OFDM PHY objects    
--
wmanIfSsOfdmPhy OBJECT IDENTIFIER ::= { wmanIfSsPhy 1 }

wmanIfSsOfdmUplinkChannelTable OBJECT-TYPE
        SYNTAX      SEQUENCE OF WmanIfSsOfdmUplinkChannelEntry
        MAX-ACCESS  not-accessible
        STATUS      current
        DESCRIPTION
            "This table contains UCD channel attributes, defining the
             transmission characteristics of uplink channels"
        REFERENCE
            "Table 349 and table 352, in IEEE 802.16-2004"
        ::= { wmanIfSsOfdmPhy 1 }

wmanIfSsOfdmUplinkChannelEntry OBJECT-TYPE
        SYNTAX      WmanIfSsOfdmUplinkChannelEntry
        MAX-ACCESS  not-accessible
        STATUS      current
        DESCRIPTION
            "This table provides one row for each uplink channel of
             multi-sector BS, and is indexed by BS ifIndex. An entry
             in this table exists for each ifEntry of BS with an
             ifType of propBWAp2Mp."
        INDEX { ifIndex }
        ::= { wmanIfSsOfdmUplinkChannelTable 1 }

WmanIfSsOfdmUplinkChannelEntry ::= SEQUENCE {
        wmanIfSsOfdmCtBasedResvTimeout          INTEGER,
        wmanIfSsOfdmBwReqOppSize                INTEGER,
        wmanIfSsOfdmRangReqOppSize              INTEGER,
        wmanIfSsOfdmUplinkCenterFreq            Unsigned32,
        wmanIfSsOfdmNumSubChReqRegionFull       INTEGER,
        wmanIfSsOfdmNumSymbolsReqRegionFull     INTEGER,
        wmanIfSsOfdmSubChFocusCtCode            INTEGER,
        wmanIfSsOfdmUpLinkChannelId             INTEGER}

wmanIfSsOfdmCtBasedResvTimeout OBJECT-TYPE
        SYNTAX      INTEGER (1..255)
        MAX-ACCESS  read-only
        STATUS      current
        DESCRIPTION
            "The number of UL-MAPs to receive before contention-based
             reservation is attempted again for the same connection."
        REFERENCE
            "Table 349, in IEEE 802.16-2004"
        ::= { wmanIfSsOfdmUplinkChannelEntry 1 }

wmanIfSsOfdmBwReqOppSize OBJECT-TYPE
        SYNTAX      INTEGER (1..65535)
        UNITS       "PS"
        MAX-ACCESS  read-only
        STATUS      current
        DESCRIPTION
            "Size (in units of PS) of PHY payload that SS may use to
             format and transmit a bandwidth request message in a
             contention request opportunity. The value includes all
             PHY overhead as well as allowance for the MAC data the
             message may hold."
        REFERENCE
            "Table 349, in IEEE 802.16-2004"
        ::= { wmanIfSsOfdmUplinkChannelEntry 2 }

wmanIfSsOfdmRangReqOppSize OBJECT-TYPE
        SYNTAX      INTEGER (1..65535)
        UNITS       "PS"
        MAX-ACCESS  read-only
        STATUS      current
        DESCRIPTION
            "Size (in units of PS) of PHY payload that SS may use to
             format and transmit a RNG-REQ message in a contention
             request opportunity. The value includes all PHY overhead
             as well as allowance for the MAC data the message may
             hold and the maxiumum SS/BS roundtrip propagation delay."
        REFERENCE
            "Table 349, in IEEE 802.16-2004"
        ::= { wmanIfSsOfdmUplinkChannelEntry 3 }

wmanIfSsOfdmUplinkCenterFreq OBJECT-TYPE
        SYNTAX      Unsigned32
        UNITS       "kHz"
        MAX-ACCESS  read-only
        STATUS      current
        DESCRIPTION
            " Uplink center frequency (kHz)"
        REFERENCE
            "Table 349, in IEEE 802.16-2004"
        ::= { wmanIfSsOfdmUplinkChannelEntry 4 }

wmanIfSsOfdmNumSubChReqRegionFull OBJECT-TYPE
        SYNTAX      INTEGER {oneSubchannel(0),
                             twoSubchannels(1),
                             fourSubchannels(2),
                             eightSubchannels(3),
                             sixteenSubchannels(4)}
        MAX-ACCESS  read-only
        STATUS      current
        DESCRIPTION
            "Number of subchannels used by each transmit
             opportunity when REQ Region-Full is allocated in
             subchannelization region."
        REFERENCE
             "Table 352, in IEEE 802.16-2004"
        ::= { wmanIfSsOfdmUplinkChannelEntry 5 }

wmanIfSsOfdmNumSymbolsReqRegionFull OBJECT-TYPE
        SYNTAX      INTEGER (0..31)
        MAX-ACCESS  read-only
        STATUS      current
        DESCRIPTION
            "Number of OFDM symbols used by each transmit
             opportunity when REQ Region-Full is allocated in
             subchannelization region."
        REFERENCE
             "Table 352, in IEEE 802.16-2004"
        ::= { wmanIfSsOfdmUplinkChannelEntry 6 }

wmanIfSsOfdmSubChFocusCtCode OBJECT-TYPE
        SYNTAX      INTEGER (0..8)
        MAX-ACCESS  read-only
        STATUS      current
        DESCRIPTION
            "Number of contention codes (CSE) that shall only be used to
             request a subchannelized allocation. Default value 0.
             Allowed values 0-8."
        REFERENCE
            "Table 352, in IEEE 802.16-2004"
        DEFVAL         { 0 }
        ::= { wmanIfSsOfdmUplinkChannelEntry 7 }

wmanIfSsOfdmUpLinkChannelId OBJECT-TYPE
        SYNTAX      INTEGER (0..255)
        MAX-ACCESS  read-only
        STATUS      current
        DESCRIPTION
            "The identifier of the uplink channel to which this
             message refers."
        REFERENCE
            "Subclause 6.3.2.3.4. Table 16, in IEEE 802.16-2004"
        ::= { wmanIfSsOfdmUplinkChannelEntry 8 }
        
wmanIfSsOfdmDownlinkChannelTable OBJECT-TYPE
        SYNTAX      SEQUENCE OF WmanIfSsOfdmDownlinkChannelEntry
        MAX-ACCESS  not-accessible
        STATUS      current
        DESCRIPTION
            "This table contains DCD channel attributes, defining the
             transmission characteristics of downlink channels"
        REFERENCE
            "Table 358, in IEEE 802.16-2004"
        ::= { wmanIfSsOfdmPhy 2 }

wmanIfSsOfdmDownlinkChannelEntry OBJECT-TYPE
        SYNTAX      WmanIfSsOfdmDownlinkChannelEntry
        MAX-ACCESS  not-accessible
        STATUS      current
        DESCRIPTION
            "This table provides one row for each downlink channel of
             multi-sector BS, and is indexed by BS ifIndex. An entry
             in this table exists for each ifEntry of BS with an
             ifType of propBWAp2Mp."
        INDEX { ifIndex }
        ::= { wmanIfSsOfdmDownlinkChannelTable 1 }

WmanIfSsOfdmDownlinkChannelEntry ::= SEQUENCE {   
        wmanIfSsOfdmBsEIRP                      INTEGER,
        wmanIfSsOfdmChannelNumber               WmanIfChannelNumber,
        wmanIfSsOfdmTTG                         INTEGER,
        wmanIfSsOfdmRTG                         INTEGER,
        wmanIfSsOfdmInitRngMaxRSS               INTEGER,
        wmanIfSsOfdmDownlinkCenterFreq          Unsigned32,
        wmanIfSsOfdmBsId                        WmanIfBsIdType,
        wmanIfSsOfdmMacVersion                  WmanIfMacVersion,
        wmanIfSsOfdmFrameDurationCode           INTEGER,
        wmanIfSsOfdmDownLinkChannelId           INTEGER}

wmanIfSsOfdmBsEIRP OBJECT-TYPE
        SYNTAX      INTEGER (0..65535)
        UNITS       "dBm"
        MAX-ACCESS  read-only
        STATUS      current
        DESCRIPTION
            "The EIRP is the equivalent isotropic radiated power of
             the base station, which is computed for a simple
             single-antenna transmitter."
        REFERENCE
            "Table 358, in IEEE 802.16-2004"
        ::= { wmanIfSsOfdmDownlinkChannelEntry 1 }

wmanIfSsOfdmChannelNumber OBJECT-TYPE
        SYNTAX      WmanIfChannelNumber
        MAX-ACCESS  read-only
        STATUS      current
        DESCRIPTION
            "Downlink channel number as defined in 8.5.
             Used for license-exempt operation only."
        REFERENCE
            "Table 358, in IEEE 802.16-2004"
        ::= { wmanIfSsOfdmDownlinkChannelEntry 2 }

wmanIfSsOfdmTTG OBJECT-TYPE
        SYNTAX      INTEGER (0..255)
        MAX-ACCESS  read-only
        STATUS      current
        DESCRIPTION
            "Transmit / Receive Transition Gap."
        REFERENCE
            "Table 358, in IEEE 802.16-2004"
        ::= { wmanIfSsOfdmDownlinkChannelEntry 3 }

wmanIfSsOfdmRTG OBJECT-TYPE
        SYNTAX      INTEGER (0..255)
        MAX-ACCESS  read-only
        STATUS      current
        DESCRIPTION
            "Receive / Transmit Transition Gap."
        REFERENCE
            "Table 358, in IEEE 802.16-2004"
        ::= { wmanIfSsOfdmDownlinkChannelEntry 4 }

wmanIfSsOfdmInitRngMaxRSS OBJECT-TYPE
        SYNTAX      INTEGER (0..65535)
        UNITS       "dBm"
        MAX-ACCESS  read-only
        STATUS      current
        DESCRIPTION
            "Initial Ranging Max. Received Signal Strength at BS
             Signed in units of 1 dBm."
        REFERENCE
            "Table 358, in IEEE 802.16-2004"
        ::= { wmanIfSsOfdmDownlinkChannelEntry 5 }

wmanIfSsOfdmDownlinkCenterFreq OBJECT-TYPE
        SYNTAX      Unsigned32
        UNITS       "kHz"
        MAX-ACCESS  read-only
        STATUS      current
        DESCRIPTION
            "Downlink center frequency (kHz)."
        REFERENCE
            "Table 358, in IEEE 802.16-2004"
        ::= { wmanIfSsOfdmDownlinkChannelEntry 6 }

wmanIfSsOfdmBsId OBJECT-TYPE
        SYNTAX      WmanIfBsIdType
        MAX-ACCESS  read-only
        STATUS      current
        DESCRIPTION
            "Base station ID."
        REFERENCE
            "Table 358, in IEEE 802.16-2004"
        ::= { wmanIfSsOfdmDownlinkChannelEntry 7 }
        
wmanIfSsOfdmMacVersion OBJECT-TYPE
        SYNTAX      WmanIfMacVersion
        MAX-ACCESS  read-only
        STATUS      current
        DESCRIPTION
            "This parameter specifies the version of 802.16 to which
             the message originator conforms."
        REFERENCE
            "Table 358, in IEEE 802.16-2004"
        ::= { wmanIfSsOfdmDownlinkChannelEntry 8 }

wmanIfSsOfdmFrameDurationCode OBJECT-TYPE
        SYNTAX      INTEGER {duration2dot5ms(0),
                             duration4ms(1),
                             duration5ms(2),
                             duration8ms(3),
                             duration10ms(4),
                             duration12dot5ms(5),
                             duration20ms(6)}
        MAX-ACCESS  read-only
        STATUS      current
        DESCRIPTION
            "The duration of the frame. The frame duration code
             values are specified in Table 230."
        REFERENCE
            "Subclause 11.4.1, table 230, in IEEE 802.16-2004"
        ::= { wmanIfSsOfdmDownlinkChannelEntry 9 }

wmanIfSsOfdmDownLinkChannelId OBJECT-TYPE
        SYNTAX      INTEGER (0..255)
        MAX-ACCESS  read-only
        STATUS      current
        DESCRIPTION
            "The identifier of the downlink channel to which this
             message refers."
        REFERENCE
            "Subclause 6.3.2.3.1. Table 15, in IEEE 802.16-2004"
        ::= { wmanIfSsOfdmDownlinkChannelEntry 10 }
        
wmanIfSsOfdmUcdBurstProfileTable OBJECT-TYPE
        SYNTAX      SEQUENCE OF WmanIfSsOfdmUcdBurstProfileEntry
        MAX-ACCESS  not-accessible
        STATUS      current
        DESCRIPTION
            "This table contains UCD burst profiles for each uplink
             channel"
        REFERENCE
            "Table 356, in IEEE 802.16-2004"
        ::= { wmanIfSsOfdmPhy 3 }

wmanIfSsOfdmUcdBurstProfileEntry OBJECT-TYPE
        SYNTAX      WmanIfSsOfdmUcdBurstProfileEntry
        MAX-ACCESS  not-accessible
        STATUS      current
        DESCRIPTION
            "This table provides one row for each UCD burst profile.
             This table is double indexed. The primary index is an
             ifIndex with an ifType of propBWAp2Mp. The secondary index
             is wmanIfSsOfdmOfdmUcdBurstProfIndex."
        INDEX { ifIndex, wmanIfSsOfdmUiucIndex }
        ::= { wmanIfSsOfdmUcdBurstProfileTable 1 }

WmanIfSsOfdmUcdBurstProfileEntry ::= SEQUENCE {
        wmanIfSsOfdmUiucIndex                   INTEGER,
        wmanIfSsOfdmUcdFecCodeType              WmanIfOfdmFecCodeType,
        wmanIfSsOfdmFocusCtPowerBoost           INTEGER,
        wmanIfSsOfdmUcdTcsEnable                INTEGER}

wmanIfSsOfdmUiucIndex OBJECT-TYPE
        SYNTAX      INTEGER (5 .. 12)
        MAX-ACCESS  not-accessible
        STATUS      current
        DESCRIPTION
            "The Uplink Interval Usage Code indicates the uplink burst
             profile in the UCD message, and is used along with ifIndex
             to identify an entry in the
             wmanIfSsOfdmUcdBurstProfileTable."
        REFERENCE
            "Subclause 8.3.6.3.1, in IEEE 802.16-2004"
        ::= { wmanIfSsOfdmUcdBurstProfileEntry 1 }

wmanIfSsOfdmUcdFecCodeType OBJECT-TYPE
        SYNTAX      WmanIfOfdmFecCodeType
        MAX-ACCESS  read-only
        STATUS      current
        DESCRIPTION
            "Uplink FEC code type and modulation type"
        REFERENCE
            "Table 356, in IEEE 802.16-2004"
        ::= { wmanIfSsOfdmUcdBurstProfileEntry 2 }

wmanIfSsOfdmFocusCtPowerBoost OBJECT-TYPE
        SYNTAX      INTEGER (0 .. 255)
        MAX-ACCESS  read-only
        STATUS      current
        DESCRIPTION
            "The power boost in dB of focused contention carriers, as
             described in 8.3.6.3.3."
        REFERENCE
            "Table 356, in IEEE 802.16-2004"
        ::= { wmanIfSsOfdmUcdBurstProfileEntry 3 }

wmanIfSsOfdmUcdTcsEnable OBJECT-TYPE
        SYNTAX      INTEGER {tcsDisabled(0),
                             tcsEnabled(1)}
        MAX-ACCESS  read-only
        STATUS      current
        DESCRIPTION
            "This parameter determines the transmission convergence
             sublayer, as described in 8.1.4.3, can be enabled on a
             per-burst basis for both uplink and downlink. through
             DIUC/UIUC messages."
        REFERENCE
            "Table 356, in IEEE 802.16-2004"
        ::= { wmanIfSsOfdmUcdBurstProfileEntry 4 }
        
wmanIfSsOfdmDcdBurstProfileTable OBJECT-TYPE
        SYNTAX      SEQUENCE OF WmanIfSsOfdmDcdBurstProfileEntry
        MAX-ACCESS  not-accessible
        STATUS      current
        DESCRIPTION
            "This table provides one row for each DCD burst profile.
             This table is double indexed. The primary index is an
             ifIndex with an ifType of propBWAp2Mp. The secondary
             index is wmanIfSsOfdmDiucIndex."
        REFERENCE
            "Table 362, in IEEE 802.16-2004"
        ::= { wmanIfSsOfdmPhy 4 }

wmanIfSsOfdmDcdBurstProfileEntry OBJECT-TYPE
        SYNTAX      WmanIfSsOfdmDcdBurstProfileEntry
        MAX-ACCESS  not-accessible
        STATUS      current
        DESCRIPTION
            "This table provides one row for each DCD burst profile.
             This table is double indexed. The primary index is an
             ifIndex with an ifType of propBWAp2Mp. The secondary index
             is wmanIfSsOfdmDcdBurstProfIndex."
        INDEX { ifIndex, wmanIfSsOfdmDiucIndex }
        ::= { wmanIfSsOfdmDcdBurstProfileTable 1 }

WmanIfSsOfdmDcdBurstProfileEntry ::= SEQUENCE {
        wmanIfSsOfdmDiucIndex                   INTEGER,
        wmanIfSsOfdmDownlinkFrequency           Unsigned32,
        wmanIfSsOfdmDcdFecCodeType              WmanIfOfdmFecCodeType,
        wmanIfSsOfdmDiucMandatoryExitThresh     INTEGER,
        wmanIfSsOfdmDiucMinEntryThresh          INTEGER,
        wmanIfSsOfdmTcsEnable                   INTEGER}

wmanIfSsOfdmDiucIndex OBJECT-TYPE
        SYNTAX      INTEGER (1..11)
        MAX-ACCESS  not-accessible
        STATUS      current
        DESCRIPTION
            "The Downlink Interval Usage Code indicates the downlink
             burst profile in the DCD message, and is used along with
             ifIndex to identify an entry in the
             wmanIfSsOfdmDcdBurstProfileTable."
        REFERENCE
            "Subclause 8.3.6.3.1, in IEEE 802.16-2004"
        ::= { wmanIfSsOfdmDcdBurstProfileEntry 1 }
        
wmanIfSsOfdmDownlinkFrequency OBJECT-TYPE
        SYNTAX      Unsigned32
        UNITS       "kHz"
        MAX-ACCESS  read-only
        STATUS      current
        DESCRIPTION
            "Downlink Frequency (kHz)."
        REFERENCE
            "Table 362, in IEEE 802.16-2004"
        ::= { wmanIfSsOfdmDcdBurstProfileEntry 2 }

wmanIfSsOfdmDcdFecCodeType OBJECT-TYPE
        SYNTAX      WmanIfOfdmFecCodeType
        MAX-ACCESS  read-only
        STATUS      current
        DESCRIPTION
            "Downlink FEC code type and modulation type"
        REFERENCE
            "Table 362, in IEEE 802.16-2004"
        ::= { wmanIfSsOfdmDcdBurstProfileEntry 3 }

wmanIfSsOfdmDiucMandatoryExitThresh OBJECT-TYPE
        SYNTAX      INTEGER (0..255)
        MAX-ACCESS  read-only
        STATUS      current
        DESCRIPTION
            "DIUC mandatory exit threshold: 0 - 63.75 dB CINR at or
             below where this DIUC can no longer be used and where this
             change to a more robust DIUC is required in 0.25 dB units."
        REFERENCE
            "Table 362, in IEEE 802.16-2004"
        ::= { wmanIfSsOfdmDcdBurstProfileEntry 4 }

wmanIfSsOfdmDiucMinEntryThresh OBJECT-TYPE
        SYNTAX      INTEGER (0..255)
        MAX-ACCESS  read-only
        STATUS      current
        DESCRIPTION
            "DIUC minimum entry threshold: 0 - 63.75 dB The minimum CINR
             required to start using this DIUC when changing from a more
             robust DIUC is required, in 0.25 dB units."
        REFERENCE
            "Table 362, in IEEE 802.16-2004"
        ::= { wmanIfSsOfdmDcdBurstProfileEntry 5 }

wmanIfSsOfdmTcsEnable OBJECT-TYPE
        SYNTAX      INTEGER {tcsDisabled (0),
                             tcsEnabled (1)}
        MAX-ACCESS  read-only
        STATUS      current
        DESCRIPTION
            "Indicates whether Transmission COnvergence Sublayer
             is enabled or disabled."
        REFERENCE
            "Table 362, in IEEE 802.16-2004"
        ::= { wmanIfSsOfdmDcdBurstProfileEntry 6 }

--
-- SS OFDMA PHY objects    
--
wmanIfSsOfdmaPhy OBJECT IDENTIFIER ::= { wmanIfSsPhy 2 }

wmanIfSsOfdmaUplinkChannelTable OBJECT-TYPE
        SYNTAX      SEQUENCE OF WmanIfSsOfdmaUplinkChannelEntry
        MAX-ACCESS  not-accessible
        STATUS      current
        DESCRIPTION
            "This table contains UCD channel attributes, defining the
             transmission characteristics of uplink channels"
        REFERENCE
            "Subclause 11.3.1, table 349 and 353, in IEEE 802.16-2004"
        ::= { wmanIfSsOfdmaPhy 1 }

wmanIfSsOfdmaUplinkChannelEntry OBJECT-TYPE
        SYNTAX      WmanIfSsOfdmaUplinkChannelEntry
        MAX-ACCESS  not-accessible
        STATUS      current
        DESCRIPTION
            "This table provides one row for each uplink channel of
             multi-sector BS, and is indexed by BS ifIndex. An entry
             in this table exists for each ifEntry of BS with an
             ifType of propBWAp2Mp."
        INDEX       { ifIndex }
        ::= { wmanIfSsOfdmaUplinkChannelTable 1 }

WmanIfSsOfdmaUplinkChannelEntry ::= SEQUENCE {
        wmanIfSsOfdmaCtBasedResvTimeout         INTEGER,
        wmanIfSsOfdmaBwReqOppSize               INTEGER,
        wmanIfSsOfdmaRangReqOppSize             INTEGER,
        wmanIfSsOfdmaUplinkCenterFreq           Unsigned32,
        wmanIfSsOfdmaInitRngCodes               INTEGER,
        wmanIfSsOfdmaPeriodicRngCodes           INTEGER,
        wmanIfSsOfdmaBWReqCodes                 INTEGER,
        wmanIfSsOfdmaPerRngBackoffStart         INTEGER,
        wmanIfSsOfdmaPerRngBackoffEnd           INTEGER,
        wmanIfSsOfdmaStartOfRngCodes            INTEGER,
        wmanIfSsOfdmaPermutationBase            INTEGER,
        wmanIfSsOfdmaULAllocSubchBitmap         OCTET STRING,
        wmanIfSsOfdmaOptPermULAllocSubchBitmap  OCTET STRING,
        wmanIfSsOfdmaBandAMCAllocThreshold      INTEGER,
        wmanIfSsOfdmaBandAMCReleaseThreshold    INTEGER,
        wmanIfSsOfdmaBandAMCAllocTimer          INTEGER,
        wmanIfSsOfdmaBandAMCReleaseTimer        INTEGER,
        wmanIfSsOfdmaBandStatRepMAXPeriod       INTEGER,
        wmanIfSsOfdmaBandAMCRetryTimer          INTEGER,
        wmanIfSsOfdmaSafetyChAllocThreshold     INTEGER,
        wmanIfSsOfdmaSafetyChReleaseThreshold   INTEGER,
        wmanIfSsOfdmaSafetyChAllocTimer         INTEGER,
        wmanIfSsOfdmaSafetyChReleaseTimer       INTEGER,
        wmanIfSsOfdmaBinStatRepMAXPeriod        INTEGER,
        wmanIfSsOfdmaSafetyChaRetryTimer        INTEGER,
        wmanIfSsOfdmaHARQAackDelayULBurst       INTEGER,
        wmanIfSsOfdmaCQICHBandAMCTranaDelay     INTEGER}

wmanIfSsOfdmaCtBasedResvTimeout OBJECT-TYPE
        SYNTAX      INTEGER (1..255)
        MAX-ACCESS  read-only
        STATUS      current
        DESCRIPTION
            "The number of UL-MAPs to receive before contention-based
             reservation is attempted again for the same connection."
        REFERENCE
            "Table 349, in IEEE 802.16-2004"
        ::= { wmanIfSsOfdmaUplinkChannelEntry 1 }

wmanIfSsOfdmaBwReqOppSize OBJECT-TYPE
        SYNTAX      INTEGER (1..65535)
        UNITS       "PS"
        MAX-ACCESS  read-only
        STATUS      current
        DESCRIPTION
            "Size (in units of PS) of PHY payload that SS may use to
             format and transmit a bandwidth request message in a
             contention request opportunity. The value includes all
             PHY overhead as well as allowance for the MAC data the
             message may hold."
        REFERENCE
            "Table 349, in IEEE 802.16-2004"
        ::= { wmanIfSsOfdmaUplinkChannelEntry 2 }

wmanIfSsOfdmaRangReqOppSize OBJECT-TYPE
        SYNTAX      INTEGER (1..65535)
        UNITS       "PS"
        MAX-ACCESS  read-only
        STATUS      current
        DESCRIPTION
            "Size (in units of PS) of PHY payload that SS may use to
             format and transmit a RNG-REQ message in a contention
             request opportunity. The value includes all PHY overhead
             as well as allowance for the MAC data the message may
             hold and the maxiumum SS/BS roundtrip propagation delay."
        REFERENCE
            "Table 349, in IEEE 802.16-2004"
        ::= { wmanIfSsOfdmaUplinkChannelEntry 3 }

wmanIfSsOfdmaUplinkCenterFreq OBJECT-TYPE
        SYNTAX      Unsigned32
        UNITS       "kHz"
        MAX-ACCESS  read-only
        STATUS      current
        DESCRIPTION
            " Uplink center frequency (kHz)"
        REFERENCE
            "Table 349, in IEEE 802.16-2004"
        ::= { wmanIfSsOfdmaUplinkChannelEntry 4 }

wmanIfSsOfdmaInitRngCodes OBJECT-TYPE
        SYNTAX      INTEGER (0..255)
        MAX-ACCESS  read-only
        STATUS      current
        DESCRIPTION
            "Number of initial ranging CDMA codes. Possible values are
             0..255. The total number of wmanIfSsOfdmaInitRngCodes,
             wmanIfSsOfdmaPeriodicRngCodes and wmanIfSsOfdmaBWReqCodes
             shall be equal or less than 256."
        REFERENCE
            "Subclause 11.3.1, table 353, in IEEE 802.16-2004"
        DEFVAL      { 30 }
        ::= { wmanIfSsOfdmaUplinkChannelEntry 5 }
        
wmanIfSsOfdmaPeriodicRngCodes OBJECT-TYPE
        SYNTAX      INTEGER (0..255)
        MAX-ACCESS  read-only
        STATUS      current
        DESCRIPTION
            "Number of periodic ranging CDMA codes. Possible values are
             0..255. The total number of wmanIfSsOfdmaInitRngCodes,
             wmanIfSsOfdmaPeriodicRngCodes and wmanIfSsOfdmaBWReqCodes
             shall be equal or less than 256."
        REFERENCE
            "Subclause 11.3.1, table 353, in IEEE 802.16-2004"
        DEFVAL 	    { 30 }
        ::= { wmanIfSsOfdmaUplinkChannelEntry 6 }

wmanIfSsOfdmaBWReqCodes OBJECT-TYPE
        SYNTAX      INTEGER (0..255)
        MAX-ACCESS  read-only
        STATUS      current
        DESCRIPTION
            "Number of bandwidth request codes. Possible values are
             0..255. The total number of wmanIfSsOfdmaInitRngCodes,
             wmanIfSsOfdmaPeriodicRngCodes and wmanIfSsOfdmaBWReqCodes
             shall be equal or less than 256."
        REFERENCE
            "Subclause 11.3.1, table 353, in IEEE 802.16-2004"
        DEFVAL 	    { 30 }
            ::= { wmanIfSsOfdmaUplinkChannelEntry 7 }

wmanIfSsOfdmaPerRngBackoffStart OBJECT-TYPE
        SYNTAX      INTEGER (0..15)
        MAX-ACCESS 	read-only
        STATUS      current
        DESCRIPTION
            "Initial backoff window size for periodic ranging
             contention, expressed as a power of 2."
        REFERENCE
            "Subclause 11.3.1, table 353, in IEEE 802.16-2004"
        DEFVAL 	    { 0 }
        ::= { wmanIfSsOfdmaUplinkChannelEntry 8 }

wmanIfSsOfdmaPerRngBackoffEnd OBJECT-TYPE
        SYNTAX      INTEGER (0 .. 15)
        MAX-ACCESS  read-only
        STATUS      current
        DESCRIPTION
            "Final backoff window size for periodic ranging contention,
             expressed as a power of 2."
        REFERENCE
            "Subclause 11.3.1, table 353, in IEEE 802.16-2004"
        DEFVAL 	    { 15 }
        ::= { wmanIfSsOfdmaUplinkChannelEntry 9 }

wmanIfSsOfdmaStartOfRngCodes OBJECT-TYPE
        SYNTAX      INTEGER (0..255)
        MAX-ACCESS  read-only
        STATUS      current
        DESCRIPTION
            "Indicates the starting number, S, of the group of codes
             used for this uplink.All the ranging codes used on this
             uplink will be between S and ((S+N+M+L) mod 256). Where,
             N is the number of initial-ranging codes M is the number
             of periodic-ranging codes L is the number of
             bandwidth-request codes The range of values is 0 S255"
        REFERENCE
            "Subclause 11.3.1, table 353, in IEEE 802.16-2004"
        DEFVAL 	    { 0 }
        ::= { wmanIfSsOfdmaUplinkChannelEntry 10 }

wmanIfSsOfdmaPermutationBase OBJECT-TYPE
        SYNTAX      INTEGER (0..255)
        MAX-ACCESS  read-only
        STATUS      current
        DESCRIPTION
            "Determines the UL_IDcell parameter for the subcarrier
             permutation to be used on this uplink channel"
        REFERENCE
            "Subclause 11.3.1, table 353, in IEEE 802.16-2004"
        DEFVAL 	    { 0 }
        ::= { wmanIfSsOfdmaUplinkChannelEntry 11 }

wmanIfSsOfdmaULAllocSubchBitmap OBJECT-TYPE
        SYNTAX      OCTET STRING (SIZE (9))
        MAX-ACCESS  read-only
        STATUS      current
        DESCRIPTION
            "This is a bitmap describing the sub-channels allocated
             to the segment in the UL, when using the uplink PUSC
             permutation. The LSB of the first byte shall corrspond to
             subchannel 0. For any bit that is not set,
             the corresponding subchannel shall not be used by the SS
             on that segment"
        REFERENCE
            "Subclause 11.3.1, table 353, in IEEE 802.16-2004"
        ::= { wmanIfSsOfdmaUplinkChannelEntry 12 }

wmanIfSsOfdmaOptPermULAllocSubchBitmap OBJECT-TYPE
        SYNTAX      OCTET STRING (SIZE (13))
        MAX-ACCESS  read-only
        STATUS      current
        DESCRIPTION
            "This is a bitmap describing the sub-channels allocated to
             the segment in the UL, when using the uplink optional PUSC
             permutation (see 8.4.6.2.5 in IEEE 802.16-2004). The LSB of
             the first byte shall correspond to subchannel 0. For any
             bit that is not set, the corresponding subchannel shall not
             be used by the SS on that segment"
        REFERENCE
            "Subclause 11.3.1, table 353, in IEEE 802.16-2004"
        ::= { wmanIfSsOfdmaUplinkChannelEntry 13 }

wmanIfSsOfdmaBandAMCAllocThreshold OBJECT-TYPE
        SYNTAX      INTEGER (0 .. 255)
        UNITS       "dB"
        MAX-ACCESS  read-only
        STATUS      current
        DESCRIPTION
            "This object defines the OFDMA band AMC allocation
             threshold."
        REFERENCE
            "Subclause 11.3.1, table 353, in IEEE 802.16-2004"
        ::= { wmanIfSsOfdmaUplinkChannelEntry 14 }

wmanIfSsOfdmaBandAMCReleaseThreshold OBJECT-TYPE
        SYNTAX      INTEGER (0 .. 255)
        UNITS       "dB"
        MAX-ACCESS  read-only
        STATUS      current
        DESCRIPTION
            "This object defines the OFDMA band AMC release
             threshold."
        REFERENCE
            "Subclause 11.3.1, table 353, in IEEE 802.16-2004"
        ::= { wmanIfSsOfdmaUplinkChannelEntry 15 }

wmanIfSsOfdmaBandAMCAllocTimer OBJECT-TYPE
        SYNTAX      INTEGER (0 .. 255)
        UNITS       "Frame"
        MAX-ACCESS  read-only
        STATUS      current
        DESCRIPTION
            "This object defines the OFDMA band AMC allocation
             timer."
        REFERENCE
            "Subclause 11.3.1, table 353, in IEEE 802.16-2004"
        ::= { wmanIfSsOfdmaUplinkChannelEntry 16 }

wmanIfSsOfdmaBandAMCReleaseTimer OBJECT-TYPE
        SYNTAX      INTEGER (0 .. 255)
        UNITS       "Frame"
        MAX-ACCESS  read-only
        STATUS      current
        DESCRIPTION
            "This object defines the OFDMA band AMC release
             timer."
        REFERENCE
            "Subclause 11.3.1, table 353, in IEEE 802.16-2004"
        ::= { wmanIfSsOfdmaUplinkChannelEntry 17 }

wmanIfSsOfdmaBandStatRepMAXPeriod OBJECT-TYPE
        SYNTAX      INTEGER (0 .. 255)
        UNITS       "Frame"
        MAX-ACCESS  read-only
        STATUS      current
        DESCRIPTION
            "This object defines the OFDMA band status reporting
             maximum period."
        REFERENCE
            "Subclause 11.3.1, table 353, in IEEE 802.16-2004"
        ::= { wmanIfSsOfdmaUplinkChannelEntry 18 }

wmanIfSsOfdmaBandAMCRetryTimer OBJECT-TYPE
        SYNTAX      INTEGER (0 .. 255)
        UNITS       "Frame"
        MAX-ACCESS  read-only
        STATUS      current
        DESCRIPTION
            "This object defines the OFDMA band AMC retry
             timer."
        REFERENCE
            "Subclause 11.3.1, table 353, in IEEE 802.16-2004"
        ::= { wmanIfSsOfdmaUplinkChannelEntry 19 }

wmanIfSsOfdmaSafetyChAllocThreshold OBJECT-TYPE
        SYNTAX      INTEGER (0 .. 255)
        UNITS       "dB"
        MAX-ACCESS  read-only
        STATUS      current
        DESCRIPTION
            "This object defines the OFDMA safety channel allocation
             threshold."
        REFERENCE
            "Subclause 11.3.1, table 353, in IEEE 802.16-2004"
        ::= { wmanIfSsOfdmaUplinkChannelEntry 20 }

wmanIfSsOfdmaSafetyChReleaseThreshold OBJECT-TYPE
        SYNTAX      INTEGER (0 .. 255)
        UNITS       "dB"
        MAX-ACCESS  read-only
        STATUS      current
        DESCRIPTION
            "This object defines the OFDMA safety channel release
             threshold."
        REFERENCE
            "Subclause 11.3.1, table 353, in IEEE 802.16-2004"
        ::= { wmanIfSsOfdmaUplinkChannelEntry 21 }

wmanIfSsOfdmaSafetyChAllocTimer OBJECT-TYPE
        SYNTAX      INTEGER (0 .. 255)
        UNITS       "Frame"
        MAX-ACCESS 	read-only
        STATUS      current
        DESCRIPTION
            "This object defines the OFDMA safety channel allocation
             timer."
        REFERENCE
            "Subclause 11.3.1, table 353, in IEEE 802.16-2004"
        ::= { wmanIfSsOfdmaUplinkChannelEntry 22 }

wmanIfSsOfdmaSafetyChReleaseTimer OBJECT-TYPE
        SYNTAX      INTEGER (0 .. 255)
        UNITS       "Frame"
        MAX-ACCESS  read-only
        STATUS      current
        DESCRIPTION
            "This object defines the OFDMA safety channel release
             timer."
        REFERENCE
            "Subclause 11.3.1, table 353, in IEEE 802.16-2004"
        ::= { wmanIfSsOfdmaUplinkChannelEntry 23 }

wmanIfSsOfdmaBinStatRepMAXPeriod OBJECT-TYPE
        SYNTAX      INTEGER (0 .. 255)
        UNITS       "Frame"
        MAX-ACCESS  read-only
        STATUS      current
        DESCRIPTION
            "This object defines the OFDMA bin status reporting
             maximum period."
        REFERENCE
            "Subclause 11.3.1, table 353, in IEEE 802.16-2004"
        ::= { wmanIfSsOfdmaUplinkChannelEntry 24 }

wmanIfSsOfdmaSafetyChaRetryTimer OBJECT-TYPE
        SYNTAX      INTEGER (0 .. 255)
        UNITS       "Frame"
        MAX-ACCESS  read-only
        STATUS      current
        DESCRIPTION
            "This object defines the OFDMA safety channel retry
             timer."
        REFERENCE
            "Subclause 11.3.1, table 353, in IEEE 802.16-2004"
        ::= { wmanIfSsOfdmaUplinkChannelEntry 25 }

wmanIfSsOfdmaHARQAackDelayULBurst OBJECT-TYPE
        SYNTAX      INTEGER {oneframeoffset(1),
                             twoframesoffset(2),
                             threeframesoffset(3)}
        MAX-ACCESS  read-only
        STATUS      current
        DESCRIPTION
            "This object defines the OFDMA H-ARQ ACK delay for UL burst. 
             1 = one frame offset
             2 = two frames offset
             3 = three frames offset"
        REFERENCE 
            "Subclause 11.3.1, table 353, in IEEE 802.16-2004"
	    ::= { wmanIfSsOfdmaUplinkChannelEntry 26 }

wmanIfSsOfdmaCQICHBandAMCTranaDelay OBJECT-TYPE
        SYNTAX      INTEGER (0 .. 255)
        UNITS       "Frame"
        MAX-ACCESS  read-only
        STATUS      current
        DESCRIPTION
            "This object defines the OFDMA CQICH band AMC transition
             delay."
        REFERENCE
            "Subclause 11.3.1, table 353, in IEEE 802.16-2004"
        ::= { wmanIfSsOfdmaUplinkChannelEntry 27 }

wmanIfSsOfdmaDownlinkChannelTable OBJECT-TYPE
        SYNTAX      SEQUENCE OF WmanIfSsOfdmaDownlinkChannelEntry
        MAX-ACCESS  not-accessible
        STATUS      current
        DESCRIPTION
            "This table contains DCD channel attributes, defining the
             transmission characteristics of downlink channels"
        REFERENCE
            "Subclause 11.4.1, Table 358, in IEEE 802.16-2004"
        ::= { wmanIfSsOfdmaPhy 2 }

wmanIfSsOfdmaDownlinkChannelEntry OBJECT-TYPE
        SYNTAX      WmanIfSsOfdmaDownlinkChannelEntry
        MAX-ACCESS  not-accessible
        STATUS      current
        DESCRIPTION
            "This table provides one row for each downlink channel of
             multi-sector BS, and is indexed by BS ifIndex. An entry in
             this table exists for each ifEntry of BS with an ifType of
             propBWAp2Mp."
        INDEX       { ifIndex }
        ::= { wmanIfSsOfdmaDownlinkChannelTable 1 }

WmanIfSsOfdmaDownlinkChannelEntry ::= SEQUENCE {
        wmanIfSsOfdmaBsEIRP                     INTEGER,
        wmanIfSsOfdmaChannelNumber              WmanIfChannelNumber,
        wmanIfSsOfdmaTTG                        INTEGER,
        wmanIfSsOfdmaRTG                        INTEGER,
        wmanIfSsOfdmaInitRngMaxRSS              INTEGER,
        wmanIfSsOfdmaDownlinkCenterFreq         Unsigned32,
        wmanIfSsOfdmaBsId                       WmanIfBsIdType,
        wmanIfSsOfdmaMacVersion                 WmanIfMacVersion,
        wmanIfSsOfdmaFrameDurationCode          INTEGER,
        wmanIfSsOfdmaSizeCqichIdField           INTEGER,
        wmanIfSsOfdmaHARQAackDelayBurst         INTEGER}

wmanIfSsOfdmaBsEIRP OBJECT-TYPE
        SYNTAX      INTEGER (0..65535)
        UNITS       "dBm"
        MAX-ACCESS  read-only
        STATUS      current
        DESCRIPTION
            "The EIRP is the equivalent isotropic radiated power of
             the base station, which is computed for a simple
             single-antenna transmitter."
        REFERENCE
            "Subclause 11.4.1, table 358, in IEEE 802.16-2004"
        ::= { wmanIfSsOfdmaDownlinkChannelEntry 1 }

wmanIfSsOfdmaChannelNumber OBJECT-TYPE
        SYNTAX      WmanIfChannelNumber
        MAX-ACCESS  read-only
        STATUS      current
        DESCRIPTION
            "Downlink channel number as defined in 8.5. Used for
             license-exempt operation only."
        REFERENCE
            "Subclause 11.4.1, table 358, in IEEE 802.16-2004"
        ::= { wmanIfSsOfdmaDownlinkChannelEntry 2 }

wmanIfSsOfdmaTTG OBJECT-TYPE
        SYNTAX      INTEGER (0..255)
        MAX-ACCESS  read-only
        STATUS      current
        DESCRIPTION
            "Transmit / Receive Transition Gap."
        REFERENCE
            "Subclause 11.4.1, table 358, in IEEE 802.16-2004"
        ::= { wmanIfSsOfdmaDownlinkChannelEntry 3 }

wmanIfSsOfdmaRTG OBJECT-TYPE
        SYNTAX      INTEGER (0..255)
        MAX-ACCESS  read-only
        STATUS      current
        DESCRIPTION
            "Receive / Transmit Transition Gap."
        REFERENCE
            "Subclause 11.4.1, table 358, in IEEE 802.16-2004"
        ::= { wmanIfSsOfdmaDownlinkChannelEntry 4 }

wmanIfSsOfdmaInitRngMaxRSS OBJECT-TYPE
        SYNTAX      INTEGER (0..65535)
        UNITS       "dBm"
        MAX-ACCESS  read-only
        STATUS      current
        DESCRIPTION
            "Initial Ranging Max. Received Signal Strength at BS
             Signed in units of 1 dBm."
        REFERENCE
            "Subclause 11.4.1, table 358, in IEEE 802.16-2004"
        ::= { wmanIfSsOfdmaDownlinkChannelEntry 5 }

wmanIfSsOfdmaDownlinkCenterFreq OBJECT-TYPE
        SYNTAX      Unsigned32
        UNITS       "kHz"
        MAX-ACCESS  read-only
        STATUS      current
        DESCRIPTION
            "Downlink center frequency (kHz)."
        REFERENCE
            "Subclause 11.4.1, table 358, in IEEE 802.16-2004"
        ::= { wmanIfSsOfdmaDownlinkChannelEntry 6 }

wmanIfSsOfdmaBsId OBJECT-TYPE
        SYNTAX      WmanIfBsIdType
        MAX-ACCESS  read-only
        STATUS      current
        DESCRIPTION
            "Base station ID."
        REFERENCE
            "Subclause 11.4.1, table 358, in IEEE 802.16-2004"
        ::= { wmanIfSsOfdmaDownlinkChannelEntry 7 }

wmanIfSsOfdmaMacVersion OBJECT-TYPE
        SYNTAX      WmanIfMacVersion
        MAX-ACCESS  read-only
        STATUS      current
        DESCRIPTION
            "This parameter specifies the version of 802.16 to which
             the message originator conforms."
        REFERENCE
            "Subclause 11.4.1, table 358, in IEEE 802.16-2004"
        ::= { wmanIfSsOfdmaDownlinkChannelEntry 8 }

wmanIfSsOfdmaFrameDurationCode OBJECT-TYPE
        SYNTAX      INTEGER {aASGap(0),
                             duration2ms(1),
                             duration2dot5ms(2),
                             duration4ms(3),
                             duration5ms(4),
                             duration8ms(5),
                             duration10ms(6),
                             duration12dot5ms(7),
                             duration20ms(8)}
        MAX-ACCESS  read-only
        STATUS      current
        DESCRIPTION
            "The duration of the frame. The frame duration code values
             are specified in Table 272."
        REFERENCE
            "Subclause 11.4.1, table 358, in IEEE 802.16-2004"
        ::= { wmanIfSsOfdmaDownlinkChannelEntry 9 }

wmanIfSsOfdmaSizeCqichIdField OBJECT-TYPE
        SYNTAX      INTEGER {threebits(1),
                             fourbits(2),
                             fivebits(3),
                             sixbits(4),
                             sevenbits(5),
                             eightbits(6),
                             ninebits(7)}
        MAX-ACCESS  read-only
        STATUS      current
        DESCRIPTION
            "This object defines the size of CQICH ID field.
             0 = Reserved
             1 = 3 bits
             2 = 4 bits
             3 = 5 bits
             4 = 6 bits
             5 = 7 bits
             6 = 8 bits
             7 = 9 bits
             8...255 = Reserved"
        REFERENCE
            "Subclause 11.3.1, table 358, in IEEE 802.16-2004"
        ::= { wmanIfSsOfdmaDownlinkChannelEntry 10 }

wmanIfSsOfdmaHARQAackDelayBurst OBJECT-TYPE
        SYNTAX      INTEGER {oneframeoffset(1),
                             twoframesoffset(2),
                             threeframesoffset(3)}
        MAX-ACCESS  read-only
        STATUS      current
        DESCRIPTION
            "This object defines the OFDMA H-ARQ ACK delay for DL burst. 
             1 = one frame offset
             2 = two frames offset
             3 = three frames offset"
        REFERENCE
            "Subclause 11.3.1, table 358, in IEEE 802.16-2004"
        ::= { wmanIfSsOfdmaDownlinkChannelEntry 11 }

wmanIfSsOfdmaUcdBurstProfileTable OBJECT-TYPE
        SYNTAX      SEQUENCE OF WmanIfSsOfdmaUcdBurstProfileEntry
        MAX-ACCESS  not-accessible
        STATUS      current
        DESCRIPTION
            "This table contains UCD burst profiles for each uplink
             channel"
        REFERENCE
            "Subclause 11.3.1.1, table 288 and 357, in IEEE 802.16-2004"
        ::= { wmanIfSsOfdmaPhy 3 }

wmanIfSsOfdmaUcdBurstProfileEntry OBJECT-TYPE
        SYNTAX      WmanIfSsOfdmaUcdBurstProfileEntry
        MAX-ACCESS  not-accessible
        STATUS      current
        DESCRIPTION
            "This table provides one row for each UCD burst profile.
             This table is double indexed. The primary index is an
             ifIndex with an ifType of propBWAp2Mp. The secondary index
             is wmanIfSsOfdmaUiucIndex."
        INDEX       { ifIndex, wmanIfSsOfdmaUiucIndex }
        ::= { wmanIfSsOfdmaUcdBurstProfileTable 1 }

WmanIfSsOfdmaUcdBurstProfileEntry ::= SEQUENCE {
        wmanIfSsOfdmaUiucIndex                  INTEGER,
        wmanIfSsOfdmaUcdFecCodeType             WmanIfOfdmaFecCodeType,
        wmanIfSsOfdmaRangingDataRatio           INTEGER,
        wmanIfSsOfdmaNorCOverNOverride          OCTET STRING}

wmanIfSsOfdmaUiucIndex OBJECT-TYPE
        SYNTAX      INTEGER (1 .. 10)
        MAX-ACCESS 	read-only
        STATUS      current
        DESCRIPTION
            "The Uplink Interval Usage Code indicates the uplink burst
             profile in the UCD message, and is used along with ifIndex
             to identify an entry in the
             wmanIfSsOfdmaUcdBurstProfileTable."
        REFERENCE
            "Subclause 8.4.5.4.1, in IEEE 802.16-2004"
        ::= { wmanIfSsOfdmaUcdBurstProfileEntry 1 }

wmanIfSsOfdmaUcdFecCodeType OBJECT-TYPE
        SYNTAX      WmanIfOfdmaFecCodeType
        MAX-ACCESS  read-only
        STATUS      current
        DESCRIPTION
            "Uplink FEC code type and modulation type"
        REFERENCE
            "Subclause 11.3.1.1, table 357, in IEEE 802.16-2004"
        ::= { wmanIfSsOfdmaUcdBurstProfileEntry 2 }

wmanIfSsOfdmaRangingDataRatio OBJECT-TYPE
        SYNTAX      INTEGER (0 .. 255)
        MAX-ACCESS  read-only
        STATUS      current
        DESCRIPTION
            "Reducing factor in units of 1 dB, between the power used
             for this burst and power should be used for CDMA Ranging."
        REFERENCE
        "Subclause 11.3.1.1, table 357, in IEEE 802.16-2004"
        ::= { wmanIfSsOfdmaUcdBurstProfileEntry 3 }

wmanIfSsOfdmaNorCOverNOverride OBJECT-TYPE
        SYNTAX 	OCTET STRING (SIZE (5))
        MAX-ACCESS 	read-only
        STATUS 	current
        DESCRIPTION
            "This is a list of numbers, where each number is encoded by
             one nibble, and interpeted as a signed integer. The nibbles
             correspond in order to the list define by Table 334 in
             IEEE 802.16-2004 starting from the second line, such that
             the LS nibble of the first byte corresponds to the second
             line in the table. The number encoded by each nibble
             represents the difference in normalized C/N relative to the
             previous line in the table"
        REFERENCE
            "Subclause 11.3.1.1, table 357, in IEEE 802.16-2004"
        ::= { wmanIfSsOfdmaUcdBurstProfileEntry 4 }

wmanIfSsOfdmaDcdBurstProfileTable OBJECT-TYPE
        SYNTAX      SEQUENCE OF WmanIfSsOfdmaDcdBurstProfileEntry
        MAX-ACCESS  not-accessible
        STATUS      current
        DESCRIPTION
            "This table provides one row for each DCD burst profile.
             This table is double indexed. The primary index is an
             ifIndex with an ifType of propBWAp2Mp. The secondary index
             is wmanIfSsOfdmaDiucIndex."
        ::= { wmanIfSsOfdmaPhy 4 }

wmanIfSsOfdmaDcdBurstProfileEntry OBJECT-TYPE
        SYNTAX      WmanIfSsOfdmaDcdBurstProfileEntry
        MAX-ACCESS  not-accessible
        STATUS      current
        DESCRIPTION
            "This table provides one row for each DCD burst profile,
             and is double indexed. The primary index is an ifIndex
             with an ifType of propBWAp2Mp. The secondary index is
             wmanIfSsOfdmaDiucIndex."
        INDEX       { ifIndex, wmanIfSsOfdmaDiucIndex }
        ::= { wmanIfSsOfdmaDcdBurstProfileTable 1 }

WmanIfSsOfdmaDcdBurstProfileEntry ::= SEQUENCE {
        wmanIfSsOfdmaDiucIndex                  INTEGER,
        wmanIfSsOfdmaDownlinkFrequency          Unsigned32,
        wmanIfSsOfdmaDcdFecCodeType             WmanIfOfdmaFecCodeType,
        wmanIfSsOfdmaDiucMandatoryExitThresh    INTEGER,
        wmanIfSsOfdmaDiucMinEntryThresh         INTEGER}
                                                
wmanIfSsOfdmaDiucIndex OBJECT-TYPE
        SYNTAX      INTEGER (0 .. 12)
        MAX-ACCESS  read-only
        STATUS      current
        DESCRIPTION
            "The Downlink Interval Usage Code indicates the downlink burst
             profile in the DCD message, and is used along with ifIndex
             to identify an entry in the
             wmanIfSsOfdmaDcdBurstProfileTable."
        REFERENCE
            "Subclause 8.4.5.3.1, in IEEE 802.16-2004"
        ::= { wmanIfSsOfdmaDcdBurstProfileEntry 1 }

wmanIfSsOfdmaDownlinkFrequency OBJECT-TYPE
        SYNTAX      Unsigned32
        UNITS       "kHz"
        MAX-ACCESS  read-only
        STATUS      current
        DESCRIPTION
            "Downlink Frequency (kHz)."
        REFERENCE
            "Subclause 11.4.2, table 359, in IEEE 802.16-2004"
        ::= { wmanIfSsOfdmaDcdBurstProfileEntry 2 }

wmanIfSsOfdmaDcdFecCodeType OBJECT-TYPE
        SYNTAX      WmanIfOfdmaFecCodeType
        MAX-ACCESS  read-only
        STATUS      current
        DESCRIPTION
            "Downlink FEC code type and modulation type"
        REFERENCE
            "Subclause 11.4.2, table 363, in IEEE 802.16-2004"
        ::= { wmanIfSsOfdmaDcdBurstProfileEntry 3 }

wmanIfSsOfdmaDiucMandatoryExitThresh OBJECT-TYPE
        SYNTAX      INTEGER (0..255)
        MAX-ACCESS  read-only
        STATUS      current
        DESCRIPTION
            "DIUC mandatory exit threshold: 0 - 63.75 dB CINR at or
             below where this DIUC can no longer be used and where this
             change to a more robust DIUC is required in 0.25 dB units."
        REFERENCE
            "Subclause 11.4.2, table 363, in IEEE 802.16-2004"
        ::= { wmanIfSsOfdmaDcdBurstProfileEntry 4 }

wmanIfSsOfdmaDiucMinEntryThresh OBJECT-TYPE
        SYNTAX      INTEGER (0..255)
        MAX-ACCESS  read-only
        STATUS      current
        DESCRIPTION
            "DIUC minimum entry threshold: 0 - 63.75 dB The minimum CINR
             required to start using this DIUC when changing from a more
             robust DIUC is required, in 0.25 dB units."
        REFERENCE
            "Subclause 11.4.2, table 363, in IEEE 802.16-2004"
        ::= { wmanIfSsOfdmaDcdBurstProfileEntry 5 }
                                                
--
-- Common object group – containing common tables and objects to be 
-- implemented in both Base Station and Subscriber Station
-- 
-- wmanIfCmnPacketCs contain the Packet Convergence Sublayer objects
-- that are common to both Base Station and Subscriber Station 
--
wmanIfCmnPacketCs OBJECT IDENTIFIER ::= { wmanIfCommonObjects 1 }
        
wmanIfCmnClassifierRuleTable OBJECT-TYPE
        SYNTAX      SEQUENCE OF WmanIfCmnClassifierRuleEntry
        MAX-ACCESS  not-accessible
        STATUS      current
        DESCRIPTION
            "This table contains packet classifier rules associated
            with service flows."
        ::= { wmanIfCmnPacketCs 1 }

wmanIfCmnClassifierRuleEntry OBJECT-TYPE
        SYNTAX      WmanIfCmnClassifierRuleEntry
        MAX-ACCESS  not-accessible
        STATUS      current
        DESCRIPTION 
            "This table provides one row for each packet classifier 
             rule, and is indexed by wmanIfCmnCpsSfId and
             wmanIfCmnClassifierRuleIndex. wmanIfCmnCpsSfId
             identifies the service flow, and
             wmanIfCmnClassifierRuleIndex identifies the packet
             classifier rule."
        INDEX { ifIndex, wmanIfCmnCpsSfId,
                wmanIfCmnClassifierRuleIndex }
        ::= { wmanIfCmnClassifierRuleTable 1 }

WmanIfCmnClassifierRuleEntry::= SEQUENCE {
        wmanIfCmnClassifierRuleIndex            Unsigned32,
        wmanIfCmnClassifierRulePriority         INTEGER,
        wmanIfCmnClassifierRuleIpTosLow         INTEGER,
        wmanIfCmnClassifierRuleIpTosHigh        INTEGER,
        wmanIfCmnClassifierRuleIpTosMask        INTEGER,
        wmanIfCmnClassifierRuleIpProtocol       Integer32,
        wmanIfCmnClassifierRuleIpSourceAddr     InetAddress,
        wmanIfCmnClassifierRuleIpSourceMask     InetAddress,
        wmanIfCmnClassifierRuleIpDestAddr       InetAddress,
        wmanIfCmnClassifierRuleIpDestMask       InetAddress,
        wmanIfCmnClassifierRuleSourcePortStart  Integer32,
        wmanIfCmnClassifierRuleSourcePortEnd    Integer32,
        wmanIfCmnClassifierRuleDestPortStart    Integer32,
        wmanIfCmnClassifierRuleDestPortEnd      Integer32,
        wmanIfCmnClassifierRuleDestMacAddr      MacAddress,
        wmanIfCmnClassifierRuleDestMacMask      MacAddress,
        wmanIfCmnClassifierRuleSourceMacAddr    MacAddress,
        wmanIfCmnClassifierRuleSourceMacMask    MacAddress,
        wmanIfCmnClassifierRuleEnetProtocolType INTEGER,
        wmanIfCmnClassifierRuleEnetProtocol     Integer32,
        wmanIfCmnClassifierRuleUserPriLow       Integer32,
        wmanIfCmnClassifierRuleUserPriHigh      Integer32,
        wmanIfCmnClassifierRuleVlanId           Integer32,
        wmanIfCmnClassifierRuleState            INTEGER,
        wmanIfCmnClassifierRulePkts             Counter64,
        wmanIfCmnClassifierRuleIpv6FlowLabel    WmanIfIpv6FlowLabel,        
        wmanIfCmnClassifierRuleBitMap           WmanIfClassifierBitMap}
        
wmanIfCmnClassifierRuleIndex  OBJECT-TYPE
        SYNTAX      Unsigned32 (1..4294967295)
        MAX-ACCESS  not-accessible
        STATUS      current
        DESCRIPTION 
            "An index is assigned to each classifier in the classifiers
             table"
        ::= { wmanIfCmnClassifierRuleEntry 1 }

wmanIfCmnClassifierRulePriority OBJECT-TYPE
        SYNTAX      INTEGER (0..255)
        MAX-ACCESS  read-only
        STATUS      current
        DESCRIPTION
            "The value specifies the order of evaluation of the
             classifiers. The higher the value the higher the 
             priority. The value of 0 is used as default in
             provisioned service flows classifiers. The default
             value of 64 is used for dynamic service flow classifiers.
             If the referenced parameter is not present in a classifier
             , this object reports the default value as defined above"
        REFERENCE
            "Subclause 11.13.19.3.4.1 in IEEE 802.16-2004"
        DEFVAL      { 0 }
        ::= { wmanIfCmnClassifierRuleEntry 2 }

wmanIfCmnClassifierRuleIpTosLow OBJECT-TYPE
        SYNTAX      INTEGER (0 .. 255)
        MAX-ACCESS  read-only
        STATUS      current
        DESCRIPTION
            "The low value of a range of TOS byte values. If the
             referenced parameter is not present in a classifier, this
             object reports the value of 0."
        REFERENCE
            "Subclause 11.13.19.3.4.2 in IEEE 802.16-2004"
        ::= { wmanIfCmnClassifierRuleEntry 3 }

wmanIfCmnClassifierRuleIpTosHigh OBJECT-TYPE
        SYNTAX      INTEGER (0 .. 255)
        MAX-ACCESS  read-only
        STATUS      current
        DESCRIPTION
            "The 8-bit high value of a range of TOS byte values.
             If the referenced parameter is not present in a classifier
             , this object reports the value of 0."
        REFERENCE
            "Subclause 11.13.19.3.4.2 in IEEE 802.16-2004"
        ::= { wmanIfCmnClassifierRuleEntry 4 }

wmanIfCmnClassifierRuleIpTosMask OBJECT-TYPE
        SYNTAX      INTEGER (0 .. 255)
        MAX-ACCESS  read-only
        STATUS      current
        DESCRIPTION
            "The mask value is bitwise ANDed with TOS byte in an IP
             packet and this value is used for the range checking of
             TosLow and TosHigh. If the referenced parameter is not
             present in a classifier, this object reports the value
             of 0."
        REFERENCE
            "Subclause 11.13.19.3.4.2 in IEEE 802.16-2004"
        ::= { wmanIfCmnClassifierRuleEntry 5 }

wmanIfCmnClassifierRuleIpProtocol OBJECT-TYPE
        SYNTAX      Integer32 (0..255)
        MAX-ACCESS  read-only
        STATUS      current
        DESCRIPTION
            "This object indicates the value of the IP Protocol field
             required for IP packets to match this rule. If the
             referenced parameter is not present in a classifier, this
             object reports the value of 0."
        REFERENCE
            "Subclause 11.13.19.3.4.3 in IEEE 802.16-2004"
        ::= { wmanIfCmnClassifierRuleEntry 6 }

wmanIfCmnClassifierRuleIpSourceAddr OBJECT-TYPE
        SYNTAX      InetAddress
        MAX-ACCESS  read-only
        STATUS      current
        DESCRIPTION
            "This object specifies the value of the IP Source Address
             required for packets to match this rule. An IP packet
             matches the rule when the packet ip source address bitwise
             ANDed with the wmanIfCmnClassifierRuleIpSourceMask value
             equals the wmanIfCmnClassifierRuleIpSourceAddr value.
             If the referenced parameter is not present in a classifier
             , this object reports the value of 0.0.0.0."
        REFERENCE
            "Subclause 11.13.19.3.4.4 in IEEE 802.16-2004"
        ::= { wmanIfCmnClassifierRuleEntry 7 }

wmanIfCmnClassifierRuleIpSourceMask OBJECT-TYPE
        SYNTAX      InetAddress
        MAX-ACCESS  read-only
        STATUS      current
        DESCRIPTION
            "This object specifies which bits of a packet's IP Source
             Address that are compared to match this rule. An IP packet
             matches the rule when the packet source address bitwise
             ANDed with the
             wmanIfCmnClassifierRuleIpSourceMask value equals the
             wmanIfCmnClassifierRuleIpSourceAddr value.
             If the referenced parameter is not present in a classifier
             , this object reports the value of 0.0.0.0."
        REFERENCE
            "Subclause 11.13.19.3.4.4 in IEEE 802.16-2004"
        ::= { wmanIfCmnClassifierRuleEntry 8 }

wmanIfCmnClassifierRuleIpDestAddr OBJECT-TYPE
        SYNTAX      InetAddress
        MAX-ACCESS  read-only
        STATUS      current
        DESCRIPTION
            "This object specifies the value of the IP Destination
             Address required for packets to match this rule. An IP
             packet matches the rule when the packet IP destination
             address bitwise ANDed with the
             wmanIfCmnClassifierRuleIpDestMask value equals the
             wmanIfCmnClassifierRuleIpDestAddr value.
             If the referenced parameter is not present in a 
             classifier, this object reports the value of 0.0.0.0."
        REFERENCE
            "Subclause 11.13.19.3.4.5 in IEEE 802.16-2004"
        ::= { wmanIfCmnClassifierRuleEntry 9 }

wmanIfCmnClassifierRuleIpDestMask OBJECT-TYPE
        SYNTAX      InetAddress
        MAX-ACCESS  read-only
        STATUS      current
        DESCRIPTION
            "This object specifies which bits of a packet's IP 
             Destination Address that are compared to match this rule.
             An IP packet matches the rule when the packet destination
             address bitwise ANDed with the
             wmanIfCmnClassifierRuleIpDestMask value equals the
             wmanIfCmnClassifierRuleIpDestAddr value.
             If the referenced parameter is not present in a classifier
             , this object reports the value of 0.0.0.0."
        REFERENCE
            "Subclause 11.13.19.3.4.5 in IEEE 802.16-2004"
        ::= { wmanIfCmnClassifierRuleEntry 10 }

wmanIfCmnClassifierRuleSourcePortStart OBJECT-TYPE
        SYNTAX      Integer32 (0..65535)
        MAX-ACCESS  read-only
        STATUS      current
        DESCRIPTION
             "This object specifies the low end inclusive range of
              TCP/UDP source port numbers to which a packet is compared
              . This object is irrelevant for non-TCP/UDP IP packets.
              If the referenced parameter is not present in a
              classifier, this object reports the value of 0."
        REFERENCE
            "Subclause 11.13.19.3.4.6 in IEEE 802.16-2004"
        ::= { wmanIfCmnClassifierRuleEntry 11 }

wmanIfCmnClassifierRuleSourcePortEnd OBJECT-TYPE
        SYNTAX      Integer32 (0..65535)
        MAX-ACCESS  read-only
        STATUS      current
        DESCRIPTION
            "This object specifies the high end inclusive range of
             TCP/UDP source port numbers to which a packet is compared.
             This object is irrelevant for non-TCP/UDP IP packets.
             If the referenced parameter is not present in a classifier,
             this object reports the value of 65535."
        REFERENCE
            "Subclause 11.13.19.3.4.6 in IEEE 802.16-2004"
        ::= { wmanIfCmnClassifierRuleEntry 12 }

wmanIfCmnClassifierRuleDestPortStart OBJECT-TYPE
        SYNTAX      Integer32 (0..65535)
        MAX-ACCESS  read-only
        STATUS      current
        DESCRIPTION
            "This object specifies the low end inclusive range of
             TCP/UDP destination port numbers to which a packet is
             compared. If the referenced parameter is not present
             in a classifier, this object reports the value of 0."
        REFERENCE
            "Subclause 11.13.19.3.4.7 in IEEE 802.16-2004"
        ::= { wmanIfCmnClassifierRuleEntry 13 }

wmanIfCmnClassifierRuleDestPortEnd OBJECT-TYPE
        SYNTAX      Integer32 (0..65535)
        MAX-ACCESS  read-only
        STATUS      current
        DESCRIPTION
            "This object specifies the high end inclusive range of
             TCP/UDP destination port numbers to which a packet is
             compared. If the referenced parameter is not present
             in a classifier, this object reports the value of
             65535."
        REFERENCE
            "Subclause 11.13.19.3.4.7 in IEEE 802.16-2004"
        ::= { wmanIfCmnClassifierRuleEntry 14 }

wmanIfCmnClassifierRuleDestMacAddr OBJECT-TYPE
        SYNTAX      MacAddress
        MAX-ACCESS  read-only
        STATUS      current
        DESCRIPTION
            "An Ethernet packet matches an entry when its destination
             MAC address bitwise ANDed with 
             wmanIfCmnClassifierRuleDestMacMask equals the value of
             wmanIfCmnClassifierRuleDestMacAddr. If the referenced
             parameter is not present in a classifier, this object
             reports the value of '000000000000'H."
        REFERENCE
            "Subclause 11.13.19.3.4.8 in IEEE 802.16-2004"
        ::= { wmanIfCmnClassifierRuleEntry 15 }

wmanIfCmnClassifierRuleDestMacMask OBJECT-TYPE
        SYNTAX      MacAddress
        MAX-ACCESS  read-only
        STATUS      current
        DESCRIPTION
            "An Ethernet packet matches an entry when its destination
             MAC address bitwise ANDed with
             wmanIfCmnClassifierRuleDestMacMask equals the value of
             wmanIfCmnClassifierRuleDestMacAddr. If the referenced
             parameter is not present in a classifier, this object
             reports the value of '000000000000'H."
        REFERENCE
            "Subclause 11.13.19.3.4.8 in IEEE 802.16-2004"
        ::= { wmanIfCmnClassifierRuleEntry 16 }

wmanIfCmnClassifierRuleSourceMacAddr OBJECT-TYPE
        SYNTAX      MacAddress
        MAX-ACCESS  read-only
        STATUS      current
        DESCRIPTION
            "An Ethernet packet matches this entry when its source
             MAC address  bitwise ANDed with
             wmanIfCmnClassifierRuleSourceMacMask equals the value
             of wmanIfCmnClassifierRuleSourceMacAddr. If the
             referenced parameter is not present in a classifier,
             this object reports the value of '000000000000'H."
        REFERENCE
            "Subclause 11.13.19.3.4.9 in IEEE 802.16-2004"
        ::= { wmanIfCmnClassifierRuleEntry 17 }

wmanIfCmnClassifierRuleSourceMacMask OBJECT-TYPE
        SYNTAX      MacAddress
        MAX-ACCESS  read-only
        STATUS      current
        DESCRIPTION
            "An Ethernet packet matches an entry when its destination
             MAC address bitwise ANDed with
             wmanIfCmnClassifierRuleSourceMacMask equals the value of
             wmanIfCmnClassifierRuleSourceMacAddr. If the referenced
             parameter is not present in a classifier, this object
             reports the value of '000000000000'H."
        REFERENCE
            "Subclause 11.13.19.3.4.9 in IEEE 802.16-2004"
        ::= { wmanIfCmnClassifierRuleEntry 18 }

wmanIfCmnClassifierRuleEnetProtocolType OBJECT-TYPE
        SYNTAX      INTEGER {none(0),
                             ethertype(1),
                             dsap(2)}
        MAX-ACCESS  read-only
        STATUS      current
        DESCRIPTION
            "This object indicates the format of the layer 3 protocol
             id in the Ethernet packet. A value of none(0) means that
             the rule does not use the layer 3 protocol type as a
             matching criteria. A value of ethertype(1) means that the
             rule applies only to frames which contains an EtherType
             value. Ethertype values are contained in packets using
             the Dec-Intel-Xerox (DIX) encapsulation or the RFC1042
             Sub-Network Access Protocol (SNAP) encapsulation formats.
             A value of dsap(2) means that the rule applies only to
             frames using the IEEE802.3 encapsulation format with a
             Destination Service Access Point (DSAP) other than 0xAA
             (which is reserved for SNAP). If the Ethernet frame
             contains an 802.1P/Q Tag header (i.e. EtherType 0x8100),
             this object applies to the embedded EtherType field within
             the 802.1P/Q header. If the referenced parameter is not
             present in a classifier, this object reports the value of
             0."
        REFERENCE
            "Subclause 11.13.19.3.4.10 in IEEE 802.16-2004"
        ::= { wmanIfCmnClassifierRuleEntry 19 }

wmanIfCmnClassifierRuleEnetProtocol OBJECT-TYPE
        SYNTAX      Integer32 (0..65535)
        MAX-ACCESS  read-only
        STATUS      current
        DESCRIPTION
            "If wmanIfCmnClassifierRuleEnetProtocolType is none(0),
             this object is ignored when considering whether a packet
             matches the current rule.
             If wmanIfCmnClassifierRuleEnetProtocolType is ethertype(1)
             ,this object gives the 16-bit value of the EtherType that
             the packet must match in order to match the rule.
             If wmanIfCmnClassifierRuleEnetProtocolType is dsap(2), the
             lower 8 bits of this object's value must match the DSAP
             byte of the packet in order to match the rule.
             If the Ethernet frame contains an 802.1P/Q Tag header
             (i.e. EtherType 0x8100), this object applies to the
             embedded EtherType field within the 802.1P/Q header.
             If the referenced parameter is not present in the
             classifier, the value of this object is reported as 0."
        REFERENCE
            "Subclause 11.13.19.3.4.10 in IEEE 802.16-2004"
        ::= { wmanIfCmnClassifierRuleEntry 20 }

wmanIfCmnClassifierRuleUserPriLow OBJECT-TYPE
        SYNTAX      Integer32 (0..7)
        MAX-ACCESS  read-only
        STATUS      current
        DESCRIPTION
            "This object applies only to Ethernet frames using the
             802.1P/Q tag header (indicated with EtherType 0x8100).
             Such frames include a 16-bit Tag that contains a 3 bit
             Priority field and a 12 bit VLAN number.
             Tagged Ethernet packets must have a 3-bit Priority field
             within the range of wmanIfCmnClassifierRulePriLow and
             wmanIfCmnClassifierRulePriHigh in order to match this
             rule.
             If the referenced parameter is not present in the
             classifier, the value of this object is reported as 0."
        REFERENCE
            "Subclause 11.13.19.3.4.11 in IEEE 802.16-2004"
        ::= { wmanIfCmnClassifierRuleEntry 21 }

wmanIfCmnClassifierRuleUserPriHigh OBJECT-TYPE
        SYNTAX      Integer32 (0..7)
        MAX-ACCESS  read-only
        STATUS      current
        DESCRIPTION
            "This object applies only to Ethernet frames using the
            802.1P/Q tag header (indicated with EtherType 0x8100).
            Such frames include a 16-bit Tag that contains a 3 bit
            Priority field and a 12 bit VLAN number.
            Tagged Ethernet packets must have a 3-bit Priority
            field within the range of wmanIfCmnClassifierRulePriLow
            and wmanIfCmnClassifierRulePriHigh in order to match
            this rule.
            If the referenced parameter is not present in the 
            classifier, the value of this object is reported as 7."
        REFERENCE
            "Subclause 11.13.19.3.4.11 in IEEE 802.16-2004"
        ::= { wmanIfCmnClassifierRuleEntry 22 }

wmanIfCmnClassifierRuleVlanId OBJECT-TYPE
        SYNTAX      Integer32 (0..4095)
        MAX-ACCESS  read-only
        STATUS      current
        DESCRIPTION
            "This object applies only to Ethernet frames using the
             802.1P/Q tag header.
             If this object's value is nonzero, tagged packets must
             have a VLAN Identifier that matches the value in order
             to match the rule.
             Only the least significant 12 bits of this object's
             value are valid.
             If the referenced parameter is not present in the
             classifier, the value of this object is reported as 0."
        REFERENCE
            "Subclause 11.13.19.3.4.12 in IEEE 802.16-2004"
        ::= { wmanIfCmnClassifierRuleEntry 23 }
       
wmanIfCmnClassifierRuleState OBJECT-TYPE
        SYNTAX      INTEGER {active(1),
                             inactive(2)}
        MAX-ACCESS  read-only
        STATUS      current
        DESCRIPTION
            "This object indicates whether or not the classifier is
             enabled to classify packets to a Service Flow.
             If the referenced parameter is not present in the
             classifier, the value of this object is reported
             as active(1)."
        ::= { wmanIfCmnClassifierRuleEntry 24 }

wmanIfCmnClassifierRulePkts OBJECT-TYPE
        SYNTAX      Counter64
        MAX-ACCESS  read-only
        STATUS      current
        DESCRIPTION
            "This object counts the number of packets that have
             been classified using this entry."
        ::= { wmanIfCmnClassifierRuleEntry 25 }

wmanIfCmnClassifierRuleIpv6FlowLabel OBJECT-TYPE
        SYNTAX      WmanIfIpv6FlowLabel
        MAX-ACCESS  read-only
        STATUS      current
        DESCRIPTION
            "The value of this field specifies the matching values for
             the IPv6 Flow label field."
        ::= { wmanIfCmnClassifierRuleEntry 26 }
                
wmanIfCmnClassifierRuleBitMap OBJECT-TYPE
        SYNTAX      WmanIfClassifierBitMap
        MAX-ACCESS  read-only
        STATUS      current
        DESCRIPTION
            "This object indicates which parameter encodings were
             actually present in the entry. A bit set to '1' indicates
             the corresponding classifier encoding is present, and '0'
             means otherwise"
        ::= { wmanIfCmnClassifierRuleEntry 27 }

wmanIfCmnPhsRuleTable OBJECT-TYPE
        SYNTAX      SEQUENCE OF WmanIfCmnPhsRuleEntry
        MAX-ACCESS  not-accessible
        STATUS      current
        DESCRIPTION                                                   
            "This table contains PHS rule dictionary entries. Each
             entry contains the data of the header to be suppressed
             along with its identification - PHSI. The classifier
             uniquely maps packets to its associated PHS Rule. The
             receiving entity uses the CID and the PHSI to restore the
             PHSF. Once a PHSF has been assigned to a PHSI, it shall
             not be changed. To change the value of a PHSF on a
             service flow, a new PHS rule shall be defined, the old
             rule is removed from the service flow, and the new rule
             is added. When a classifier is deleted, any associated
             PHS rule shall also be deleted."
        REFERENCE
            "Subclause 5.2.3 in IEEE 802.16-2004"
        ::= { wmanIfCmnPacketCs 2 }

wmanIfCmnPhsRuleEntry OBJECT-TYPE
        SYNTAX      WmanIfCmnPhsRuleEntry
        MAX-ACCESS  not-accessible
        STATUS      current
        DESCRIPTION                                                   
            "This table provides one row for each PHS rule created
             dynamically by the BS and SS on a given service flow. The
             PHS rule is defined by the pair (PHSS, PHSM) for each
             distinct header data. It is indexed by 
             wmanIfCmnCpsSfId and wmanIfCmnPhsIndex. The table is
             read-only for NMS. "
        INDEX       { ifIndex, wmanIfCmnCpsSfId,
                      wmanIfCmnPhsRulePhsIndex }
        ::= { wmanIfCmnPhsRuleTable 1 }

WmanIfCmnPhsRuleEntry::= SEQUENCE {             
        wmanIfCmnPhsRulePhsIndex                INTEGER,
        wmanIfCmnPhsRulePhsField                OCTET STRING,
        wmanIfCmnPhsRulePhsMask                 OCTET STRING,
        wmanIfCmnPhsRulePhsSize                 Integer32,
        wmanIfCmnPhsRulePhsVerify               WmanIfPhsRuleVerify}
        
wmanIfCmnPhsRulePhsIndex OBJECT-TYPE
        SYNTAX      INTEGER (1..255)
        MAX-ACCESS  not-accessible
        STATUS      current
        DESCRIPTION 
            "The PHSI (PHS Index) has a value between 1 and 255, which
             uniquely references the suppressed byte string. The index
             is unique per service flow. The uplink and downlink PHSI
             values are independent of each other."
        REFERENCE
            "Subclause 11.13.19.3.7.1 in IEEE 802.16-2004"
        ::= { wmanIfCmnPhsRuleEntry 1 }
        
wmanIfCmnPhsRulePhsField OBJECT-TYPE
        SYNTAX      OCTET STRING (SIZE(0..65535))
        MAX-ACCESS  read-only
        STATUS      current
        DESCRIPTION 
            "The PHSF (PHS Field) is a string of bytes containing the
             header information to be suppressed by the sending CS and
             reconstructed by the receiving CS. The most significant
             byte of the string corresponds to the first byte of the
             CS-SDU."
        REFERENCE
            "Subclause 11.13.19.3.7.2 in IEEE 802.16-2004"
        ::= { wmanIfCmnPhsRuleEntry 2 }
        
wmanIfCmnPhsRulePhsMask OBJECT-TYPE
        SYNTAX      OCTET STRING (SIZE(0..65535))
        MAX-ACCESS  read-only
        STATUS      current
        DESCRIPTION 
            "The PHSM An 8-bit mask that indicates which bytes in the
             PHS Field (PHSF) to suppress and which bytes to not
             suppress. The PHSM allows fields, such as sequence numbers
             or checksums (which vary in value), to be excluded from
             suppression with the constant bytes around them suppressed.
             It is encodded as follows:
             bit 0:
                0 = don't suppress the 1st byte of the suppression field
                1 = suppress first byte of the suppression field
             bit 1:
                0 = don't suppress the 2nd byte of the suppression field
                1 = suppress second byte of the suppression field
             bit x:
                0 = don't suppress the (x+1) byte of the suppression
                    field
                1 = suppress (x+1) byte of the suppression field
             where the length of the octet string is ceiling
             (wmanIfCmnPhsRulePhsSize/8)."             
        REFERENCE
            "Subclause 11.13.19.3.7.3 in IEEE 802.16-2004"
        ::= { wmanIfCmnPhsRuleEntry 3 }
        
wmanIfCmnPhsRulePhsSize OBJECT-TYPE
        SYNTAX      Integer32
        UNITS       "byte"
        MAX-ACCESS  read-only
        STATUS      current
        DESCRIPTION
            "The value of this field - PHSS is the total number of bytes 
             in the header to be suppressed and then restored in a
             service flow that uses PHS."
        REFERENCE
            "Subclause 11.13.19.3.7.4 in IEEE 802.16-2004"
        DEFVAL      {0}
        ::= { wmanIfCmnPhsRuleEntry 4 }

wmanIfCmnPhsRulePhsVerify OBJECT-TYPE
        SYNTAX      WmanIfPhsRuleVerify
        MAX-ACCESS  read-only
        STATUS      current
        DESCRIPTION
            "The value of this field indicates to the sending entity 
             whether or not the packet header contents are to be
             verified prior to performing suppression."
        DEFVAL      { phsVerifyEnable }
        ::= { wmanIfCmnPhsRuleEntry 5 }
        
--
-- wmanIfCmnCps contain the Common Part Sublayer objects that are
-- common to both Base Station and Subscriber Station
--
wmanIfCmnCps OBJECT IDENTIFIER ::= { wmanIfCommonObjects 2 }

wmanIfCmnCpsServiceFlowTable OBJECT-TYPE
        SYNTAX      SEQUENCE OF WmanIfCmnCpsServiceFlowEntry
        MAX-ACCESS  not-accessible
        STATUS      current
        DESCRIPTION
            "This table contains Service Flow managed objects that
             are common in BS and SS."
        ::= { wmanIfCmnCps 1 }

wmanIfCmnCpsServiceFlowEntry OBJECT-TYPE
        SYNTAX      WmanIfCmnCpsServiceFlowEntry
        MAX-ACCESS  not-accessible
        STATUS      current
        DESCRIPTION
            "This table provides one row for each created service
             flow for a given MacAddress, and is doubly indexed by
             (wmanIfCmnCpsSfMacAddress, wmanIfCmnCpsSfId)"
        INDEX     { ifIndex, wmanIfCmnCpsSfMacAddress,
                    wmanIfCmnCpsSfId  }
        ::= { wmanIfCmnCpsServiceFlowTable 1 }

WmanIfCmnCpsServiceFlowEntry::= SEQUENCE {
        wmanIfCmnCpsSfMacAddress                MacAddress,
        wmanIfCmnCpsSfId                        Unsigned32,
        wmanIfCmnCpsSfCid                       WmanIfCidType,
        wmanIfCmnCpsSfDirection                 INTEGER,
        wmanIfCmnCpsSfState                     WmanIfSfState,
        wmanIfCmnCpsTrafficPriority             INTEGER,
        wmanIfCmnCpsMaxSustainedRate            Unsigned32,
        wmanIfCmnCpsMaxTrafficBurst             Unsigned32,
        wmanIfCmnCpsMinReservedRate             Unsigned32,
        wmanIfCmnCpsToleratedJitter             Unsigned32,
        wmanIfCmnCpsMaxLatency                  Unsigned32,
        wmanIfCmnCpsFixedVsVariableSduInd       INTEGER,
        wmanIfCmnCpsSduSize                     Unsigned32,
        wmanIfCmnCpsSfSchedulingType            WmanIfSfSchedulingType,
        wmanIfCmnCpsArqEnable                   TruthValue,
        wmanIfCmnCpsArqWindowSize               INTEGER,
        wmanIfCmnCpsArqBlockLifetime            INTEGER,
        wmanIfCmnCpsArqSyncLossTimeout          INTEGER,
        wmanIfCmnCpsArqDeliverInOrder           TruthValue,
        wmanIfCmnCpsArqRxPurgeTimeout           INTEGER,
        wmanIfCmnCpsArqBlockSize                INTEGER,
        wmanIfCmnCpsMinRsvdTolerableRate        Unsigned32,
        wmanIfCmnCpsReqTxPolicy                 BITS,
        wmanIfCmnSfCsSpecification              WmanIfCsSpecification,
        wmanIfCmnCpsTargetSaid                  INTEGER}

wmanIfCmnCpsSfMacAddress OBJECT-TYPE
        SYNTAX      MacAddress
        MAX-ACCESS  not-accessible
        STATUS      current
        DESCRIPTION
            "When this table is implemented on the basestation, this
             object contains the SS Mac address, the reported service
             flow was created for. On the SS, the value returned is
             the SS's own Mac address."
        ::= { wmanIfCmnCpsServiceFlowEntry 1 }
        
wmanIfCmnCpsSfId OBJECT-TYPE
        SYNTAX      Unsigned32 ( 1 .. 4294967295)
        MAX-ACCESS  read-only
        STATUS      current
        DESCRIPTION
            "A 32 bit quantity that uniquely identifies a service flow
             to both the subscriber station and base station (BS)."
        ::= { wmanIfCmnCpsServiceFlowEntry 2 }

wmanIfCmnCpsSfCid OBJECT-TYPE
        SYNTAX      WmanIfCidType
        MAX-ACCESS  read-only
        STATUS      current
        DESCRIPTION
            "A 16 bit channel identifier to identify the connection
             being created by DSA."
        ::= { wmanIfCmnCpsServiceFlowEntry 3 }
                
wmanIfCmnCpsSfDirection OBJECT-TYPE
        SYNTAX      INTEGER {downstream(1),
                             upstream(2)}
        MAX-ACCESS  read-only
        STATUS      current
        DESCRIPTION
            "An attribute indicating the service flow is downstream or
             upstream."
        ::= { wmanIfCmnCpsServiceFlowEntry 4 }                        
      
wmanIfCmnCpsSfState OBJECT-TYPE
        SYNTAX      WmanIfSfState
        MAX-ACCESS  read-only
        STATUS      current
        DESCRIPTION
            "wmanIfCmnCpsSfState indicates the service flow state:
             Authorized (1), Admitted (2), and Active (3) service
             flow state."
        REFERENCE
            "Subclause 6.3.14.6, in IEEE 802.16-2004"
        ::= { wmanIfCmnCpsServiceFlowEntry 5 }                
            
wmanIfCmnCpsTrafficPriority OBJECT-TYPE
        SYNTAX      INTEGER (0 .. 7)
        MAX-ACCESS  read-only
        STATUS      current
        DESCRIPTION
            "The value of this parameter specifies the priority
             assigned to a service flow. For uplink service flows,
             the BS should use this parameter when determining
             precedence in request service and grant generation,
             and the SS shall preferentially select contention
             Request opportunities for Priority Request CIDs
             based on this priority"
        REFERENCE
            "Subclause 11.13.5 in IEEE 802.16-2004"
        ::= { wmanIfCmnCpsServiceFlowEntry 6 }
        
wmanIfCmnCpsMaxSustainedRate OBJECT-TYPE
        SYNTAX      Unsigned32
        UNITS       "b/s"
        MAX-ACCESS  read-only
        STATUS      current
        DESCRIPTION
            "This parameter defines the peak information rate
             of the service. The rate is expressed in bits per
             second and pertains to the SDUs at the input to
             the system."
        REFERENCE
            "Subclause 11.13.6 in IEEE 802.16-2004"
        ::= { wmanIfCmnCpsServiceFlowEntry 7 }        
                
wmanIfCmnCpsMaxTrafficBurst OBJECT-TYPE
        SYNTAX      Unsigned32
        UNITS	    "byte"
        MAX-ACCESS  read-only
        STATUS      current
        DESCRIPTION
            "This parameter defines the maximum burst size that
             must be accommodated for the service."
        REFERENCE
            "Subclause 11.13.7 in IEEE 802.16-2004"
        ::= { wmanIfCmnCpsServiceFlowEntry 8 }
                        
wmanIfCmnCpsMinReservedRate OBJECT-TYPE
        SYNTAX      Unsigned32
        UNITS       "byte" 
        MAX-ACCESS  read-only
        STATUS      current
        DESCRIPTION
            "This parameter specifies the minimum rate reserved
             for this service flow."
        REFERENCE
            "Subclause 11.13.8 in IEEE 802.16-2004"
        ::= { wmanIfCmnCpsServiceFlowEntry 9 }
                                
wmanIfCmnCpsToleratedJitter OBJECT-TYPE
        SYNTAX      Unsigned32
        UNITS       "millisecond"
        MAX-ACCESS  read-only
        STATUS      current
        DESCRIPTION
            "This parameter defines the Maximum delay 
             variation (jitter) for the connection."
        REFERENCE
            "Subclause 11.13.13 in IEEE 802.16-2004"
        ::= { wmanIfCmnCpsServiceFlowEntry 10 }
                                
wmanIfCmnCpsMaxLatency OBJECT-TYPE
        SYNTAX      Unsigned32
        UNITS       "millisecond"
        MAX-ACCESS  read-only
        STATUS      current
        DESCRIPTION
            "The value of this parameter specifies the maximum
             latency between the reception of a packet by the BS
             or SS on its network interface and the forwarding
             of the packet to its RF Interface."
        REFERENCE
            "Subclause 11.13.14 in IEEE 802.16-2004"
        ::= { wmanIfCmnCpsServiceFlowEntry 11 }

wmanIfCmnCpsFixedVsVariableSduInd OBJECT-TYPE
        SYNTAX      INTEGER {variableLength(0),
                             fixedLength(1)}
        MAX-ACCESS  read-only
        STATUS      current
        DESCRIPTION
            "The value of this parameter specifies whether the SDUs
             on the service flow are variable-length (0) or 
             fixed-length (1). The parameter is used only if
             packing is on for the service flow. The default value
             is 0, i.e.,variable-length SDUs."
        REFERENCE
            "Subclause 11.13.15 in IEEE 802.16-2004"
        DEFVAL      { variableLength }
        ::= { wmanIfCmnCpsServiceFlowEntry 12 }
        
wmanIfCmnCpsSduSize OBJECT-TYPE
        SYNTAX      Unsigned32
        UNITS       "byte"
        MAX-ACCESS  read-only
        STATUS      current
        DESCRIPTION
            "The value of this parameter specifies the length of the
             SDU for a fixed-length SDU service flow. This parameter
             is used only if packing is on and the service flow is
             indicated as carrying fixed-length SDUs. The default
             value is 49 bytes, i.e., VC-switched ATM cells with PHS.
             The parameter is relevant for both ATM and Packet
             Convergence Sublayers."
        REFERENCE
            "Subclause 11.13.16 in IEEE 802.16-2004"
        DEFVAL      { 49 }
        ::= { wmanIfCmnCpsServiceFlowEntry 13 }
        
wmanIfCmnCpsSfSchedulingType OBJECT-TYPE
        SYNTAX      WmanIfSfSchedulingType
        MAX-ACCESS  read-only
        STATUS      current
        DESCRIPTION
            "Specifies the upstream scheduling service used for
             upstream service flow. If the referenced parameter
             is not present in the corresponding 802.16 QOS
             Parameter Set of an upstream service flow, the
             default value of this object is bestEffort(2)."
        REFERENCE
            "Subclause 11.13.11 in IEEE 802.16-2004"
        DEFVAL         { bestEffort }
        ::= { wmanIfCmnCpsServiceFlowEntry 14 }

wmanIfCmnCpsArqEnable OBJECT-TYPE
        SYNTAX      TruthValue
        MAX-ACCESS  read-only
        STATUS      current
        DESCRIPTION
            "True(1) ARQ enabling is requested for the connection."
        ::= { wmanIfCmnCpsServiceFlowEntry 15 }

wmanIfCmnCpsArqWindowSize	 OBJECT-TYPE
        SYNTAX	    INTEGER (1..1024)
        MAX-ACCESS  read-only
        STATUS      current
        DESCRIPTION
            "Indicates the maximum number of unacknowledged 
		     fragments at any time."
        ::= { wmanIfCmnCpsServiceFlowEntry 16 }

wmanIfCmnCpsArqBlockLifetime OBJECT-TYPE
        SYNTAX	    INTEGER (0 .. 65535)
        UNITS	    "10 us"
        MAX-ACCESS  read-only
        STATUS      current
        DESCRIPTION
            "The maximum time interval an ARQ fragment will be
             managed by the transmitter ARQ machine, once
             initial transmission of the fragment has occured.
             If transmission or retransmission of the fragment
             is not acknowledged by the receiver before the 
             time limit is reached, the fragment is discarded.
             A value of 0 means Infinite."
        ::= { wmanIfCmnCpsServiceFlowEntry 17 }

wmanIfCmnCpsArqSyncLossTimeout OBJECT-TYPE
        SYNTAX	    INTEGER (0 .. 65535 )
        UNITS	    "10 us"
        MAX-ACCESS  read-only
        STATUS      current
        DESCRIPTION
            "The maximum interval before declaring a loss
		     of synchronization of the sender and receiver
		     state machines. A value of 0 means Infinite."
        ::= { wmanIfCmnCpsServiceFlowEntry 18 }

wmanIfCmnCpsArqDeliverInOrder  OBJECT-TYPE
        SYNTAX      TruthValue
        MAX-ACCESS  read-only
        STATUS      current
        DESCRIPTION
            "Indicates whether or not data is to be delivered
             by the receiving MAC to its client application
             in the order in which data was handed off to the
             originating MAC."
        ::= { wmanIfCmnCpsServiceFlowEntry 19 }

wmanIfCmnCpsArqRxPurgeTimeout  OBJECT-TYPE
        SYNTAX	    INTEGER (0 .. 65535)
        UNITS	    "10 us"
        MAX-ACCESS  read-only
        STATUS      current
        DESCRIPTION
            "Indicates the time interval the ARQ window is advanced
             after a fragment is received. A value of 0 means
             Infinite."
        ::= { wmanIfCmnCpsServiceFlowEntry 20 }

wmanIfCmnCpsArqBlockSize OBJECT-TYPE
        SYNTAX	    INTEGER (1..2040)
        UNITS       "byte"
        MAX-ACCESS  read-only
        STATUS      current
        DESCRIPTION
            "This value of this parameter specifies the size of an
             ARQ block. This parameter shall be established by
             negotiation during the connection creation dialog."
        REFERENCE
            "Subclause 11.13.18.8 in IEEE 802.16-2004"             
        ::= { wmanIfCmnCpsServiceFlowEntry 21 }

wmanIfCmnCpsMinRsvdTolerableRate OBJECT-TYPE
        SYNTAX      Unsigned32
        UNITS       "b/s"
        MAX-ACCESS  read-only
        STATUS      current
        DESCRIPTION
            "Minimum Tolerable Traffic Rate = R (bits/sec) with
             time base T(sec) means the following. Let S denote
             additional demand accumulated at the MAC SAP of the
             transmitter during an arbitrary time interval of the
             length T. Then the amount of data forwarded at the
             receiver to CS (in bits) during this interval should
             be not less than min {S, R * T}."
        REFERENCE
            "Subclause 11.13.9 in IEEE 802.16-2004"
        ::= { wmanIfCmnCpsServiceFlowEntry 22 }
        
wmanIfCmnCpsReqTxPolicy OBJECT-TYPE
        SYNTAX      BITS {noBroadcastBwReq(0),
                          reserved1(1),
                          noPiggybackReq(2),
                          noFragmentData(3),
                          noPHS(4),
                          noSduPacking(5),
                          noCrc(6),
                          reserved2(7)} 
        MAX-ACCESS  read-only
        STATUS      current
        DESCRIPTION
            "The value of this parameter provides the capability to
             specify certain attributes for the associated service
             flow. An attribute is enabled by setting the
             corresponding bit position to 1."
        REFERENCE
            "Subclause 11.13.12 in IEEE 802.16-2004"
        ::= { wmanIfCmnCpsServiceFlowEntry 23 }

wmanIfCmnSfCsSpecification OBJECT-TYPE
        SYNTAX      WmanIfCsSpecification
        MAX-ACCESS  read-only
        STATUS      current
        DESCRIPTION
            "This parameter specifies the convergence sublayer
             encapsulation mode."
        REFERENCE
            "Subclause 11.13.19.1 in IEEE 802.16-2004"
        ::= { wmanIfCmnCpsServiceFlowEntry 24 }

wmanIfCmnCpsTargetSaid OBJECT-TYPE
        SYNTAX      INTEGER (0 .. 65535)
        MAX-ACCESS  read-only
        STATUS      current
        DESCRIPTION
            "The target SAID parameter indicates the SAID onto
             which the service flow being set up shall be mapped."
        REFERENCE
            "Subclause 11.13.17 in IEEE 802.16-2004"
        ::= { wmanIfCmnCpsServiceFlowEntry 25 }
                            
--
-- wmanIfCmnBsSsConfigurationTable contains global parameters
-- common in BS and SS         
--
wmanIfCmnBsSsConfigurationTable OBJECT-TYPE
        SYNTAX      SEQUENCE OF WmanIfCmnBsSsConfigurationEntry
        MAX-ACCESS  not-accessible
        STATUS      current
        DESCRIPTION
            "This table provides one row for each BS sector that
             contains the system parameters common in both SS and
             BS. All SSs shall have the same parameters as the BS
             to which the SSs are associated."
        REFERENCE
            "Subclause 10.1 in IEEE 802.16-2004"
        ::= { wmanIfCmnCps 2 }

wmanIfCmnBsSsConfigurationEntry OBJECT-TYPE
        SYNTAX      WmanIfCmnBsSsConfigurationEntry
        MAX-ACCESS  not-accessible
        STATUS      current
        DESCRIPTION
            "This table is indexed by ifIndex, indicating BS
             sector."
        INDEX       { ifIndex }
        ::= { wmanIfCmnBsSsConfigurationTable 1 }

WmanIfCmnBsSsConfigurationEntry ::= SEQUENCE {
        wmanIfCmnInvitedRangRetries             INTEGER,
        wmanIfCmnDSxReqRetries                  Unsigned32,
        wmanIfCmnDSxRespRetries                 Unsigned32,
        wmanIfCmnT7Timeout                      INTEGER,
        wmanIfCmnT8Timeout                      INTEGER,
        wmanIfCmnT10Timeout                     INTEGER,
        wmanIfCmnT22Timeout                     INTEGER}
               
wmanIfCmnInvitedRangRetries OBJECT-TYPE
        SYNTAX      INTEGER (16..65535)
        MAX-ACCESS  read-write
        STATUS      current
        DESCRIPTION
            "Number of retries on inviting Ranging Requests."
        ::= { wmanIfCmnBsSsConfigurationEntry 1 }

wmanIfCmnDSxReqRetries OBJECT-TYPE
        SYNTAX      Unsigned32
        MAX-ACCESS  read-write
        STATUS      current
        DESCRIPTION
            "Number of Timeout Retries on DSA/DSC/DSD Requests."
        DEFVAL      { 3 }
        ::= { wmanIfCmnBsSsConfigurationEntry 2 }

wmanIfCmnDSxRespRetries OBJECT-TYPE
        SYNTAX      Unsigned32
        MAX-ACCESS  read-write
        STATUS      current
        DESCRIPTION
            "Number of Timeout Retries on DSA/DSC/DSD Responses."
        DEFVAL      { 3 }
        ::= { wmanIfCmnBsSsConfigurationEntry 3 }

wmanIfCmnT7Timeout OBJECT-TYPE
        SYNTAX      INTEGER (0 .. 1000)
        UNITS       "milliseconds"
        MAX-ACCESS  read-write
        STATUS      current
        DESCRIPTION
            "Wait for DSA/DSC/DSD Response Timeout in ms."
        ::= { wmanIfCmnBsSsConfigurationEntry 4 }

wmanIfCmnT8Timeout OBJECT-TYPE
        SYNTAX      INTEGER (0 .. 300)
        UNITS       "milliseconds"
        MAX-ACCESS  read-write
        STATUS      current
        DESCRIPTION
            "Wait for DSA/DSC/DSD Acknowledge Timeout in ms."
        ::= { wmanIfCmnBsSsConfigurationEntry 5 }

wmanIfCmnT10Timeout OBJECT-TYPE
        SYNTAX      INTEGER (0 .. 3000)
        UNITS       "milliseconds"
        MAX-ACCESS  read-write
        STATUS      current
        DESCRIPTION
            "Wait for Transaction End timeout in ms."
        ::= { wmanIfCmnBsSsConfigurationEntry 6 }

wmanIfCmnT22Timeout OBJECT-TYPE
        SYNTAX      INTEGER (0 .. 500)
        UNITS       "milliseconds"
        MAX-ACCESS  read-write
        STATUS      current
        DESCRIPTION
            "Wait for ARQ Reset in ms."
        ::= { wmanIfCmnBsSsConfigurationEntry 7 }
       
-- Common PKM  group
-- wmanIfCmnPkmObjects contain the Privacy Sublayer objects that are
-- common to both Base Station and Subscriber Station
--
wmanIfCmnPkmObjects OBJECT IDENTIFIER ::= { wmanIfCommonObjects  3 }

--
-- Table wmanIfCmnCryptoSuiteTable
--
wmanIfCmnCryptoSuiteTable OBJECT-TYPE
        SYNTAX      SEQUENCE OF   WmanIfCmnCryptoSuiteEntry
        MAX-ACCESS  not-accessible
        STATUS      current
        DESCRIPTION
            "This table describes the PKM cryptographic suite
             capabilites for each SS or BS wireless interface."
        ::= { wmanIfCmnPkmObjects  1 }

wmanIfCmnCryptoSuiteEntry OBJECT-TYPE
        SYNTAX      WmanIfCmnCryptoSuiteEntry
        MAX-ACCESS  not-accessible
        STATUS      current
        DESCRIPTION
            "Each entry contains the cryptographic suite pair that SS
             or BS supports."
        INDEX       { ifIndex, wmanIfCmnCryptoSuiteIndex }
        ::= { wmanIfCmnCryptoSuiteTable  1 }

WmanIfCmnCryptoSuiteEntry ::= SEQUENCE {
        wmanIfCmnCryptoSuiteIndex               Integer32,
        wmanIfCmnCryptoSuiteDataEncryptAlg      WmanIfDataEncryptAlgId,
        wmanIfCmnCryptoSuiteDataAuthentAlg      WmanIfDataAuthAlgId,
        wmanIfCmnCryptoSuiteTekEncryptAlg       WmanIfTekEncryptAlgId}

wmanIfCmnCryptoSuiteIndex OBJECT-TYPE
        SYNTAX      Integer32 (1 .. 1000) 
        MAX-ACCESS  not-accessible
        STATUS      current
        DESCRIPTION
            "The index for a cryptographic suite row."
        ::= { wmanIfCmnCryptoSuiteEntry 1 }

wmanIfCmnCryptoSuiteDataEncryptAlg OBJECT-TYPE
        SYNTAX      WmanIfDataEncryptAlgId
        MAX-ACCESS  read-only
        STATUS      current
        DESCRIPTION
            "The value of this object is the data encryption algorithm
             for this cryptographic suite capability."
        REFERENCE
            "Table 375, IEEE 802.16-2004"
        ::= { wmanIfCmnCryptoSuiteEntry 2 }

wmanIfCmnCryptoSuiteDataAuthentAlg OBJECT-TYPE
        SYNTAX      WmanIfDataAuthAlgId
        MAX-ACCESS  read-only
        STATUS      current
        DESCRIPTION
            "The value of this object is the data authentication
             algorithm for this cryptographic suite capability."
        REFERENCE
            "Table 376, IEEE 802.16-2004"
        ::= { wmanIfCmnCryptoSuiteEntry 3 }

wmanIfCmnCryptoSuiteTekEncryptAlg OBJECT-TYPE
        SYNTAX      WmanIfTekEncryptAlgId
        MAX-ACCESS  read-only
        STATUS      current
        DESCRIPTION
            "The value of this object is the TEK key encryption
             algorithm for this cryptographic suite capability."
        REFERENCE
            "Table 377, IEEE 802.16-2004"
        ::= { wmanIfCmnCryptoSuiteEntry 4 }

--
-- Conformance Information
--
wmanIfMibConformance OBJECT IDENTIFIER ::= {wmanIfMib 2}
wmanIfMibGroups      OBJECT IDENTIFIER ::= {wmanIfMibConformance 1}
wmanIfMibCompliances OBJECT IDENTIFIER ::= {wmanIfMibConformance 2}

-- compliance statements
wmanIfMibCompliance MODULE-COMPLIANCE
        STATUS      current
        DESCRIPTION
            "The compliance statement for devices that implement
             Wireless MAN interfaces as defined in IEEE 802.16-2004."

        MODULE  -- wmanIfMib

        MANDATORY-GROUPS            -- unconditionally mandatory groups
            { wmanIfMibCommonGroup }
            
        GROUP wmanIfMibQoSGroup     -- unconditionally mandatory group
        DESCRIPTION
            "This group is mandatory for Base Station and subscriber
             station."
                    
        GROUP wmanIfMibBsGroup      -- conditionally mandatory group
        DESCRIPTION
            "This group is mandatory for Base Station."

        GROUP wmanIfMibBsAasGroup   -- optional group
        DESCRIPTION
            "This group is mandatory for Base Station."
            
        GROUP wmanIfMibSsGroup      -- conditionally mandatory group
        DESCRIPTION
            "This group is mandatory for Subscriber Station."

        GROUP wmanIfMibBsOfdmGroup  -- conditionally mandatory group
        DESCRIPTION
            "This group is mandatory for Base Station
             implementaing the OFDM PHY."
            
        GROUP wmanIfMibSsOfdmGroup  -- conditionally mandatory group
        DESCRIPTION
            "This group is mandatory for Subscriber Station
             implementing the OFDM PHY."            

        GROUP wmanIfMibBsOfdmaGroup -- conditionally mandatory group
        DESCRIPTION
            "This group is mandatory for Base Station
             implementaing the OFDMA PHY."
            
        GROUP wmanIfMibSsOfdmaGroup -- conditionally mandatory group
        DESCRIPTION
            "This group is mandatory for Subscriber Station
             implementing the OFDMA PHY."
             
        GROUP wmanIfMibBsNotificationGroup -- unconditionally
                                           -- mandatory groups
        DESCRIPTION
            "This group is mandatory for Base Station."
                         
        GROUP wmanIfMibSsNotificationGroup -- optional group
        DESCRIPTION
            "This group is optional for Subscriber Station."

        GROUP wmanIfMibCmnPhsGroup -- optional group
        DESCRIPTION
            "This group is optional for Base Station and 
             Subscriber Station."
            
        GROUP wmanIfMibBsPhsGroup -- optional group
        DESCRIPTION
            "This group is optional for Base Station."
        ::= { wmanIfMibCompliances 1 }
                     
wmanIfMibCommonGroup     OBJECT-GROUP
        OBJECTS {-- Classification
                 wmanIfCmnClassifierRulePriority,
                 wmanIfCmnClassifierRuleIpTosLow,
                 wmanIfCmnClassifierRuleIpTosHigh,
                 wmanIfCmnClassifierRuleIpTosMask,
                 wmanIfCmnClassifierRuleIpProtocol,
                 wmanIfCmnClassifierRuleIpSourceAddr,
                 wmanIfCmnClassifierRuleIpSourceMask,
                 wmanIfCmnClassifierRuleIpDestAddr,
                 wmanIfCmnClassifierRuleIpDestMask,
                 wmanIfCmnClassifierRuleSourcePortStart,
                 wmanIfCmnClassifierRuleSourcePortEnd,
                 wmanIfCmnClassifierRuleDestPortStart,
                 wmanIfCmnClassifierRuleDestPortEnd,
                 wmanIfCmnClassifierRuleDestMacAddr,
                 wmanIfCmnClassifierRuleDestMacMask,
                 wmanIfCmnClassifierRuleSourceMacAddr,
                 wmanIfCmnClassifierRuleSourceMacMask,
                 wmanIfCmnClassifierRuleEnetProtocolType,
                 wmanIfCmnClassifierRuleEnetProtocol,
                 wmanIfCmnClassifierRuleUserPriLow,
                 wmanIfCmnClassifierRuleUserPriHigh,
                 wmanIfCmnClassifierRuleVlanId,
                 wmanIfCmnClassifierRuleState,
                 wmanIfCmnClassifierRulePkts,
                 wmanIfCmnClassifierRuleIpv6FlowLabel,
                 wmanIfCmnClassifierRuleBitMap,
                 
                 -- Configuration parameters
                 wmanIfCmnCpsTargetSaid,            
                 wmanIfCmnInvitedRangRetries,
                 wmanIfCmnDSxReqRetries,
                 wmanIfCmnDSxRespRetries,
                 wmanIfCmnT7Timeout,
                 wmanIfCmnT8Timeout,
                 wmanIfCmnT10Timeout,
                 wmanIfCmnT22Timeout, 
                 wmanIfCmnCryptoSuiteDataEncryptAlg,
                 wmanIfCmnCryptoSuiteDataAuthentAlg,
                 wmanIfCmnCryptoSuiteTekEncryptAlg}
        STATUS       current
        DESCRIPTION
            "This group contains objects for both BS and SS,
             and are independent of PHY."
        ::= { wmanIfMibGroups 1 }
        
wmanIfMibQoSGroup     OBJECT-GROUP
        OBJECTS {wmanIfCmnCpsSfId,
                 wmanIfCmnCpsSfCid,
                 wmanIfCmnCpsSfDirection,
                 wmanIfCmnCpsSfState,
                 wmanIfCmnCpsTrafficPriority,
                 wmanIfCmnCpsMaxSustainedRate,
                 wmanIfCmnCpsMaxTrafficBurst,
                 wmanIfCmnCpsMinReservedRate,
                 wmanIfCmnCpsToleratedJitter,
                 wmanIfCmnCpsMaxLatency,
                 wmanIfCmnCpsFixedVsVariableSduInd,
                 wmanIfCmnCpsSduSize,
                 wmanIfCmnCpsSfSchedulingType,
                 wmanIfCmnCpsArqEnable,
                 wmanIfCmnCpsArqWindowSize,
                 wmanIfCmnCpsArqBlockLifetime,
                 wmanIfCmnCpsArqSyncLossTimeout,
                 wmanIfCmnCpsArqDeliverInOrder,
                 wmanIfCmnCpsArqRxPurgeTimeout,
                 wmanIfCmnCpsArqBlockSize,
                 wmanIfCmnCpsMinRsvdTolerableRate,
                 wmanIfCmnCpsReqTxPolicy,
                 wmanIfCmnSfCsSpecification}
        STATUS       current
        DESCRIPTION
            "This group contains QoS objects for both BS and SS."
        ::= { wmanIfMibGroups 2 }
        
wmanIfMibBsGroup     OBJECT-GROUP
        OBJECTS {-- Service classes
                 wmanIfBsSfDirection,
                 wmanIfBsServiceClassIndex,
                 wmanIfBsSfState,
                 wmanIfBsSfProvisionedTime,
                 wmanIfBsProvisionedSfRowStatus,
                 wmanIfBsSsProvisionedForSfRowStatus,
                 wmanIfBsSfCsSpecification,
                 wmanIfBsQosServiceClassName,
                 wmanIfBsQoSTrafficPriority,
                 wmanIfBsQoSMaxSustainedRate,
                 wmanIfBsQoSMaxTrafficBurst,
                 wmanIfBsQoSMinReservedRate,
                 wmanIfBsQoSToleratedJitter,
                 wmanIfBsQoSMaxLatency,
                 wmanIfBsQoSFixedVsVariableSduInd,
                 wmanIfBsQoSSduSize,
                 wmanIfBsQosScSchedulingType,
                 wmanIfBsQosScArqEnable,
                 wmanIfBsQosScArqWindowSize,
                 wmanIfBsQosScArqBlockLifetime,
                 wmanIfBsQosScArqSyncLossTimeout,
                 wmanIfBsQosScArqDeliverInOrder,
                 wmanIfBsQosScArqRxPurgeTimeout,
                 wmanIfBsQosScArqBlockSize,
                 wmanIfBsQosSCMinRsvdTolerableRate,
                 wmanIfBsQoSReqTxPolicy,
                 wmanIfBsQoSServiceClassRowStatus,
                 
                 -- Classification
                 wmanIfBsClassifierRulePriority,
                 wmanIfBsClassifierRuleIpTosLow,
                 wmanIfBsClassifierRuleIpTosHigh,
                 wmanIfBsClassifierRuleIpTosMask,
                 wmanIfBsClassifierRuleIpProtocol,
                 wmanIfBsClassifierRuleIpSourceAddr,
                 wmanIfBsClassifierRuleIpSourceMask,
                 wmanIfBsClassifierRuleIpDestAddr,
                 wmanIfBsClassifierRuleIpDestMask,
                 wmanIfBsClassifierRuleSourcePortStart,
                 wmanIfBsClassifierRuleSourcePortEnd,
                 wmanIfBsClassifierRuleDestPortStart,
                 wmanIfBsClassifierRuleDestPortEnd,
                 wmanIfBsClassifierRuleDestMacAddr,
                 wmanIfBsClassifierRuleDestMacMask,
                 wmanIfBsClassifierRuleSourceMacAddr,
                 wmanIfBsClassifierRuleSourceMacMask,
                 wmanIfBsClassifierRuleEnetProtocolType,
                 wmanIfBsClassifierRuleEnetProtocol,
                 wmanIfBsClassifierRuleUserPriLow,
                 wmanIfBsClassifierRuleUserPriHigh,
                 wmanIfBsClassifierRuleVlanId,
                 wmanIfBsClassifierRuleState,
                 wmanIfBsClassifierRulePhsSize,
                 wmanIfBsClassifierRulePhsMask,
                 wmanIfBsClassifierRulePhsVerify,
                 wmanIfBsClassifierRuleIpv6FlowLabel,
                 wmanIfBsClassifierRuleBitMap,
                 wmanIfBsClassifierRuleRowStatus,
                 
                 -- Packet counters
                 wmanIfBsSsMacSduCount,
                 wmanIfBsSsOctetCount,
                 wmanIfBsSsResetCounter,
                 wmanIfBsSsResetCounterTime,
                 
                 -- Capability negotiation
                 wmanIfBsSsBasicCid,
                 wmanIfBsSsPrimaryCid,
                 wmanIfBsSsSecondaryCid,
                 wmanIfBsSsManagementSupport,
                 wmanIfBsSsIpManagementMode,
                 wmanIfBs2ndMgmtDlQoSProfileIndex,
                 wmanIfBs2ndMgmtUlQoSProfileIndex,
                 wmanIfBsAutoSfidEnabled,
                 wmanIfBsAutoSfidRangeMin,
                 wmanIfBsAutoSfidRangeMax,
                 wmanIfBsResetSector, 
                 wmanIfBsSs2ndMgmtArqEnable,
                 wmanIfBsSs2ndMgmtArqWindowSize,
                 wmanIfBsSs2ndMgmtArqDnLinkTxDelay,
                 wmanIfBsSs2ndMgmtArqUpLinkTxDelay,
                 wmanIfBsSs2ndMgmtArqDnLinkRxDelay,
                 wmanIfBsSs2ndMgmtArqUpLinkRxDelay,
                 wmanIfBsSs2ndMgmtArqBlockLifetime,
                 wmanIfBsSs2ndMgmtArqSyncLossTimeout,
                 wmanIfBsSs2ndMgmtArqDeliverInOrder,
                 wmanIfBsSs2ndMgmtArqRxPurgeTimeout,
                 wmanIfBsSs2ndMgmtArqBlockSize,
                 wmanIfBsSsVendorIdEncoding,
                 wmanIfBsSsAasBroadcastPermission, 
                 wmanIfBsSsMaxTxPowerBpsk, 
                 wmanIfBsSsMaxTxPowerQpsk,
                 wmanIfBsSsMaxTxPower16Qam,
                 wmanIfBsSsMaxTxPower64Qam,
                 
                 -- Configuration parameters
                 wmanIfBsSsMacVersion,
                 wmanIfBsDcdInterval,
                 wmanIfBsUcdInterval,
                 wmanIfBsUcdTransition,
                 wmanIfBsDcdTransition,
                 wmanIfBsInitialRangingInterval,
                 wmanIfBsSsULMapProcTime,
                 wmanIfBsSsRangRespProcTime,
                 wmanIfBsT5Timeout,
                 wmanIfBsT9Timeout,
                 wmanIfBsT13Timeout,
                 wmanIfBsT15Timeout,
                 wmanIfBsT17Timeout,
                 wmanIfBsT27IdleTimer,
                 wmanIfBsT27ActiveTimer,
                 
                 -- Performance monitoring
                 wmanIfBsHistogramIndex,
                 wmanIfBsChannelNumber,
                 wmanIfBsStartFrame,
                 wmanIfBsDuration,
                 wmanIfBsBasicReport,
                 wmanIfBsMeanCinrReport,
                 wmanIfBsMeanRssiReport,
                 wmanIfBsStdDeviationCinrReport,
                 wmanIfBsStdDeviationRssiReport,

                 -- Capability negotiation                 
                 wmanIfBsSsReqCapUplinkCidSupport,
                 wmanIfBsSsReqCapArqSupport,
                 wmanIfBsSsReqCapDsxFlowControl,
                 wmanIfBsSsReqCapMacCrcSupport,
                 wmanIfBsSsReqCapMcaFlowControl,
                 wmanIfBsSsReqCapMcpGroupCidSupport,
                 wmanIfBsSsReqCapPkmFlowControl,
                 wmanIfBsSsReqCapAuthPolicyControl,
                 wmanIfBsSsReqCapMaxNumOfSupportedSA,
                 wmanIfBsSsReqCapIpVersion,
                 wmanIfBsSsReqCapMacCsSupportBitMap,
                 wmanIfBsSsReqCapMaxNumOfClassifier,
                 wmanIfBsSsReqCapPhsSupport,
                 wmanIfBsSsReqCapBandwidthAllocSupport,
                 wmanIfBsSsReqCapPduConstruction,
                 wmanIfBsSsReqCapTtgTransitionGap,
                 wmanIfBsSsReqCapRtgTransitionGap,
                 wmanIfBsSsRspCapUplinkCidSupport,
                 wmanIfBsSsRspCapArqSupport,
                 wmanIfBsSsRspCapDsxFlowControl,
                 wmanIfBsSsRspCapMacCrcSupport,
                 wmanIfBsSsRspCapMcaFlowControl,
                 wmanIfBsSsRspCapMcpGroupCidSupport,
                 wmanIfBsSsRspCapPkmFlowControl,
                 wmanIfBsSsRspCapAuthPolicyControl,
                 wmanIfBsSsRspCapMaxNumOfSupportedSA,
                 wmanIfBsSsRspCapIpVersion,
                 wmanIfBsSsRspCapMacCsSupportBitMap,
                 wmanIfBsSsRspCapMaxNumOfClassifier,
                 wmanIfBsSsRspCapPhsSupport,
                 wmanIfBsSsRspCapBandwidthAllocSupport,
                 wmanIfBsSsRspCapPduConstruction,
                 wmanIfBsSsRspCapTtgTransitionGap,
                 wmanIfBsSsRspCapRtgTransitionGap,
                 wmanIfBsCapUplinkCidSupport,
                 wmanIfBsCapArqSupport,
                 wmanIfBsCapDsxFlowControl,
                 wmanIfBsCapMacCrcSupport,
                 wmanIfBsCapMcaFlowControl,
                 wmanIfBsCapMcpGroupCidSupport,
                 wmanIfBsCapPkmFlowControl,
                 wmanIfBsCapAuthPolicyControl,
                 wmanIfBsCapMaxNumOfSupportedSA,
                 wmanIfBsCapIpVersion,
                 wmanIfBsCapMacCsSupportBitMap,
                 wmanIfBsCapMaxNumOfClassifier,
                 wmanIfBsCapPhsSupport,
                 wmanIfBsCapBandwidthAllocSupport,
                 wmanIfBsCapPduConstruction,
                 wmanIfBsCapTtgTransitionGap,
                 wmanIfBsCapRtgTransitionGap,
                 wmanIfBsCapCfgUplinkCidSupport,
                 wmanIfBsCapCfgArqSupport,
                 wmanIfBsCapCfgDsxFlowControl,
                 wmanIfBsCapCfgMacCrcSupport,
                 wmanIfBsCapCfgMcaFlowControl,
                 wmanIfBsCapCfgMcpGroupCidSupport,
                 wmanIfBsCapCfgPkmFlowControl,
                 wmanIfBsCapCfgAuthPolicyControl,
                 wmanIfBsCapCfgMaxNumOfSupportedSA,
                 wmanIfBsCapCfgIpVersion,
                 wmanIfBsCapCfgMacCsSupportBitMap,
                 wmanIfBsCapCfgMaxNumOfClassifier,
                 wmanIfBsCapCfgPhsSupport,
                 wmanIfBsCapCfgBandwidthAllocSupport,
                 wmanIfBsCapCfgPduConstruction,
                 wmanIfBsCapCfgTtgTransitionGap,
                 wmanIfBsCapCfgRtgTransitionGap,
                 wmanIfBsSsActionsResetSs,
                 wmanIfBsSsActionsAbortSs,
                 wmanIfBsSsActionsOverrideDnFreq,
                 wmanIfBsSsActionsOverrideChannelId,
                 wmanIfBsSsActionsDeReRegSs,
                 wmanIfBsSsActionsDeReRegSsCode,
                 wmanIfBsSsActionsRowStatus,
                 
                 -- Privacy sublayer
                 wmanIfBsPkmDefaultAuthLifetime,
                 wmanIfBsPkmDefaultTekLifetime,
                 wmanIfBsPkmDefaultSelfSigManufCertTrust,
                 wmanIfBsPkmCheckCertValidityPeriods,
                 wmanIfBsPkmAuthentInfos,
                 wmanIfBsPkmAuthRequests,
                 wmanIfBsPkmAuthReplies,
                 wmanIfBsPkmAuthRejects,
                 wmanIfBsPkmAuthInvalids,
                 wmanIfBsSsPkmAuthKeySequenceNumber,
                 wmanIfBsSsPkmAuthExpiresOld,
                 wmanIfBsSsPkmAuthExpiresNew,
                 wmanIfBsSsPkmAuthLifetime,
                 wmanIfBsSsPkmAuthReset,
                 wmanIfBsSsPkmAuthInfos,
                 wmanIfBsSsPkmAuthRequests,
                 wmanIfBsSsPkmAuthReplies,
                 wmanIfBsSsPkmAuthRejects,
                 wmanIfBsSsPkmAuthInvalids,
                 wmanIfBsSsPkmAuthRejectErrorCode,
                 wmanIfBsSsPkmAuthRejectErrorString,
                 wmanIfBsSsPkmAuthInvalidErrorCode,
                 wmanIfBsSsPkmAuthInvalidErrorString,
                 wmanIfBsSsPkmAuthPrimarySAId,
                 wmanIfBsSsPkmAuthValidStatus,
                 wmanIfBsPkmTekSAType,
                 wmanIfBsPkmTekDataEncryptAlg,
                 wmanIfBsPkmTekDataAuthentAlg,
                 wmanIfBsPkmTekEncryptAlg,
                 wmanIfBsPkmTekLifetime,
                 wmanIfBsPkmTekKeySequenceNumber,
                 wmanIfBsPkmTekExpiresOld,
                 wmanIfBsPkmTekExpiresNew,
                 wmanIfBsPkmTekReset,
                 wmanIfBsPkmKeyRequests,
                 wmanIfBsPkmKeyReplies,
                 wmanIfBsPkmKeyRejects,
                 wmanIfBsPkmTekInvalids,
                 wmanIfBsPkmKeyRejectErrorCode,
                 wmanIfBsPkmKeyRejectErrorString,
                 wmanIfBsPkmTekInvalidErrorCode,
                 wmanIfBsPkmTekInvalidErrorString,
                 
                 -- Notification
                 wmanIfBsTrapControlRegister,
                 wmanIfBsStatusTrapControlRegister,
                 wmanIfBsRssiLowThreshold,
                 wmanIfBsRssiHighThreshold,
                 wmanIfBsSsNotificationMacAddr,
                 wmanIfBsSsStatusValue,
                 wmanIfBsSsStatusInfo,
                 wmanIfBsDynamicServiceType,
                 wmanIfBsDynamicServiceFailReason,
                 wmanIfBsSsRssiStatus,
                 wmanIfBsSsRssiStatusInfo,
                 wmanIfBsSsRegisterStatus}
        STATUS       current
        DESCRIPTION
            "This group contains objects for BS, and are 
             independent of PHY."
        ::= { wmanIfMibGroups 3 }                  

wmanIfMibBsAasGroup     OBJECT-GROUP
        OBJECTS {-- AAS Configuration parameters
                 wmanIfBsAasChanFbckReqFreq,
                 wmanIfBsAasBeamSelectFreq,
                 wmanIfBsAasChanFbckReqResolution,
                 wmanIfBsAasBeamReqResolution,
                 wmanIfBsAasNumOptDiversityZones}
        STATUS       current
        DESCRIPTION
            "This group contains objects for AAS in BS."
        ::= { wmanIfMibGroups 4 }
        
wmanIfMibSsGroup     OBJECT-GROUP
        OBJECTS {-- Configuration parameters        
                 wmanIfSsLostDLMapInterval,
                 wmanIfSsLostULMapInterval,
                 wmanIfSsContentionRangRetries,
                 wmanIfSsRequestRetries,
                 wmanIfSsRegRequestRetries,
                 wmanIfSsTftpBackoffStart,
                 wmanIfSsTftpBackoffEnd,
                 wmanIfSsTftpRequestRetries,
                 wmanIfSsTftpDownloadRetries,
                 wmanIfSsTftpWait,
                 wmanIfSsToDRetries,
                 wmanIfSsToDRetryPeriod,
                 wmanIfSsT1Timeout,
                 wmanIfSsT2Timeout,
                 wmanIfSsT3Timeout,
                 wmanIfSsT4Timeout,
                 wmanIfSsT6Timeout,
                 wmanIfSsT12Timeout,
                 wmanIfSsT14Timeout,
                 wmanIfSsT16Timeout,
                 wmanIfSsT18Timeout,
                 wmanIfSsT19Timeout,
                 wmanIfSsT20Timeout,
                 wmanIfSsT21Timeout,
                 wmanIfSsSBCRequestRetries,
                 wmanIfSsTftpCpltRetries,
                 wmanIfSsT26Timeout,
                 wmanIfSsDLManagProcTime,
                 
                 -- Performance monitoring                 
                 wmanIfSsChannelNumber,
                 wmanIfSsStartFrame ,
                 wmanIfSsDuration,
                 wmanIfSsBasicReport,
                 wmanIfSsMeanCinrReport,
                 wmanIfSsStdDeviationCinrReport,
                 wmanIfSsMeanRssiReport,
                 wmanIfSsStdDeviationRssiReport,
                 
                 -- Privacy sublayer
                 wmanIfSsPkmAuthState,
                 wmanIfSsPkmAuthKeySequenceNumber,
                 wmanIfSsPkmAuthExpiresOld,
                 wmanIfSsPkmAuthExpiresNew ,
                 wmanIfSsPkmAuthReset,
                 wmanIfSsPkmAuthentInfos,
                 wmanIfSsPkmAuthRequests,
                 wmanIfSsPkmAuthReplies,
                 wmanIfSsPkmAuthRejects,
                 wmanIfSsPkmAuthInvalids,
                 wmanIfSsPkmAuthRejectErrorCode,
                 wmanIfSsPkmAuthRejectErrorString,
                 wmanIfSsPkmAuthInvalidErrorCode,
                 wmanIfSsPkmAuthInvalidErrorString ,
                 wmanIfSsPkmAuthGraceTime,
                 wmanIfSsPkmTekGraceTime,
                 wmanIfSsPkmAuthWaitTimeout,
                 wmanIfSsPkmReauthWaitTimeout,
                 wmanIfSsPkmOpWaitTimeout,
                 wmanIfSsPkmRekeyWaitTimeout,
                 wmanIfSsPkmAuthRejectWaitTimeout,
                 wmanIfSsPkmTekSAType,
                 wmanIfSsPkmTekDataEncryptAlg,
                 wmanIfSsPkmTekDataAuthentAlg,
                 wmanIfSsPkmTekEncryptAlg,
                 wmanIfSsPkmTekState,
                 wmanIfSsPkmTekKeySequenceNumber,
                 wmanIfSsPkmTekExpiresOld,
                 wmanIfSsPkmTekExpiresNew,
                 wmanIfSsPkmTekKeyRequests,
                 wmanIfSsPkmTekKeyReplies,
                 wmanIfSsPkmTekKeyRejects,
                 wmanIfSsPkmTekInvalids,
                 wmanIfSsPkmTekAuthPends,
                 wmanIfSsPkmTekKeyRejectErrorCode,
                 wmanIfSsPkmTekKeyRejectErrorString,
                 wmanIfSsPkmTekInvalidErrorCode,
                 wmanIfSsPkmTekInvalidErrorString,
                 wmanIfSsDeviceCert,
                 wmanIfSsDeviceManufCert,
                 
                 -- Notofocation
                 wmanIfSsTrapControlRegister,
                 wmanIfSsRssiLowThreshold,
                 wmanIfSsRssiHighThreshold,
                 wmanIfSsMacAddress,
                 wmanIfSsUnknownTlv,
                 wmanIfSsDynamicServiceType,
                 wmanIfSsDynamicServiceFailReason,
                 wmanIfSsRssiStatus,
                 wmanIfSsRssiStatusInfo}        
        STATUS       current
        DESCRIPTION
            "This group contains objects for SS, and are
             independent of PHY."
        ::= { wmanIfMibGroups 5 }

wmanIfMibBsOfdmGroup     OBJECT-GROUP
        OBJECTS {wmanIfBsOfdmCtBasedResvTimeout,
                 wmanIfBsOfdmBwReqOppSize,
                 wmanIfBsOfdmRangReqOppSize,
                 wmanIfBsOfdmUplinkCenterFreq,
                 wmanIfBsOfdmNumSubChReqRegionFull,
                 wmanIfBsOfdmNumSymbolsReqRegionFull,
                 wmanIfBsOfdmSubChFocusCtCode,
                 wmanIfBsOfdmUpLinkChannelId,   
                 wmanIfBsOfdmBsEIRP,
                 wmanIfBsOfdmChannelNumber,
                 wmanIfBsOfdmTTG,
                 wmanIfBsOfdmRTG,
                 wmanIfBsOfdmInitRngMaxRSS,
                 wmanIfBsOfdmDownlinkCenterFreq,
                 wmanIfBsOfdmBsId,
                 wmanIfBsOfdmMacVersion,
                 wmanIfBsOfdmFrameDurationCode,
                 wmanIfBsOfdmDownLinkChannelId,
                 wmanIfBsOfdmUcdFecCodeType,
                 wmanIfBsOfdmFocusCtPowerBoost,
                 wmanIfBsOfdmUcdTcsEnable,
                 wmanIfBsOfdmUcdBurstProfileRowStatus,
                 wmanIfBsOfdmDownlinkFrequency,
                 wmanIfBsOfdmDcdFecCodeType,
                 wmanIfBsOfdmDiucMandatoryExitThresh,
                 wmanIfBsOfdmDiucMinEntryThresh,
                 wmanIfBsOfdmTcsEnable, 
                 wmanIfBsOfdmDcdBurstProfileRowStatus,
                 wmanIfBsOfdmMinReqRegionFullTxOpp,
                 wmanIfBsOfdmMinFocusedCtTxOpp,
                 wmanIfBsOfdmMaxRoundTripDelay,
                 wmanIfBsOfdmRangeAbortTimingThold,
                 wmanIfBsOfdmRangeAbortPowerThold ,
                 wmanIfBsOfdmRangeAbortFreqThold,
                 wmanIfBsOfdmDnlkRateId,
                 wmanIfBsOfdmRatioG,        
                 wmanIfBsSsOfdmReqCapFftSizes,
                 wmanIfBsSsOfdmReqCapSsDemodulator,
                 wmanIfBsSsOfdmReqCapSsModulator,
                 wmanIfBsSsOfdmReqCapFocusedCtSupport,
                 wmanIfBsSsOfdmReqCapTcSublayerSupport,
                 wmanIfBsSsOfdmRspCapFftSizes,
                 wmanIfBsSsOfdmRspCapSsDemodulator,
                 wmanIfBsSsOfdmRspCapSsModulator,
                 wmanIfBsSsOfdmRspCapFocusedCtSupport,
                 wmanIfBsSsOfdmRspCapTcSublayerSupport,
                 wmanIfBsOfdmCapFftSizes,
                 wmanIfBsOfdmCapSsDemodulator,
                 wmanIfBsOfdmCapSsModulator,
                 wmanIfBsOfdmCapFocusedCtSupport,
                 wmanIfBsOfdmCapTcSublayerSupport,
                 wmanIfBsOfdmCapCfgFftSizes,
                 wmanIfBsOfdmCapCfgSsDemodulator,
                 wmanIfBsOfdmCapCfgSsModulator,
                 wmanIfBsOfdmCapCfgFocusedCtSupport,
                 wmanIfBsOfdmCapCfgTcSublayerSupport}
        STATUS       current
        DESCRIPTION
            "This group contains objects for BS and OFDM PHY."
        ::= { wmanIfMibGroups 6 }
        
wmanIfMibSsOfdmGroup     OBJECT-GROUP
        OBJECTS {wmanIfSsOfdmCtBasedResvTimeout,
                 wmanIfSsOfdmBwReqOppSize,
                 wmanIfSsOfdmRangReqOppSize,
                 wmanIfSsOfdmUplinkCenterFreq,
                 wmanIfSsOfdmNumSubChReqRegionFull,
                 wmanIfSsOfdmNumSymbolsReqRegionFull,
                 wmanIfSsOfdmSubChFocusCtCode,
                 wmanIfSsOfdmUpLinkChannelId,   
                 wmanIfSsOfdmBsEIRP,
                 wmanIfSsOfdmChannelNumber,
                 wmanIfSsOfdmTTG,
                 wmanIfSsOfdmRTG,
                 wmanIfSsOfdmInitRngMaxRSS,
                 wmanIfSsOfdmDownlinkCenterFreq,
                 wmanIfSsOfdmBsId,
                 wmanIfSsOfdmMacVersion,
                 wmanIfSsOfdmFrameDurationCode,
                 wmanIfSsOfdmDownLinkChannelId,
                 wmanIfSsOfdmUcdFecCodeType,
                 wmanIfSsOfdmFocusCtPowerBoost,
                 wmanIfSsOfdmUcdTcsEnable,
                 wmanIfSsOfdmDownlinkFrequency,
                 wmanIfSsOfdmDcdFecCodeType,
                 wmanIfSsOfdmDiucMandatoryExitThresh,
                 wmanIfSsOfdmDiucMinEntryThresh,
                 wmanIfSsOfdmTcsEnable}        
        STATUS       current
        DESCRIPTION
            "This group contains objects for SS and OFDM PHY."
        ::= { wmanIfMibGroups 7 }
        
wmanIfMibBsOfdmaGroup     OBJECT-GROUP
        OBJECTS {wmanIfBsOfdmaCtBasedResvTimeout,
                 wmanIfBsOfdmaBwReqOppSize,
                 wmanIfBsOfdmaRangReqOppSize,
                 wmanIfBsOfdmaUplinkCenterFreq,
                 wmanIfBsOfdmaInitRngCodes,
                 wmanIfBsOfdmaPeriodicRngCodes,
                 wmanIfBsOfdmaBWReqCodes,
                 wmanIfBsOfdmaPerRngBackoffStart,
                 wmanIfBsOfdmaPerRngBackoffEnd,
                 wmanIfBsOfdmaStartOfRngCodes,
                 wmanIfBsOfdmaPermutationBase,
                 wmanIfBsOfdmaULAllocSubchBitmap,
                 wmanIfBsOfdmaOptPermULAllocSubchBitmap,
                 wmanIfBsOfdmaBandAMCAllocThreshold,
                 wmanIfBsOfdmaBandAMCReleaseThreshold,
                 wmanIfBsOfdmaBandAMCAllocTimer,
                 wmanIfBsOfdmaBandAMCReleaseTimer,
                 wmanIfBsOfdmaBandStatRepMAXPeriod,
                 wmanIfBsOfdmaBandAMCRetryTimer,
                 wmanIfBsOfdmaSafetyChAllocThreshold,
                 wmanIfBsOfdmaSafetyChReleaseThreshold,
                 wmanIfBsOfdmaSafetyChAllocTimer,
                 wmanIfBsOfdmaSafetyChReleaseTimer,
                 wmanIfBsOfdmaBinStatRepMAXPeriod,
                 wmanIfBsOfdmaSafetyChaRetryTimer,
                 wmanIfBsOfdmaHARQAackDelayULBurst,
                 wmanIfBsOfdmaCQICHBandAMCTranaDelay,
                 wmanIfBsOfdmaBsEIRP,
                 wmanIfBsOfdmaChannelNumber,
                 wmanIfBsOfdmaTTG,
                 wmanIfBsOfdmaRTG,
                 wmanIfBsOfdmaInitRngMaxRSS,
                 wmanIfBsOfdmaDownlinkCenterFreq,
                 wmanIfBsOfdmaBsId,
                 wmanIfBsOfdmaMacVersion,
                 wmanIfBsOfdmaFrameDurationCode,
                 wmanIfBsOfdmaSizeCqichIdField,
                 wmanIfBsOfdmaHARQAackDelayBurst,
                 wmanIfBsOfdmaUcdFecCodeType,
                 wmanIfBsOfdmaRangingDataRatio,
                 wmanIfBsOfdmaNorCOverNOverride,
                 wmanIfBsOfdmaUcdBurstProfileRowStatus,
                 wmanIfBsOfdmaDownlinkFrequency,
                 wmanIfBsOfdmaDcdFecCodeType,
                 wmanIfBsOfdmaDiucMandatoryExitThresh,
                 wmanIfBsOfdmaDiucMinEntryThresh,
                 wmanIfBsOfdmaDcdBurstProfileRowStatus}        
        STATUS       current
        DESCRIPTION
            "This group contains objects for BS and OFDMA PHY."
        ::= { wmanIfMibGroups 8 }
        
wmanIfMibSsOfdmaGroup     OBJECT-GROUP
        OBJECTS {wmanIfSsOfdmaCtBasedResvTimeout,
                 wmanIfSsOfdmaBwReqOppSize,
                 wmanIfSsOfdmaRangReqOppSize,
                 wmanIfSsOfdmaUplinkCenterFreq,
                 wmanIfSsOfdmaInitRngCodes,
                 wmanIfSsOfdmaPeriodicRngCodes,
                 wmanIfSsOfdmaBWReqCodes,
                 wmanIfSsOfdmaPerRngBackoffStart,
                 wmanIfSsOfdmaPerRngBackoffEnd,
                 wmanIfSsOfdmaStartOfRngCodes,
                 wmanIfSsOfdmaPermutationBase,
                 wmanIfSsOfdmaULAllocSubchBitmap,
                 wmanIfSsOfdmaOptPermULAllocSubchBitmap,
                 wmanIfSsOfdmaBandAMCAllocThreshold,
                 wmanIfSsOfdmaBandAMCReleaseThreshold,
                 wmanIfSsOfdmaBandAMCAllocTimer,
                 wmanIfSsOfdmaBandAMCReleaseTimer,
                 wmanIfSsOfdmaBandStatRepMAXPeriod,
                 wmanIfSsOfdmaBandAMCRetryTimer,
                 wmanIfSsOfdmaSafetyChAllocThreshold,
                 wmanIfSsOfdmaSafetyChReleaseThreshold,
                 wmanIfSsOfdmaSafetyChAllocTimer,
                 wmanIfSsOfdmaSafetyChReleaseTimer,
                 wmanIfSsOfdmaBinStatRepMAXPeriod,
                 wmanIfSsOfdmaSafetyChaRetryTimer,
                 wmanIfSsOfdmaHARQAackDelayULBurst,
                 wmanIfSsOfdmaCQICHBandAMCTranaDelay,
                 wmanIfSsOfdmaBsEIRP,
                 wmanIfSsOfdmaChannelNumber,
                 wmanIfSsOfdmaTTG,
                 wmanIfSsOfdmaRTG,
                 wmanIfSsOfdmaInitRngMaxRSS,
                 wmanIfSsOfdmaDownlinkCenterFreq,
                 wmanIfSsOfdmaBsId,
                 wmanIfSsOfdmaMacVersion,
                 wmanIfSsOfdmaFrameDurationCode,
                 wmanIfSsOfdmaSizeCqichIdField,
                 wmanIfSsOfdmaHARQAackDelayBurst,
                 wmanIfSsOfdmaUiucIndex,
                 wmanIfSsOfdmaUcdFecCodeType,
                 wmanIfSsOfdmaRangingDataRatio,
                 wmanIfSsOfdmaNorCOverNOverride,
                 wmanIfSsOfdmaDiucIndex,
                 wmanIfSsOfdmaDownlinkFrequency,
                 wmanIfSsOfdmaDcdFecCodeType,
                 wmanIfSsOfdmaDiucMandatoryExitThresh,
                 wmanIfSsOfdmaDiucMinEntryThresh}        
        STATUS       current
        DESCRIPTION
            "This group contains objects for SS and OFDMA PHY."
        ::= { wmanIfMibGroups 9 }
        
wmanIfMibBsNotificationGroup     NOTIFICATION-GROUP
        NOTIFICATIONS {wmanIfBsSsStatusNotificationTrap,
                       wmanIfBsSsDynamicServiceFailTrap,
                       wmanIfBsSsRssiStatusChangeTrap,
                       wmanIfBsSsPkmFailTrap,
                       wmanIfBsSsRegistrerTrap}
        STATUS       current
        DESCRIPTION
            "This group contains event notifications for BS."
        ::= { wmanIfMibGroups 10 }
        
wmanIfMibSsNotificationGroup     NOTIFICATION-GROUP
        NOTIFICATIONS {wmanIfSsTlvUnknownTrap,
                       wmanIfSsDynamicServiceFailTrap,
                       wmanIfSsDhcpSuccessTrap,
                       wmanIfSsRssiStatusChangeTrap}
        STATUS       current
        DESCRIPTION
            "This group contains event notifications for SS."
        ::= { wmanIfMibGroups 11 }

wmanIfMibCmnPhsGroup     OBJECT-GROUP
        OBJECTS {-- Payload header supression
                 wmanIfCmnPhsRulePhsField,
                 wmanIfCmnPhsRulePhsMask,
                 wmanIfCmnPhsRulePhsSize,
                 wmanIfCmnPhsRulePhsVerify}
        STATUS       current
        DESCRIPTION
            "This group contains common objects for PHS."
        ::= { wmanIfMibGroups 12 }                  

wmanIfMibBsPhsGroup     OBJECT-GROUP
        OBJECTS {-- Payload header supression
                 wmanIfBsClassifierRulePhsSize,
                 wmanIfBsClassifierRulePhsMask,
                 wmanIfBsClassifierRulePhsVerify,
                 wmanIfBsClassifierRuleBitMap}
        STATUS       current
        DESCRIPTION
            "This group contains BS objects for PHS."
        ::= { wmanIfMibGroups 13 }                 
END
