--
-- AIRSPAN-DEMOMAX-MIB.mib
-- MIB generated by MG-SOFT Visual MIB Builder 2010 Version 8.0  Build 400
-- Wednesday, November 09, 2011 at 12:09:02
--

    AIRSPAN-DEMOMAX-MIB DEFINITIONS ::= BEGIN
 
        IMPORTS
            AsmaxVlanIdOrNone, AsmaxBsSoftwareType            
                FROM AIRSPAN-ASMAX-BS-COMMON-MIB            
            AsmaxBooleanSwitch            
                FROM AIRSPAN-ASMAX-COMMON-MIB            
            asMaxBS            
                FROM AIRSPAN-PRODUCTS-MIB            
            ifIndex, InterfaceIndex            
                FROM IF-MIB            
            InetAddressType, InetAddress            
                FROM INET-ADDRESS-MIB            
            OBJECT-GROUP, MODULE-COMPLIANCE, NOTIFICATION-GROUP            
                FROM SNMPv2-CONF            
            IpAddress, Integer32, Unsigned32, Counter32, Counter64, 
            OBJECT-TYPE, MODULE-IDENTITY, NOTIFICATION-TYPE            
                FROM SNMPv2-SMI            
            RowStatus, DisplayString, MacAddress, TruthValue, TEXTUAL-CONVENTION            
                FROM SNMPv2-TC            
            wmanIfBsSfId, wmanIfBsQoSProfileIndex, wmanIfBsSfIndex, wmanIfBsClassifierRuleIndex, wmanIfCmnCpsSfId, 
            wmanIfCmnOfdmUiucIndex, VariableMacAddress, WmanIfSfSchedulingType            
                FROM WMAN-IF-ASDRAFT1-MIB;
    
    
        -- 1.3.6.1.4.1.989.1.16.2.4
        asMaxBSDemoMax MODULE-IDENTITY 
            LAST-UPDATED "201007291600Z"		-- July 29, 2010 at 16:00 GMT
            ORGANIZATION 
                "Airspan Networks Inc."
            CONTACT-INFO 
                "Krzysztof Dudzinski
                Airspan Communications Ltd.
                email: kdudzins@airspan.com
                http://www.airspan.com"
            DESCRIPTION 
                "DemoMax private MIB Draft1.
                This MIB is compatible with Draft 1 of standard MIB 
                defined in the document P802.16f-Draft1
                and in the source file WMAN-IF-MIB-9-21.MIB.
                It is intended to be obsoleted by Rev1 
                of the new private MIB at the time when standard MIB 
                will be released and implemented in Airspan equipment."
            REVISION "201007291600Z"		-- July 29, 2010 at 16:00 GMT
            DESCRIPTION 
                "Draft 1BX
                Jan 24, 2011 at 10:30 GMT
                - Added asdmaxSwServerType
                - Added asdmaxSwServerUserName
                - Added asdmaxSwServerPassword
                
                Draft 1BW
                July 29, 2010 at 16:00 GMT
                - Added asdmaxCustomScrtRedundancyEnabled
                
                Draft 1BU
                May 12, 2010 at 11:00 GMT
                - Added asdmaxRfPathStatusChangeTrapEnabled
                
                Draft 1BT
                May 11, 2010 at 19:00 GMT
                - Added object asdmaxCustomActiveStcMode
                
                Draft 1BS
                May 11, 2010 at 14:00 GMT
                - Added object asdmaxCustomActiveRxDiversity
                - Added trap asdmaxRfPathStatusChangeTrap with objects:
                  asdmaxRfPathStatus, asdmaxRfPathStatusBits, asdmaxRfPathStatusInfo
                
                Draft 1BR
                April 23, 2010 at 15:45 GMT
                - Added object asdmaxScrtStatusCarrierSense
                
                Draft 1BQ
                April 23, 2010 at 14:51 GMT
                - Removed object asdmaxCarrierSenseCountStatus from trap asdmaxCarrierSenseV2Trap
                - Added trap control object asdmaxCarrierSenseV2TrapEnabled
                
                Draft 1BP
                April 22, 2010 at 11:44 GMT
                Deprecated objects: 
                  asdmaxCarrierSenseSamplingPeriod,
                  asdmaxCarrierSenseDetectionCountLimit
                New objects:
                  asdmaxCarrierSenseMonitorPeriod (was asdmaxCustomCarrierSenseMonitorPeriod),
                  asdmaxCarrierSenseHighThreshold (was asdmaxCustomCarrierSenseHighThresholdPercentageMuting),
                  asdmaxCarrierSenseStatusV2
                New trap:
                  asdmaxCarrierSenseV2Trap
                
                Draft 1BO
                April 21, 2010 at 05:15 GMT
                Added asdmaxCustomCarrierSenseMonitorPeriod, asdmaxCustomCarrierSenseHighThresholdPercentageMuting to asdmaxCustomConfigTable.
                
                Draft 1BN
                November 14, 2008 at 05:15 GMT
                Added asdmaxCustomGpsloopShift to asdmaxCustomConfigTable.
                
                Draft 1BM
                Old revisions history combined into one revision description:
                -------------------------------------------------------------
                
                April 23, 2008 at 17:53 GMT
                Draft 1BL
                - added columns asdmaxScrtStatusForwardPower and asdmaxScrtStatusReversePower
                  to table asdmaxScrtStatusTable
                February 25, 2008 at 11:15 GMT
                Draft 1BK
                - added objects for encryption licence control:
                  asdmaxCustomActiveEncryptionMode (AsdmaxEncryptionMode textual convention),
                  asdmaxLicenceCertificate, 
                  asdmaxLicenceCertCapabilities, 
                  asdmaxLicenceCertInvalid,
                - added trap asdmaxLicenceCertInvalidTrap
                January 02, 2008 at 11:02 GMT
                Draft 1BJ
                - asdmaxProvSfExtSaid type changed to Integer32 with value range
                December 03, 2007 at 09:41 GMT
                Draft 1BI
                - added asdmaxProvSfExtSaid to AsdmaxProvSfExtEntry
                November 29, 2007 at 11:45 GMT
                AsmaxBooleanSwitch imported from ASMAX-COMMON-MIB.
                September 13, 2007 at 10:19 GMT
                Draft 1BH
                - added asdmaxCustomReuseGroup
                - added asdmaxProvSsQSTagPvid
                - added asdmaxProvSsQSTagUsesSTagPriority
                - added asdmaxProvSsQSTagPriority
                - added asdmaxQBridgeMode
                - added asdmaxQBridgeSTagEthertype
                - added asdmaxQBridgeSTagConfigMode
                - added asdmaxQBridgeSTagPvid
                - added asdmaxQBridgeSTagUseSTagPriority
                - added asdmaxQBridgeSTagPriority
                August 08, 2007 at 14:00 GMT
                Draft 1BG
                - added asdmaxProvSsToVlanMapTagging
                July 19, 2007 at 16:35 GMT
                Draft 1BF
                - added asdmaxProvSsBsidConfigEnabled
                June 20, 2007 at 15:30 GMT
                Draft 1BE
                - Added SS IP address to trap objects for asdmaxSsStatusChangedTrap
                - Added description of asdmaxSsEventTrap
                May 17, 2007 at 18:00 GMT
                Draft 1BD
                - Range defined for asdmaxCustomBridgeEntriesPerBs
                - Added asdmaxBsQDefaultPriority, asdmaxProvSsQDefaultPriority
                - Default for asdmaxProvSsAllowedBSIDXxx
                April 24, 2007 at 11:00 GMT
                Draft 1BC
                - added value vlanModeDot1q to type AsmaxTrafficPortVlanMode
                - changed status back to current for objects asdmaxProvSsPortMode, asdmaxCustomTrafficPortMode
                - range and default changed for asdmaxCustomBridgeTimeout to match the 802.1q standard
                - defined new enumeration values in asdmaxProvVlanDhcpRelayAgentActive for option82 mode text and binary
                - textual conventions replacements to avoid importing symbols from AIRSPAN-Q-BRIDGE-MIB 
                  (incompatibility with AIRSPAN-DEMOMAX-MIB):
                  AsDot1qVlanIdOrNone repalced with imported AsmaxVlanIdOrNone
                  AsDot1qAllowedFrameTypes replaced with defined AsmaxDot1qAllowedFrameTypes
                  AsDot1qPortMode replaced with defined AsdmaxPortMode
                April 13, 2007 at 14:00 GMT
                Draft 1BB
                  First draft for SR6
                - Added classification objects: 
                  asdmaxProvClassifierRuleExtAction,
                  asdmaxProvClassifierRuleExtQTagEnabled,
                  asdmaxProvClassifierRuleExtQTagVlanID,
                  asdmaxProvClassifierRuleExtQTagPriority,
                - Description changed for asdmaxSsStatusIpAddr (new source of this data)
                - Added SS status objects:
                  asdmaxSsStatusHwRevision,
                  asdmaxSsStatusSwVersion,
                  asdmaxSsStatusWiFiApIpAddrType, asdmaxSsStatusWiFiApIpAddress,
                  asdmaxSsStatusWiFiApMacAddress,
                  asdmaxSsStatusEasyVoiceIpAddrType, asdmaxSsStatusEasyVoiceIpAddress,
                  asdmaxSsStatusEasyVoiceMacAddress
                - Added SS prov objects:
                  asdmaxProvSsLanTableMaxSize,
                  asdmaxProvSsAllowedBSID,
                  asdmaxProvSsAllowedBSIDMask
                - Added table asdmaxSsTrapStatusTable
                - Added traps: asdmaxSsStatusChangedTrap, asdmaxSsEventTrap
                - Added QBridge config objects:
                  asdmaxProvSsTable:
                    asdmaxProvSsQPortMode,
                    asdmaxProvSsQPvid,
                    asdmaxProvSsQIngressFilterEnabled,
                    asdmaxProvSsQFrameTypes
                  asdmaxBsQPortTable
                    asdmaxBsQPortIndex,
                    asdmaxBsQPortMode,
                    asdmaxBsQPvid,
                    asdmaxBsQIngressFilterEnabled,
                    asdmaxBsQFrameTypes
                - depracated objects with name changed:
                  asdmaxProvSsPortMode,
                  asdmaxCustomTrafficPortMode
                March 13, 2007 at 19:57 GMT
                Draft 1BA
                - added objects to asdmaxCustomConfigTable
                  asdmaxCustomBridgeTimeout, asdmaxCustomBridgeFlooding
                - changed defaults for asdmaxEarliestStcStartTime and asdmaxCustomMinimumRegToStcGap
                February 21, 2007 at 14:43 GMT
                Draft 1AZ
                - added objects for SS SNR config: 
                  asdmaxProvSsSnrAlphaLow, asdmaxProvSsSnrAlphaHigh, 
                  asdmaxProvSsSnrProtectionMargin, asdmaxProvSsSnrHysteresisMargin, 
                  asdmaxProvSsSnrConfigEnabled
                - range extended for asdmaxCustomUplinkOverbookingRatio, 
                  asdmaxCustomDownlinkOverbookingRatio
                - added default to asdmaxCustomTddDownlinkPercentage
                - obsoleted objects asdmaxBsCfgAutoScEnabled, 
                  asdmaxBsCfgExtAutoScIndexRangeMin, asdmaxBsCfgExtAutoScIndexRangeMax
                - default changed for asdmaxProvVlanDhcpRelayAgentActive
                - range extended for asdmaxOfdmUiucMandatoryExitThreshold and asdmaxOfdmUiucMinEntryThreshold
                February 09, 2007 at 17:02 GMT
                Draft 1AY
                - renames some stc modes in enumeration of asdmaxCustomStcMode
                December 06, 2006 at 10:10 GMT
                Draft 1AX
                - Added asdmaxCmnCpsServiceFlowTable
                November 29, 2006 at 10:59 GMT
                Draft 1AW
                - Added scrtStatusAntennaMismatch bit
                - Range changed for asdmaxCustomMinSubchReqRegionFullTxOpp
                - Default changed for asdmaxCustomContentionPeriodTtg
                - Cor1 fixes to asdmaxCustomUlMidambles
                November 09, 2006 at 16:27 GMT
                Draft 1AV
                Added asmaxBsIfStatsTable.
                October 26, 2006 at 16:37 GMT
                Draft 1AU
                Added new tables asdmaxBsSsModSubChanStatsTable and asdmaxBsSsPacketCounterTable.
                Obsoleted counts from asdmaxSsStatusTable.
                September 22, 2006 at 12:21 GMT
                Draft 1AT
                - added objects 17-19 to table asdmaxBsConfigExtTable
                - added object 79 to table asdmaxCustomConfigTable
                - new values for asdmaxCustomStcMode
                September 11, 2006 at 12:11 GMT
                Draft 1AS
                Added objects 74-78 in asdmaxCustomConfig table.
                June 26, 2006 at 12:43 GMT
                Draft 1AR:
                - New objects in asdmaxCustomConfigTable
                  asdmaxCustomCidQuarantinePeriod
                  asdmaxCustomSasNumBeams
                  asdmaxCustomStcFramesBetweenShifts
                  asdmaxCustomStcMinimumShift
                - Changes to objects in asdmaxCustomConfigTable
                  asdmaxCustomSnrChangeForUlBurstProfile - units and default specified
                - Changed definition of asdmaxSwType to use textual convention imported from AIRSPAN-ASMAX-BS-COMMON-MIB
                - Added asdmaxBsChannelMeasurementTable
                May 05, 2006 at 09:01 GMT
                Draft 1AP
                - Thresholds ranges and defaults changed in asdmaxOfdmSubChannelConfigTable
                - Description changed for asdmaxProvSsSubChannelWidth
                - Added object asdmaxCustomAdvertisedIeeeVersion
                - Changed sysntax of asdmaxScrtStatusRfTransceiverStatus to BITS
                - Changed value list for asdmaxCustomGlobalEncryptionMode
                - Added:
                  - asdmaxBsCfgAutoScEnabled
                  - asdmaxBsCfgAutoScIndexRangeMin
                  - asdmaxBsCfgAutoScIndexRangeMax
                April 24, 2006 at 18:18 GMT
                Draft 1AN
                - obsoleted objects:
                  - asdmaxProvVlanMacForceForwardIpAddressOld
                - new objects:
                  - asdmaxProvVlanMacForceForwardIpAddressType
                  - asdmaxProvVlanMacForceForwardIpAddress
                  - asdmaxCustomGlobalEncryptionMode
                - changed range for:
                  - asdmaxBsCfg2ndMgmtDlQoSProfileIndex
                  - asdmaxBsCfg2ndMgmtUlQoSProfileIndex
                April 11, 2006 at 17:53 GMT
                Draft 1AM
                - Added object asdmaxCustomScrtPowerUpDelay
                - Added table asdmaxScrtConfigTable
                - Added more software types for SwUpgrade table
                April 05, 2006 at 09:15 GMT
                Draft 1AL
                - New objects 
                - asdmaxBsCfgPrimMgmtDlQoSProfileIndex
                - asdmaxBsCfgPrimMgmtUlQoSProfileIndex
                - asdmaxBsCfgBasicMgmtDlQoSProfileIndex
                - asdmaxBsCfgBasicMgmtUlQoSProfileIndex
                - asdmaxCustomCidAllocationNumSss
                - asdmaxCustomPacketCounterUpdatePeriod
                April 03, 2006 at 13:52 GMT
                Draft 1AK
                - Change name of import module
                  from WMAN-IF-MIB to ASMAX-WMAN-IF-MIB
                April 03, 2006 at 12:44 GMT
                Draft 1AJ
                - default values changed for objects
                  asdmaxCustomContentionPeriodTtg through to asdmaxCustomTransmitFrameGap
                - fixed value list for object asdmaxCustomUlMidambles as per standard
                - added object asdmaxSsStatusProductCode
                - BooleanSwitch type replaced with AsmaxBooleanSwitch textual convention (compatible values)
                - Added traps with the related status and control objects:
                  - asdmaxObsaiLinkTrap
                  - asdmaxRfTransceiverFaultTrap
                - Added device table asdmaxScrtStatusTable
                March 21, 2006 at 11:18 GMT
                Draft 1AH
                - new columns in asdmaxProvVlanTable:
                  - asdmaxProvVlanMacForceForwardIpAddress
                  - asdmaxProvVlanDhcpRelayAgentActive
                - new columns in asdmaxProvSsTable:
                  - asdmaxProvSsMeasPollingRequired
                  - asdmaxProvSsMeasPollPeriodMs
                - new columns in asdmaxSsStatusTable:
                  - asdmaxSsStatusUlBasicSduCount
                  - asdmaxSsStatusDlBasicSduCount
                  - asdmaxSsStatusUlPrimarySduCount
                  - asdmaxSsStatusDlPrimarySduCount
                  - asdmaxSsStatusUlSecondarySduCount
                  - asdmaxSsStatusDlSecondarySduCount
                - new columns in asdmaxCustomConfigTable:
                  - asdmaxCustomStrictConformance
                  - asdmaxCustomUlMidambles
                  - asdmaxCustomStcMode
                  - asdmaxCustomTransmitFrameGap
                - objects moved 2 OIDs below in asdmaxCustomConfigTable (safe - previous version not released):
                  - asdmaxCustomTimingSource
                  - asdmaxCustomCarrierSenseThreshold 
                  - asdmaxCustomCarrierSenseBackoffFrames
                - new columns in asdmaxServiceClassExtTable:
                  - asdmaxServiceClassExtFlags
                  - asdmaxServiceClassExtUplinkVlan
                  - asdmaxServiceClassExtUplinkDSField
                - changes in asdmaxTrapStatusTable and int the trap asdmax1ppsFrameLockTrap:
                  - new column asdmax1ppsClockDetected
                  - unified columns access to read-only
                March 10, 2006 at 15:29 GMT
                Draft 1AG
                - fixed objects to trap asdmax1ppsFrameLockTrap
                March 10, 2006 at 13:20 GMT
                Draft 1AF
                - added objects to trap asdmax1ppsFrameLockTrap
                March 09, 2006 at 14:17 GMT
                Draft 1AE
                - Objects moved to CustomConfigTable:
                  CarrierSenseThreshold
                  CarrierSenseBackoffFrames
                March 09, 2006 at 09:47 GMT
                Draft 1AD
                - Added custom config objects:
                  asdmaxCustomInitialBurstTtg
                  asdmaxCustomDlMaxAllocSize
                  asdmaxCustomTimingSource
                - Added table asdmaxPkmConfigTable
                - Added traps:
                  asdmaxCarrierSenseTrap
                  asdmaxCarrierSenseFreqChangeTrap
                  asdmax1ppsFrameLockTrap
                - Added trap assotiated tables:
                  asdmaxTrapControlTable
                  asdmaxTrapStatusTable
                  asdmaxTrapConfigTable
                January 09, 2006 at 17:02 GMT
                Draft 1AC
                - range changed for asdmaxCustomUlMaxAllocSize
                December 14, 2005 at 15:18 GMT
                Draft 1AB
                - Added table asdmaxServiceClassExtTable
                  with one column: asdmaxServiceClassExtPollPeriod
                November 29, 2005 at 12:44 GMT
                Draft 1AA
                -Added columns in AsdmaxProvSsTable:
                 -asdmaxProvSsSubChannelWidth
                -Added columns in asdmaxCustomConfigTable:
                 -asdmaxCustomAchievedTxPower
                 -asdmaxCustomAchievedRxGain
                 -asdmaxCustomContentionPeriodTtg
                -Added table: asdmax
                -Added columns in asdmaxSnmpTrapDestTable:
                 -asdmaxSnmpTrapDestDescription
                October 05, 2005 at 15:50 GMT
                Draft 1Z
                - Added default values to objects in asdmaxCustomConfigTable:
                  with oids 44-49
                - Added object asdmaxSwTypeDescription in asdmaxSwUpgradeTable
                October 03, 2005 at 16:07 GMT
                Draft 1Y
                - added objects to table asdmaxCustomConfigTable:
                  asdmaxCustomCommissioningMode, 
                  asdmaxCustomCommissioningFrameNumber,
                  asdmaxCustomUlMaxAllocSize,
                  asdmaxCustomUlAdjacentAllocGap,
                  asdmaxCustomUseDlPreambles,
                  asdmaxCustomRxGainB,
                  asdmaxCustomTxGainB,
                  asdmaxCustomRxDiversity,
                  asdmaxCustomDlMaxBurstSize
                - objects marked as obsoleted:
                  asdmaxCustomMinPowerToRaise,
                  asdmaxCustomMaxPowerToLower
                - changed enumeration values for objects:
                  asdmaxSwCfgCommand,
                  asdmaxSwStatusCode
                  in the table asdmaxSwUpgradeTable
                - change asdmaxSwStandbyDetails type to DisplayString
                September 09, 2005 at 11:18 GMT
                Draft 1X
                - default change for asdmaxCustomAllocStartTime to 0 (automatic)
                - obsoleted asdmaxCustomMaxBroadcastSize
                - default changed for asdmaxCustomConfigTable to 250
                September 08, 2005 at 19:07 GMT
                Draft 1W
                - range for asdmaxProvClassifierRuleExtPhsSize defined as 0..255
                - range for asdmaxCustomMinSubchReqRegionFullTxOpp changed to 0..65535
                - added objects:
                  asdmaxCustomFastPeriodicRangingExchange (enum)
                  asdmaxCustomDlMapPeriod 
                  asdmaxCustomTargetTxPower
                  asdmaxCustomTargetRxGain
                  asdmaxCustomUplinkRxSetPoint
                  asdmaxCustomUplinkRxSetPointSpread
                  asdmaxCustomUplinkRxInitialRangingSpread
                - name of the object changed 
                  from asdmaxSnmpV1V2TrapDestIpAddr to asdmaxSnmpV1V2TrapDestAddrType
                - objects added:
                  asdmaxSnmpAgentIpAddressType,
                  asdmaxSnmpAgentIpAddress
                July 29, 2005 at 18:13 GMT
                Draft 1U
                - Removed definition of VariableMacAddress - replaced with import
                - Removed unreferenced imported objects
                - Revision history put in order
                July 07, 2005 at 12:20 GMT
                Draft 1T
                - Added VariableMacAddress textual convention
                  to address issues with net-snmp indexing by MacAddress
                - Applied VariableMacAddress to:
                  asdmaxProvSsMacAddress
                  asdmaxSsActionsMacAddress
                  wmanIfBsSsMacAddress (in status table) replaced with asdmaxProvSsMacAddress
                July 07, 2005 at 10:57 GMT
                Draft 1S
                - Added objects:
                  asdmaxSsProvFakeRegistration
                  asdmaxBsCfgUncheckedBcastSfid
                  asdmaxBsCfgUncheckedBcastServiceClassIndex
                  asdmaxCustomGainRf
                  asdmaxCustomGainPc8520  
                  asdmaxCustomAllocStartTime
                  asdmaxCustomMaxBroadcastSize
                  asdmaxCustomInitialBurstTailGap
                June 22, 2005 at 15:41 GMT
                Draft 1R
                - Fixed description of 
                  asdmaxCustomMaxPowerToLower
                - Added asdmaxProvSsFixedUplinkBurstProfile
                  and asdmaxProvSsFixedDownlinkBurstProfile
                - Added more details to history change for draft 1K
                June 06, 2005 at 10:05 GMT
                Draft 1Q
                - Added arbitrary Tx nd Rx gains
                  to asdmaxCustomConfigTable
                - Moved trap destination config to separate 
                  table asdmaxSnmpTrapDestTable
                  with possibility of 8 rows.
                May 20, 2005 at 12:26 GMT
                Draft 1P
                - Fixed MAX-ACCESS of asdmaxSsStatusIpAddress
                May 16, 2005 at 10:44 GMT
                Draft 1N
                - Fixed Row Status inasdmaxSnmpTestTable
                May 13, 2005 at 15:55 GMT
                Draft 1M
                - asdmaxProvClassifierRuleExtPhsSize - default removed
                - asdmaxProvVlanIdForSs -> not-accessible
                - asdmaxSwType
                - AsmaxPollGroupId - display hint defined
                - AsmaxPollGroupIdOrNone - display hint defined
                May 06, 2005 at 18:23 GMT
                Draft 1L
                of DemoMax MIB Draft1.
                - Added units to asdmaxCustomDownlinkRadioEfficiency.
                - Added asdmaxSnmpTestTable
                May 04, 2005 at 08:34 GMT
                Draft 1K
                of DemoMax MIB Draft1.
                Moved 6 objects to differnet tables:
                - MgmtVlanId from asdmaxCustomConfigTable to asdmaxSnmpAgentConfigTable
                - MgmtOnTrafficPort from asmaxCustomConfigTable to asdmaxSnmpAgentConfigTable
                - MinRangingTosPerSec from asdmxOfdmConfigTable to asdmaxCustomConfigTable
                - MinSubchReqRegionFullTxOpp from asdmxOfdmConfigTable to asdmaxCustomConfigTable
                - ChannelBandwidth from asdmxOfdmConfigTable to asdmaxCustomConfigTable
                - ResetBs from asdmaxSnmpAgentConfigTable to asdmaxSnmpAgentActionsTable
                - Removed row-status form read-write tables.
                May 02, 2005 at 17:31 GMT
                Draft 1J
                of DemoMax MIB Draft1.
                Added vlan fro mmt traffic, overbooking ratios,
                traffic efficiency objects.
                April 19, 2005 at 11:39 GMT
                Draft 1H
                of DemoMax MIB Draft1.
                Added swUpgrade table and radio
                channel bandwidth configuration.
                April 18, 2005 at 12:16 GMT
                Draft 1G
                of DemoMax MIB Draft1.
                Added object asdmaxCustomAllowInsecureSs.
                April 05, 2005 at 16:37 GMT
                Draft 1F
                of DemoMax MIB Draft1.
                Removed default value for asdmaxProvSsDsxAllowed,
                corrected compliance module name.
                April 04, 2005 at 16:54 GMT
                Draft 1E
                of DemoMax MIB Draft1.
                Added Service Class Index for Vlan table.
                April 01, 2005 at 16:49 GMT
                Draft 1D
                of DemoMax MIB Draft1.
                Added some objects to Custom BS config table, Mcast table and Ofdm Config table.
                Removed asdmaxCustomSubchNumOfdmSymbols.
                March 08, 2005 at 12:18 GMT
                Draft 1C
                of DemoMax MIB Draft1.
                Added LinkUpdate config, BS traffic port mode and Licenced flag.
                Moved BS custom config table to Cps branch.
                March 01, 2005 at 18:25 GMT
                Draft 1B
                of DemoMax MIB Draft1.
                Added SnmpActions and TransmitterEnabled objects.
                Updated to import objects from released AIRSPAN-PRODUCTS-MIB
                March 01, 2005 at 11:22 GMT
                Draft 1A
                of DemoMax MIB Draft1"
            REVISION "201111091206Z"		-- November 09, 2011 at 12:06 GMT
            DESCRIPTION 
                "Draft 1BY:
                - Added rfTransceiverWarning to asdmaxRfTransceiverFaultStatus"
            ::= { asMaxBS 4 }

        
    
--
-- Textual conventions
--
    
        AsmaxExtendedVlanId ::= TEXTUAL-CONVENTION
            DISPLAY-HINT 
                "d"
            STATUS current
            DESCRIPTION 
                "Defines VLAN ID for use in Airspan specifc 
                implementation of VLAN bridge.
                Range 1.4094 is reserved for standard (802.1Q) VLAN IDs.
                Value of 4096 is used for untagged traffic."
            REFERENCE 
                "RFC2674, IEEE802.1Q, IEEE801.3"
            SYNTAX INTEGER (1..4094 | 4096)

        AsmaxPollGroupIdOrNone ::= TEXTUAL-CONVENTION
            DISPLAY-HINT 
                "d"
            STATUS current
            DESCRIPTION 
                "The polling group IDs are subject to custom implementation 
                This ID should be unique withing the BS domain.
                Teh value of 0 means none."
            SYNTAX INTEGER (0 | 1..253)

        AsmaxTrafficPortVlanMode ::= TEXTUAL-CONVENTION
            STATUS current
            DESCRIPTION 
                "Defines how the Ethernet frames are encoded on local traffic 
                Ethernet port.
                vlanModeRaw - Vlan tags are not checked
                vlanModeCheckAndTag - Vlan tags are checked (invalid discarded) 
                  and frames are tagged
                vlanModeCheckAndUntag - Vlan tags are checked and frames are not tagged 
                  (tags are stripped).
                vlanModeDot1q - The behaviour of the bridge for this port is defined 
                  by additional configuration objects based on 802.1q standard"
            SYNTAX INTEGER
                {
                vlanModeRaw(0),
                vlanModeCheckAndTag(1),
                vlanModeCheckAndUntag(2),
                vlanModeDot1q(3)
                }

        AsmaxWmanIfBsIdType ::= TEXTUAL-CONVENTION
            STATUS current
            DESCRIPTION 
                "Defines the encoding of BSID. The BSID is a 6 byte number
                and follows the encoding rules of MacAddress textual
                convention, i.e. as if it were transmitted
                least-significant bit first. The value should be displayed
                with 2 parts clearly separated by a colon e.g:
                001DFF:00003A. The most significant part is representing
                the Operator ID.
                This object is defined in Draft6 of WMAN-IF-MIB."
            SYNTAX OCTET STRING (SIZE (6))

        AsdmaxQPortMode ::= TEXTUAL-CONVENTION
            STATUS current
            DESCRIPTION 
                "Configures standard (portModeVlan) behaviour or non standard 
                behaviour of the port (portModeRaw).
                In mode portModeRaw all port configuration and port Vlan list 
                are ignored. The traffic is allow to flow in and out unfiltered 
                and without changes to tagging."
            SYNTAX INTEGER
                {
                portModeRaw(1),
                portModeVlan(2)
                }

        AsmaxExtendedVlanIdOrNone ::= TEXTUAL-CONVENTION
            STATUS current
            DESCRIPTION 
                "Defines VLAN ID for use in Airspan specifc 
                implementation of VLAN bridge.
                Range 1.4094 is reserved for standard (802.1Q) VLAN IDs.
                Value of 4096 is used for untagged traffic.
                Value of 0 means none."
            SYNTAX INTEGER (0 | 1..4094 | 4096)

        AsdmaxQAllowedFrameTypes ::= TEXTUAL-CONVENTION
            STATUS current
            DESCRIPTION 
                "When this is admitOnlyVlanTagged, the device will discard 
                untagged frames or Priority-Tagged frames received on this port.
                When admitAll(1), untagged frames or Priority-Tagged frames 
                received on the port will be accepted and assigned to 
                a VID based on the PVID of for this port.
                When admitOnlyUntagged(3), is set the device will discard 
                all VLAN tagged frames."
            SYNTAX INTEGER
                {
                admitAll(1),
                admitOnlyVlanTagged(2),
                admitOnlyUntagged(3)
                }

        AsmaxConnectionId ::= TEXTUAL-CONVENTION
            DISPLAY-HINT 
                "d"
            STATUS current
            DESCRIPTION 
                "Connection Identifier defined temporarly in absence of 
                the textual convention defined in later drafts of the standard MIB."
            SYNTAX INTEGER (0..65535)

        AsdmaxEncryptionMode ::= TEXTUAL-CONVENTION
            STATUS current
            DESCRIPTION 
                "Defines the 'maximum' encryption mode that the
                BS will permit for an SS.The no XOR IV mode
                selects the non-standard DES mode used by early Rosedale software."
            SYNTAX INTEGER
                {
                glEncryptNone(0),
                glEncryptAuthOnly(1),
                glEncryptDesNoXorIv3Des(2),
                glEncryptDes3Des(3),
                glEncryptDesRsa(4),
                glEncryptAes(5)
                }

        AsmaxPollGroupId ::= TEXTUAL-CONVENTION
            DISPLAY-HINT 
                "d"
            STATUS current
            DESCRIPTION 
                "The polling group IDs are subject to custom implementation 
                This ID should be unique withing the BS domain."
            SYNTAX INTEGER (1..253)

        AsmaxDSFieldValue ::= TEXTUAL-CONVENTION
            DISPLAY-HINT 
                "d"
            STATUS current
            DESCRIPTION 
                "Differential service field value used in the TOS field of the IP header."
            SYNTAX INTEGER (0..63)

        AsmaxWmanIfChannelNumber ::= TEXTUAL-CONVENTION
            STATUS current
            DESCRIPTION 
                "Physical channel number.
                This object is defined in Draft6 of WMAN-IF-MIB."
            SYNTAX INTEGER (0..199)

        AsmaxWmanIfCidType ::= TEXTUAL-CONVENTION
            STATUS current
            DESCRIPTION 
                "Type of CID.
                This object is defined in Draft6 of WMAN-IF-MIB."
            SYNTAX INTEGER (0..65535)

        AsmaxWmanIfSfState ::= TEXTUAL-CONVENTION
            STATUS current
            DESCRIPTION 
                "Defines the state of a service flow.
                This object is defined in Draft6 of WMAN-IF-MIB."
            SYNTAX INTEGER
                {
                authorized(1),
                admitted(2),
                active(3)
                }

        AsmaxWmanIfCsSpecification ::= TEXTUAL-CONVENTION
            STATUS current
            DESCRIPTION 
                "Defines the types of convergence sublayer.
                This object is defined in Draft6 of WMAN-IF-MIB."
            SYNTAX INTEGER
                {
                noCs(0),
                packetIpV4(1),
                packetIpV6(2),
                packet802dot3Ethernet(3),
                packet802dot1QVlan(4),
                packetIpV4Over802dot3(5),
                packetIpV6Over802dot3(6),
                packetIpV4Over802dot1Q(7),
                packetIpV6Over802dot1Q(8),
                atm(9)
                }

        AsmaxAction ::= TEXTUAL-CONVENTION
            STATUS current
            DESCRIPTION 
                "Universal encoding for Asmax Actions.
                The object of this type should be implemented as follows:
                - When value set to actionExecute value, 
                  instructs the agent to execute the action
                - When set to value different than actionExecute it
                  should be ignored
                - When read it should return actionIgnore"
            SYNTAX INTEGER
                {
                actionIgnore(0),
                actionApply(1)
                }

    
--
-- Node definitions
--
    
        -- 1.3.6.1.4.1.989.1.16.2.4.1
        asdmaxMibObjects OBJECT IDENTIFIER ::= { asMaxBSDemoMax 1 }

        
        -- 1.3.6.1.4.1.989.1.16.2.4.1.1
        asdmaxPacketCs OBJECT IDENTIFIER ::= { asdmaxMibObjects 1 }

        
        -- 1.3.6.1.4.1.989.1.16.2.4.1.1.1
        asdmaxProvSfExtTable OBJECT-TYPE
            SYNTAX SEQUENCE OF AsdmaxProvSfExtEntry
            MAX-ACCESS not-accessible
            STATUS current
            DESCRIPTION
                "This table is defined as a temporary holder Convergence Sublayer
                type configuration object specified in later drafts 
                of the standard MIB."
            ::= { asdmaxPacketCs 1 }

        
        -- 1.3.6.1.4.1.989.1.16.2.4.1.1.1.1
        asdmaxProvSfExtEntry OBJECT-TYPE
            SYNTAX AsdmaxProvSfExtEntry
            MAX-ACCESS not-accessible
            STATUS current
            DESCRIPTION
                "Description."
            INDEX { wmanIfBsSfId }
            ::= { asdmaxProvSfExtTable 1 }

        
        AsdmaxProvSfExtEntry ::=
            SEQUENCE { 
                asdmaxProvSfExtCsType
                    INTEGER,
                asdmaxProvSfExtRowStatus
                    RowStatus,
                asdmaxProvSfExtSaid
                    Integer32
             }

        -- 1.3.6.1.4.1.989.1.16.2.4.1.1.1.1.1
        asdmaxProvSfExtCsType OBJECT-TYPE
            SYNTAX INTEGER
                {
                packet802dot3Ethernet(3),
                packet802dot1QVlan(4),
                packetIpV4Over802dot3(5),
                packetIpV6Over802dot3(6),
                packetIpV4Over802dot1Q(7),
                packetIpV6Over802dot1Q(8)
                }
            MAX-ACCESS read-create
            STATUS current
            DESCRIPTION
                "Description."
            ::= { asdmaxProvSfExtEntry 1 }

        
        -- 1.3.6.1.4.1.989.1.16.2.4.1.1.1.1.2
        asdmaxProvSfExtRowStatus OBJECT-TYPE
            SYNTAX RowStatus
            MAX-ACCESS read-create
            STATUS current
            DESCRIPTION
                "Description.
                "
            ::= { asdmaxProvSfExtEntry 2 }

        
        -- 1.3.6.1.4.1.989.1.16.2.4.1.1.1.1.3
        asdmaxProvSfExtSaid OBJECT-TYPE
            SYNTAX Integer32 (0..65535)
            MAX-ACCESS read-create
            STATUS current
            DESCRIPTION
                "Specifies the security association ID for this service flow.
                A value of 0 indicates that the primary SA should be used.
                This column is used for certification purposes only;
                not accessed by Netspan"
            DEFVAL { 0 }
            ::= { asdmaxProvSfExtEntry 3 }

        
        -- 1.3.6.1.4.1.989.1.16.2.4.1.1.2
        asdmaxProvVlanTable OBJECT-TYPE
            SYNTAX SEQUENCE OF AsdmaxProvVlanEntry
            MAX-ACCESS not-accessible
            STATUS current
            DESCRIPTION
                "This table defines Virtual LANs as per IEEE802.3Q.
                The VLAN defined in this table can be used by SSs 
                as defined in asdmaxProvSsToVlanMapTable."
            ::= { asdmaxPacketCs 2 }

        
        -- 1.3.6.1.4.1.989.1.16.2.4.1.1.2.1
        asdmaxProvVlanEntry OBJECT-TYPE
            SYNTAX AsdmaxProvVlanEntry
            MAX-ACCESS not-accessible
            STATUS current
            DESCRIPTION
                "Description."
            INDEX { asdmaxProvVlanId }
            ::= { asdmaxProvVlanTable 1 }

        
        AsdmaxProvVlanEntry ::=
            SEQUENCE { 
                asdmaxProvVlanId
                    AsmaxExtendedVlanId,
                asdmaxProvVlanFlags
                    BITS,
                asdmaxProvVlanUntaggedBcastSfid
                    Unsigned32,
                asdmaxProvVlanTaggedBcastSfid
                    Unsigned32,
                asdmaxProvVlanBcastServiceClassIndex
                    INTEGER,
                asdmaxProvVlanRowStatus
                    RowStatus,
                asdmaxProvVlanMacForceForwardIpAddressOld
                    IpAddress,
                asdmaxProvVlanDhcpRelayAgentActive
                    INTEGER,
                asdmaxProvVlanMacForceForwardIpAddressType
                    InetAddressType,
                asdmaxProvVlanMacForceForwardIpAddress
                    InetAddress
             }

        -- 1.3.6.1.4.1.989.1.16.2.4.1.1.2.1.1
        asdmaxProvVlanId OBJECT-TYPE
            SYNTAX AsmaxExtendedVlanId
            MAX-ACCESS not-accessible
            STATUS current
            DESCRIPTION
                "This object defines VLAN Identifier as specified in IEEE802.3Q.
                A special value of 4096 (AirspanExtendedVlanId textual convention)
                is used to define untagged traffic (no VLAN)."
            ::= { asdmaxProvVlanEntry 1 }

        
        -- 1.3.6.1.4.1.989.1.16.2.4.1.1.2.1.2
        asdmaxProvVlanFlags OBJECT-TYPE
            SYNTAX BITS
                {
                provVlanFlagsSingleUser(0),
                provVlanFlagsMacForceForwarding(1)
                }
            MAX-ACCESS read-create
            STATUS current
            DESCRIPTION
                "This object defines the custom behaviour of VLAN bridge applied to
                the specific VLAN as follows:
                provVlanFlagsSingleUser - When this flag is set, the broadcast 
                  traffic tagged with the referred asdmaxProvVlanId is separated
                  between SSs using the same VlanId.
                provVlanFlagsMacForceForwarding - When this flag is set all uplink
                  traffic from the SSs is forwarded to a specified router; see
                  asdmaxProvVlanMacForceForwardIpAddress."
            ::= { asdmaxProvVlanEntry 2 }

        
        -- 1.3.6.1.4.1.989.1.16.2.4.1.1.2.1.3
        asdmaxProvVlanUntaggedBcastSfid OBJECT-TYPE
            SYNTAX Unsigned32 (1..2147483647)
            MAX-ACCESS read-create
            STATUS current
            DESCRIPTION
                "SFID of the service flow provisioned for the untagged 
                broadcast VLAN traffic. The parameters of this service 
                flow are defined by asdmaxProvVlanBcastServiceClassIndex object."
            ::= { asdmaxProvVlanEntry 3 }

        
        -- 1.3.6.1.4.1.989.1.16.2.4.1.1.2.1.4
        asdmaxProvVlanTaggedBcastSfid OBJECT-TYPE
            SYNTAX Unsigned32 (1..2147483647)
            MAX-ACCESS read-create
            STATUS current
            DESCRIPTION
                "SFID of the service flow provisioned for the tagged 
                broadcast VLAN traffic. The parameters of this service 
                flow are defined by asdmaxProvVlanBcastServiceClassIndex object."
            ::= { asdmaxProvVlanEntry 4 }

        
        -- 1.3.6.1.4.1.989.1.16.2.4.1.1.2.1.5
        asdmaxProvVlanBcastServiceClassIndex OBJECT-TYPE
            SYNTAX INTEGER (1..1000)
            MAX-ACCESS read-create
            STATUS current
            DESCRIPTION
                "Defines Service Class to use for Broadcast Service Flows 
                of both tagged and untagged traffic."
            ::= { asdmaxProvVlanEntry 5 }

        
        -- 1.3.6.1.4.1.989.1.16.2.4.1.1.2.1.6
        asdmaxProvVlanRowStatus OBJECT-TYPE
            SYNTAX RowStatus
            MAX-ACCESS read-create
            STATUS current
            DESCRIPTION
                "Description."
            ::= { asdmaxProvVlanEntry 6 }

        
        -- 1.3.6.1.4.1.989.1.16.2.4.1.1.2.1.7
        asdmaxProvVlanMacForceForwardIpAddressOld OBJECT-TYPE
            SYNTAX IpAddress
            MAX-ACCESS read-create
            STATUS obsolete
            DESCRIPTION
                "This specifies the IP address of the router that uplink traffic is
                forwarded to when MAC forced forwarding is selected. Obsolete"
            ::= { asdmaxProvVlanEntry 7 }

        
        -- 1.3.6.1.4.1.989.1.16.2.4.1.1.2.1.8
        asdmaxProvVlanDhcpRelayAgentActive OBJECT-TYPE
            SYNTAX INTEGER
                {
                dhcpAgentModeOff(0),
                dhcpAgentModeOption82Text(1),
                dhcpAgentModeOption82Binary(2)
                }
            MAX-ACCESS read-create
            STATUS current
            DESCRIPTION
                "Enables the addition of RelayAgentInd sub options in server bound
                DHCP messages, tagging with cctID as SS MAC, remID as BSMac"
            DEFVAL { dhcpAgentOff }
            ::= { asdmaxProvVlanEntry 8 }

        
        -- 1.3.6.1.4.1.989.1.16.2.4.1.1.2.1.9
        asdmaxProvVlanMacForceForwardIpAddressType OBJECT-TYPE
            SYNTAX InetAddressType
            MAX-ACCESS read-create
            STATUS current
            DESCRIPTION
                "This specifies the type of IP address of the router that uplink 
                traffic is forwarded to when MAC forced forwarding is selected. "
            DEFVAL { ipv4 }
            ::= { asdmaxProvVlanEntry 9 }

        
        -- 1.3.6.1.4.1.989.1.16.2.4.1.1.2.1.10
        asdmaxProvVlanMacForceForwardIpAddress OBJECT-TYPE
            SYNTAX InetAddress
            MAX-ACCESS read-create
            STATUS current
            DESCRIPTION
                "This specifies the IP address of the router that uplink traffic is
                forwarded to when MAC forced forwarding is selected. "
            DEFVAL { "" }
            ::= { asdmaxProvVlanEntry 10 }

        
        -- 1.3.6.1.4.1.989.1.16.2.4.1.1.3
        asdmaxProvSsToVlanMapTable OBJECT-TYPE
            SYNTAX SEQUENCE OF AsdmaxProvSsToVlanMapEntry
            MAX-ACCESS not-accessible
            STATUS current
            DESCRIPTION
                "This table provides the provisioning of the mapping 
                between VLANs and SSs. There can be multiple VLANs per SS
                as well as multiple SSs servings the same VLAN.
                The SSs are identified by MAC Address as they are provisioned
                in the asdmaxSsConfigTable."
            ::= { asdmaxPacketCs 3 }

        
        -- 1.3.6.1.4.1.989.1.16.2.4.1.1.3.1
        asdmaxProvSsToVlanMapEntry OBJECT-TYPE
            SYNTAX AsdmaxProvSsToVlanMapEntry
            MAX-ACCESS not-accessible
            STATUS current
            DESCRIPTION
                "Description."
            INDEX { asdmaxProvSsMacAddress, asdmaxProvVlanIdForSs }
            ::= { asdmaxProvSsToVlanMapTable 1 }

        
        AsdmaxProvSsToVlanMapEntry ::=
            SEQUENCE { 
                asdmaxProvVlanIdForSs
                    AsmaxExtendedVlanId,
                asdmaxProvSsToVlanMapRowStatus
                    RowStatus,
                asdmaxProvSsToVlanMapTagging
                    INTEGER
             }

        -- 1.3.6.1.4.1.989.1.16.2.4.1.1.3.1.1
        asdmaxProvVlanIdForSs OBJECT-TYPE
            SYNTAX AsmaxExtendedVlanId
            MAX-ACCESS not-accessible
            STATUS current
            DESCRIPTION
                "Description."
            ::= { asdmaxProvSsToVlanMapEntry 1 }

        
        -- 1.3.6.1.4.1.989.1.16.2.4.1.1.3.1.2
        asdmaxProvSsToVlanMapRowStatus OBJECT-TYPE
            SYNTAX RowStatus
            MAX-ACCESS read-create
            STATUS current
            DESCRIPTION
                "Description."
            ::= { asdmaxProvSsToVlanMapEntry 2 }

        
        -- 1.3.6.1.4.1.989.1.16.2.4.1.1.3.1.3
        asdmaxProvSsToVlanMapTagging OBJECT-TYPE
            SYNTAX INTEGER
                {
                tagged(1),
                untagged(2)
                }
            MAX-ACCESS read-create
            STATUS current
            DESCRIPTION
                "Tagging behaviour for the given VLAN on a given port in egress."
            DEFVAL { tagged }
            ::= { asdmaxProvSsToVlanMapEntry 3 }

        
        -- 1.3.6.1.4.1.989.1.16.2.4.1.1.4
        asdmaxProvClassifierRuleExtTable OBJECT-TYPE
            SYNTAX SEQUENCE OF AsdmaxProvClassifierRuleExtEntry
            MAX-ACCESS not-accessible
            STATUS current
            DESCRIPTION
                "This table is defined as a temporary holder for PHS 
                configuration objects specified in later drafts 
                of the standard MIB.
                The value 0 of PHS Size instructs BS not to use 
                the PHS config in the given classifer."
            ::= { asdmaxPacketCs 4 }

        
        -- 1.3.6.1.4.1.989.1.16.2.4.1.1.4.1
        asdmaxProvClassifierRuleExtEntry OBJECT-TYPE
            SYNTAX AsdmaxProvClassifierRuleExtEntry
            MAX-ACCESS not-accessible
            STATUS current
            DESCRIPTION
                "Description."
            INDEX { wmanIfBsSfIndex, wmanIfBsClassifierRuleIndex }
            ::= { asdmaxProvClassifierRuleExtTable 1 }

        
        AsdmaxProvClassifierRuleExtEntry ::=
            SEQUENCE { 
                asdmaxProvClassifierRuleExtPhsSize
                    INTEGER,
                asdmaxProvClassifierRuleExtPhsMask
                    OCTET STRING,
                asdmaxProvClassifierRuleExtPhsVerify
                    INTEGER,
                asdmaxProvClassifierRuleExtRowStatus
                    RowStatus,
                asdmaxProvClassifierRuleExtAction
                    BITS,
                asdmaxProvClassifierRuleExtQTagEnabled
                    AsmaxBooleanSwitch,
                asdmaxProvClassifierRuleExtQTagVlanID
                    AsmaxVlanIdOrNone,
                asdmaxProvClassifierRuleExtQTagPriority
                    INTEGER
             }

        -- 1.3.6.1.4.1.989.1.16.2.4.1.1.4.1.2
        asdmaxProvClassifierRuleExtPhsSize OBJECT-TYPE
            SYNTAX INTEGER (0..255)
            UNITS "byte"
            MAX-ACCESS read-create
            STATUS current
            DESCRIPTION
                "This object is used to configure the PHS rule for this
                classifer. The value of this field - PHSS is the total
                number of bytes in the header to be suppressed and then
                restored in a service flow that uses PHS. 
                If the value of this field is 0 bytes then PHS is disabled 
                for this classifer. 
                Draft D4 of corrigendum set the TLV 
                for this object for size 1 octet."
            REFERENCE
                "Section 11.13.19.3.7.4 in IEEE 802.16-2004"
            DEFVAL { 0 }
            ::= { asdmaxProvClassifierRuleExtEntry 2 }

        
        -- 1.3.6.1.4.1.989.1.16.2.4.1.1.4.1.3
        asdmaxProvClassifierRuleExtPhsMask OBJECT-TYPE
            SYNTAX OCTET STRING
            MAX-ACCESS read-create
            STATUS current
            DESCRIPTION
                "This object is used to configure the PHS rule for this
                classifer. It is encoded as follows:
                bit 0:
                  0 = do not suppress first byte of the suppression field
                  1 = suppress first byte of the suppression field
                bit 1:
                  0 = do not suppress second byte of the suppression field
                  1 = suppress second byte of the suppression field
                bit x:
                  0 = do not suppress (x+1) byte of the suppression field
                  1 = suppress (x+1) byte of the suppression field
                where the length of the octet string is ceiling
                (wmanIfBsClassifierRulePhsSize/8). BS should use this value
                to create a new PHS rule index (PHSI) and field (PHSF) as
                defined in the standard. If flag phsMask in
                wmanIfBSClassifierRuleBitMap is set to 0 and flag phsSize
                in wmanIfBsClassifierRuleBitMap is set to 0, then BS can
                still create PHS rules using its own custom mask (i.e. the
                rule is not configured by NMS)."
            REFERENCE
                "Section 11.13.19.3.7.3 in IEEE 802.16-2004"
            ::= { asdmaxProvClassifierRuleExtEntry 3 }

        
        -- 1.3.6.1.4.1.989.1.16.2.4.1.1.4.1.4
        asdmaxProvClassifierRuleExtPhsVerify OBJECT-TYPE
            SYNTAX INTEGER
                {
                phsVerifyEnable(0),
                phsVerifyDisable(1)
                }
            MAX-ACCESS read-create
            STATUS current
            DESCRIPTION
                "The value of this field indicates to the sending entity    
                whether or not the packet header contents are to be
                verified prior to performing suppression."
            REFERENCE
                "Section 11.13.19.3.7.3 in IEEE 802.16-2004"
            ::= { asdmaxProvClassifierRuleExtEntry 4 }

        
        -- 1.3.6.1.4.1.989.1.16.2.4.1.1.4.1.5
        asdmaxProvClassifierRuleExtRowStatus OBJECT-TYPE
            SYNTAX RowStatus
            MAX-ACCESS read-create
            STATUS current
            DESCRIPTION
                "Description."
            ::= { asdmaxProvClassifierRuleExtEntry 5 }

        
        -- 1.3.6.1.4.1.989.1.16.2.4.1.1.4.1.6
        asdmaxProvClassifierRuleExtAction OBJECT-TYPE
            SYNTAX BITS { classifierRuleActionDiscard(0) }
            MAX-ACCESS read-create
            STATUS current
            DESCRIPTION
                "An action to be taken when the packet matches the rule. The first bit defines
                general forward/discard action. The default value is empty (i.e. all bits clear), 
                which means forward. The classification rule actions were initially defined 
                in the amendment 802.16e. This object is defined in absence of relevant object
                in the standard WMAN-IF-MIB."
            REFERENCE
                "IEEE802.16e-2005 standard, subcluse 11.13.19.3.4.17"
            DEFVAL { {  } }
            ::= { asdmaxProvClassifierRuleExtEntry 6 }

        
        -- 1.3.6.1.4.1.989.1.16.2.4.1.1.4.1.7
        asdmaxProvClassifierRuleExtQTagEnabled OBJECT-TYPE
            SYNTAX AsmaxBooleanSwitch
            MAX-ACCESS read-create
            STATUS current
            DESCRIPTION
                "When enabled each packet matching this classifier rule shall have
                a VLAN tag inserted with VLAN ID defined by asMaxBsSocClsfRuleExtQTagVlanID
                and VLAN priority defined by asMaxBsSocClsfRuleExtQTagPriority."
            ::= { asdmaxProvClassifierRuleExtEntry 7 }

        
        -- 1.3.6.1.4.1.989.1.16.2.4.1.1.4.1.8
        asdmaxProvClassifierRuleExtQTagVlanID OBJECT-TYPE
            SYNTAX AsmaxVlanIdOrNone
            MAX-ACCESS read-create
            STATUS current
            DESCRIPTION
                "VLAN ID of the VLAN tag inserted in the packet when packet matches 
                the classification rule and the tagging is enabled by the object 
                asMaxBsSocClsfRuleExtQTagEnabled. A value of 0 should be used when 
                the tagging is disabled."
            DEFVAL { 0 }
            ::= { asdmaxProvClassifierRuleExtEntry 8 }

        
        -- 1.3.6.1.4.1.989.1.16.2.4.1.1.4.1.9
        asdmaxProvClassifierRuleExtQTagPriority OBJECT-TYPE
            SYNTAX INTEGER (0..7)
            MAX-ACCESS read-create
            STATUS current
            DESCRIPTION
                "VLAN priority (as defined in 802.1Q) of the VLAN tag inserted in the packet when packet matches 
                the classification rule and the tagging is enabled by the object 
                asMaxBsSocClsfRuleExtQTagEnabled."
            DEFVAL { 0 }
            ::= { asdmaxProvClassifierRuleExtEntry 9 }

        
        -- 1.3.6.1.4.1.989.1.16.2.4.1.2
        asdmaxCps OBJECT IDENTIFIER ::= { asdmaxMibObjects 2 }

        
        -- 1.3.6.1.4.1.989.1.16.2.4.1.2.1
        asdmaxProvSsTable OBJECT-TYPE
            SYNTAX SEQUENCE OF AsdmaxProvSsEntry
            MAX-ACCESS not-accessible
            STATUS current
            DESCRIPTION
                "Description."
            ::= { asdmaxCps 1 }

        
        -- 1.3.6.1.4.1.989.1.16.2.4.1.2.1.1
        asdmaxProvSsEntry OBJECT-TYPE
            SYNTAX AsdmaxProvSsEntry
            MAX-ACCESS not-accessible
            STATUS current
            DESCRIPTION
                "Description."
            INDEX { asdmaxProvSsMacAddress }
            ::= { asdmaxProvSsTable 1 }

        
        AsdmaxProvSsEntry ::=
            SEQUENCE { 
                asdmaxProvSsMacAddress
                    VariableMacAddress,
                asdmaxProvSsDsxAllowed
                    BITS,
                asdmaxProvSsMcastPollGroupId
                    AsmaxPollGroupIdOrNone,
                asdmaxProvSsPortMode
                    AsmaxTrafficPortVlanMode,
                asdmaxProvSsFixedUplinkBurstProfile
                    INTEGER,
                asdmaxProvSsFixedDownlinkBurstProfile
                    INTEGER,
                asdmaxProvSsFakeRegistration
                    INTEGER,
                asdmaxProvSsRowStatus
                    RowStatus,
                asdmaxProvSsSubChannelWidth
                    INTEGER,
                asdmaxProvSsMeasPollingRequired
                    AsmaxBooleanSwitch,
                asdmaxProvSsMeasPollPeriodMs
                    INTEGER,
                asdmaxProvSsSnrAlphaLow
                    INTEGER,
                asdmaxProvSsSnrAlphaHigh
                    INTEGER,
                asdmaxProvSsSnrProtectionMargin
                    INTEGER,
                asdmaxProvSsSnrHysteresisMargin
                    INTEGER,
                asdmaxProvSsSnrConfigEnabled
                    AsmaxBooleanSwitch,
                asdmaxProvSsLanTableMaxSize
                    INTEGER,
                asdmaxProvSsAllowedBSID
                    AsmaxWmanIfBsIdType,
                asdmaxProvSsAllowedBSIDMask
                    AsmaxWmanIfBsIdType,
                asdmaxProvSsQPortMode
                    AsdmaxQPortMode,
                asdmaxProvSsQPvid
                    AsmaxExtendedVlanIdOrNone,
                asdmaxProvSsQIngressFilterEnabled
                    AsmaxBooleanSwitch,
                asdmaxProvSsQFrameTypes
                    AsdmaxQAllowedFrameTypes,
                asdmaxProvSsQDefaultPriority
                    Integer32,
                asdmaxProvSsBsidConfigEnabled
                    AsmaxBooleanSwitch,
                asdmaxProvSsQSTagPvid
                    AsmaxVlanIdOrNone,
                asdmaxProvSsQSTagUseSTagPriority
                    AsmaxBooleanSwitch,
                asdmaxProvSsQSTagPriority
                    Integer32
             }

        -- 1.3.6.1.4.1.989.1.16.2.4.1.2.1.1.1
        asdmaxProvSsMacAddress OBJECT-TYPE
            SYNTAX VariableMacAddress
            MAX-ACCESS not-accessible
            STATUS current
            DESCRIPTION
                "Description."
            ::= { asdmaxProvSsEntry 1 }

        
        -- 1.3.6.1.4.1.989.1.16.2.4.1.2.1.1.2
        asdmaxProvSsDsxAllowed OBJECT-TYPE
            SYNTAX BITS
                {
                ssConfigDsaAllowed(0),
                ssConfigDscAllowed(1),
                ssConfigDsdAllowed(2)
                }
            MAX-ACCESS read-create
            STATUS current
            DESCRIPTION
                "Binary coded configuration flags indicating what DSX operations
                are allowed to be requested by SS. No remote DSX operation 
                is allowed by default."
            ::= { asdmaxProvSsEntry 2 }

        
        -- 1.3.6.1.4.1.989.1.16.2.4.1.2.1.1.3
        asdmaxProvSsMcastPollGroupId OBJECT-TYPE
            SYNTAX AsmaxPollGroupIdOrNone
            MAX-ACCESS read-create
            STATUS current
            DESCRIPTION
                "The identifier of Multicast Polling Group.
                A value of 0 means none.
                A value > 0 identifies a Multicast Polling Group 
                as provisioned in asdmaxProvMcastPollGroupTable.
                "
            REFERENCE
                "Table 345 in 802.16-2004."
            ::= { asdmaxProvSsEntry 3 }

        
        -- 1.3.6.1.4.1.989.1.16.2.4.1.2.1.1.4
        asdmaxProvSsPortMode OBJECT-TYPE
            SYNTAX AsmaxTrafficPortVlanMode
            MAX-ACCESS read-create
            STATUS current
            DESCRIPTION
                "Defines how the Ethernet frames are encoded 
                on local traffic Ethernet port.
                When configured with value vlanModeDot1q alternative objects 
                asdmaxProvSsQXxx define the behaviour of this bridge port."
            DEFVAL { vlanModeRaw }
            ::= { asdmaxProvSsEntry 4 }

        
        -- 1.3.6.1.4.1.989.1.16.2.4.1.2.1.1.5
        asdmaxProvSsFixedUplinkBurstProfile OBJECT-TYPE
            SYNTAX INTEGER (0 | 5..12)
            MAX-ACCESS read-create
            STATUS current
            DESCRIPTION
                "Defines UIUC of the fixed uplink burst profile for the SS.
                If set to zero (0) the SS uplink modulation 
                is established dynamically.
                "
            ::= { asdmaxProvSsEntry 5 }

        
        -- 1.3.6.1.4.1.989.1.16.2.4.1.2.1.1.6
        asdmaxProvSsFixedDownlinkBurstProfile OBJECT-TYPE
            SYNTAX INTEGER (0 | 1..11)
            MAX-ACCESS read-create
            STATUS current
            DESCRIPTION
                "Defines DIUC of the fixed downlink burst profile for the SS.
                If set to zero (0) the SS downlink modulation 
                is established dynamically.
                "
            ::= { asdmaxProvSsEntry 6 }

        
        -- 1.3.6.1.4.1.989.1.16.2.4.1.2.1.1.7
        asdmaxProvSsFakeRegistration OBJECT-TYPE
            SYNTAX INTEGER (0..1)
            MAX-ACCESS read-create
            STATUS current
            DESCRIPTION
                "Set to 1 to fake the registration of this SS. 
                0 for normal operation.
                This is persistent debug config."
            ::= { asdmaxProvSsEntry 7 }

        
        -- 1.3.6.1.4.1.989.1.16.2.4.1.2.1.1.8
        asdmaxProvSsRowStatus OBJECT-TYPE
            SYNTAX RowStatus
            MAX-ACCESS read-create
            STATUS current
            DESCRIPTION
                "Description."
            ::= { asdmaxProvSsEntry 8 }

        
        -- 1.3.6.1.4.1.989.1.16.2.4.1.2.1.1.9
        asdmaxProvSsSubChannelWidth OBJECT-TYPE
            SYNTAX INTEGER
                {
                subChannelWidthAuto(0),
                subChannelWidthSixteenth(1),
                subChannelWidthEighth(2),
                subChannelWidthQuarter(4),
                subChannelWidthHalf(8),
                subChannelWidthFull(16)
                }
            MAX-ACCESS read-create
            STATUS current
            DESCRIPTION
                "Indicates the minimum bandwidth that will be granted to the SS 
                for uplink data.  Must be 16, 8, 4, 2, or 1, where 
                16 = full bandwidth and 1 = sixteenth of bandwidth.
                Values subChannelWidthAuto and subChannelWidthSixteenth result 
                in the same BS behaviour for this SS i.e. in both cases 
                the minimum bandwidth is the sixteenth."
            ::= { asdmaxProvSsEntry 9 }

        
        -- 1.3.6.1.4.1.989.1.16.2.4.1.2.1.1.10
        asdmaxProvSsMeasPollingRequired OBJECT-TYPE
            SYNTAX AsmaxBooleanSwitch
            MAX-ACCESS read-create
            STATUS current
            DESCRIPTION
                "1 Enables polling for SS measurements 0 disables it"
            ::= { asdmaxProvSsEntry 10 }

        
        -- 1.3.6.1.4.1.989.1.16.2.4.1.2.1.1.11
        asdmaxProvSsMeasPollPeriodMs OBJECT-TYPE
            SYNTAX INTEGER (0..65535)
            UNITS "ms"
            MAX-ACCESS read-create
            STATUS current
            DESCRIPTION
                "Measurement poll period for BS polls of SS measured data in Ms"
            DEFVAL { 10000 }
            ::= { asdmaxProvSsEntry 11 }

        
        -- 1.3.6.1.4.1.989.1.16.2.4.1.2.1.1.12
        asdmaxProvSsSnrAlphaLow OBJECT-TYPE
            SYNTAX INTEGER (1..1023)
            MAX-ACCESS read-create
            STATUS current
            DESCRIPTION
                "SNR averaging coefficient in case SNR is decreased."
            DEFVAL { 1 }
            ::= { asdmaxProvSsEntry 12 }

        
        -- 1.3.6.1.4.1.989.1.16.2.4.1.2.1.1.13
        asdmaxProvSsSnrAlphaHigh OBJECT-TYPE
            SYNTAX INTEGER (1..1023)
            MAX-ACCESS read-create
            STATUS current
            DESCRIPTION
                "SNR averaging coefficient in case SNR is increased"
            DEFVAL { 32 }
            ::= { asdmaxProvSsEntry 13 }

        
        -- 1.3.6.1.4.1.989.1.16.2.4.1.2.1.1.14
        asdmaxProvSsSnrProtectionMargin OBJECT-TYPE
            SYNTAX INTEGER (0..15)
            UNITS "dB"
            MAX-ACCESS read-create
            STATUS current
            DESCRIPTION
                "SNR margin over AWGN nominal value"
            DEFVAL { 4 }
            ::= { asdmaxProvSsEntry 14 }

        
        -- 1.3.6.1.4.1.989.1.16.2.4.1.2.1.1.15
        asdmaxProvSsSnrHysteresisMargin OBJECT-TYPE
            SYNTAX INTEGER (0..15)
            UNITS "dB"
            MAX-ACCESS read-create
            STATUS current
            DESCRIPTION
                "SNR margin over burst profile mandatory exit threshold"
            DEFVAL { 3 }
            ::= { asdmaxProvSsEntry 15 }

        
        -- 1.3.6.1.4.1.989.1.16.2.4.1.2.1.1.16
        asdmaxProvSsSnrConfigEnabled OBJECT-TYPE
            SYNTAX AsmaxBooleanSwitch
            MAX-ACCESS read-create
            STATUS current
            DESCRIPTION
                "Enables/disables SS SNR configuration of Alpha, protection and hysteresis."
            DEFVAL { booleanFalse }
            ::= { asdmaxProvSsEntry 16 }

        
        -- 1.3.6.1.4.1.989.1.16.2.4.1.2.1.1.17
        asdmaxProvSsLanTableMaxSize OBJECT-TYPE
            SYNTAX INTEGER (1..128)
            MAX-ACCESS read-create
            STATUS current
            DESCRIPTION
                "Maximum size of the CPE LAN MAC address table. This object restricts number 
                of host machines connected to the SS LAN.
                The object is defined in TLV 1.2 of CNFG-REQ."
            REFERENCE
                "ASMAX Proprietary TLV r9.doc"
            DEFVAL { 128 }
            ::= { asdmaxProvSsEntry 17 }

        
        -- 1.3.6.1.4.1.989.1.16.2.4.1.2.1.1.18
        asdmaxProvSsAllowedBSID OBJECT-TYPE
            SYNTAX AsmaxWmanIfBsIdType
            MAX-ACCESS read-create
            STATUS current
            DESCRIPTION
                "Test value used to check if SS is allowed to registered on a given 
                BS identified with BSID.
                To allow registration BS BSID binary anded with the value of asMaxBsSocSsCfgAllowedBSIDMask
                should match the value of asMaxBsSocSsCfgAllowedBSID.
                The object is defined in TLV 1.4 of CNFG-REQ."
            REFERENCE
                "ASMAX Proprietary TLV r9.doc"
            DEFVAL { '000000000000'h }
            ::= { asdmaxProvSsEntry 18 }

        
        -- 1.3.6.1.4.1.989.1.16.2.4.1.2.1.1.19
        asdmaxProvSsAllowedBSIDMask OBJECT-TYPE
            SYNTAX AsmaxWmanIfBsIdType
            MAX-ACCESS read-create
            STATUS current
            DESCRIPTION
                "Mask value used to check if SS is allowed to registered on a given 
                BS identified with BSID.
                To allow registration BS BSID binary anded with the value of asMaxBsSocSsCfgAllowedBSIDMask
                should match the value of asMaxBsSocSsCfgAllowedBSID.
                The object is defined in TLV 1.4 of CNFG-REQ."
            REFERENCE
                "ASMAX Proprietary TLV r9.doc"
            DEFVAL { '000000000000'h }
            ::= { asdmaxProvSsEntry 19 }

        
        -- 1.3.6.1.4.1.989.1.16.2.4.1.2.1.1.20
        asdmaxProvSsQPortMode OBJECT-TYPE
            SYNTAX AsdmaxQPortMode
            MAX-ACCESS read-create
            STATUS current
            DESCRIPTION
                "Configures standard (portModeVlan) behaviour or non standard 
                behaviour of the port (portModeRaw).
                In mode portModeRaw all port configuration and port Vlan list 
                are ignored. The traffic is allow to flow in and out unfiltered 
                and without changes to tagging."
            DEFVAL { portModeRaw }
            ::= { asdmaxProvSsEntry 20 }

        
        -- 1.3.6.1.4.1.989.1.16.2.4.1.2.1.1.21
        asdmaxProvSsQPvid OBJECT-TYPE
            SYNTAX AsmaxExtendedVlanIdOrNone
            MAX-ACCESS read-create
            STATUS current
            DESCRIPTION
                "Extended port VID defined as follows:
                -values 1..4094 are used for standard PVID behaviour
                -values 0 (none) is used when only tagged frames are processed
                -value 4096 is used for backwards compatibility with older bridge implementations."
            DEFVAL { 0 }
            ::= { asdmaxProvSsEntry 21 }

        
        -- 1.3.6.1.4.1.989.1.16.2.4.1.2.1.1.22
        asdmaxProvSsQIngressFilterEnabled OBJECT-TYPE
            SYNTAX AsmaxBooleanSwitch
            MAX-ACCESS read-create
            STATUS current
            DESCRIPTION
                "When disabled the frames arriving from the port (ingress) 
                are accepted regardles on the tag.
                When enabled the tags are checekd against port vlan list."
            DEFVAL { booleanTrue }
            ::= { asdmaxProvSsEntry 22 }

        
        -- 1.3.6.1.4.1.989.1.16.2.4.1.2.1.1.23
        asdmaxProvSsQFrameTypes OBJECT-TYPE
            SYNTAX AsdmaxQAllowedFrameTypes
            MAX-ACCESS read-create
            STATUS current
            DESCRIPTION
                "Defines in general what frame types are allowed on ingress:
                all, tagged only or untagged only.
                For tagged only Pvid should be set to 0."
            DEFVAL { admitAll }
            ::= { asdmaxProvSsEntry 23 }

        
        -- 1.3.6.1.4.1.989.1.16.2.4.1.2.1.1.24
        asdmaxProvSsQDefaultPriority OBJECT-TYPE
            SYNTAX Integer32 (0..7)
            MAX-ACCESS read-create
            STATUS current
            DESCRIPTION
                "Priority applied to VLAN tag for untagged framed 
                where PVID is used."
            DEFVAL { 0 }
            ::= { asdmaxProvSsEntry 24 }

        
        -- 1.3.6.1.4.1.989.1.16.2.4.1.2.1.1.25
        asdmaxProvSsBsidConfigEnabled OBJECT-TYPE
            SYNTAX AsmaxBooleanSwitch
            MAX-ACCESS read-create
            STATUS current
            DESCRIPTION
                "When set to booleanFalse Base Station ignores the configuration 
                of allowed BSID and BSID Mask.
                When set to booleanTrue Base Station sends the configuration 
                of BSID and BSID Mask to SS."
            DEFVAL { booleanFalse }
            ::= { asdmaxProvSsEntry 25 }

        
        -- 1.3.6.1.4.1.989.1.16.2.4.1.2.1.1.26
        asdmaxProvSsQSTagPvid OBJECT-TYPE
            SYNTAX AsmaxVlanIdOrNone
            MAX-ACCESS read-create
            STATUS current
            DESCRIPTION
                "This object is defined using 802.1q and 802.ad terminology.
                The object is used when asmaxQBridgeSTagConfigMode is set to sTagUseSsConfig.
                Object defines VLAN ID applied to outer tag (S-TAG) of the frame when 
                the bridge works in Providers mode (as defined in asmaxQBridgeMode). 
                All the packets received from the C-Bridge of this port
                (tagged or untagged with C-TAG i.e Q-tag) are tagged with this VID."
            DEFVAL { 1 }
            ::= { asdmaxProvSsEntry 26 }

        
        -- 1.3.6.1.4.1.989.1.16.2.4.1.2.1.1.27
        asdmaxProvSsQSTagUseSTagPriority OBJECT-TYPE
            SYNTAX AsmaxBooleanSwitch
            MAX-ACCESS read-create
            STATUS current
            DESCRIPTION
                "When false (default) the user priority for STag is copied from 
                the inner tag (CTag).
                When true the user priority for STag is taken from 
                the object asdmaxProvSsQSTagPriority."
            DEFVAL { booleanFalse }
            ::= { asdmaxProvSsEntry 27 }

        
        -- 1.3.6.1.4.1.989.1.16.2.4.1.2.1.1.28
        asdmaxProvSsQSTagPriority OBJECT-TYPE
            SYNTAX Integer32 (0..7)
            MAX-ACCESS read-create
            STATUS current
            DESCRIPTION
                "This object is defined using 802.1q and 802.ad terminology.
                It is only used when instructed by asdmaxProvSsQSTagDefaultPriority.
                Object defines VLAN user priority applied to outer tag (S-TAG) of the frame 
                when the bridge works in Providers mode (as defined in asmaxQBridgeMode). 
                All the packets received from the C-Bridge of this port
                (tagged or untagged with C-TAG i.e Q-tag) are tagged with this VLAN user priority."
            DEFVAL { 0 }
            ::= { asdmaxProvSsEntry 28 }

        
        -- 1.3.6.1.4.1.989.1.16.2.4.1.2.2
        asdmaxSsActionsTable OBJECT-TYPE
            SYNTAX SEQUENCE OF AsdmaxSsActionsEntry
            MAX-ACCESS not-accessible
            STATUS current
            DESCRIPTION
                "This table contains actions of two types:
                - Those planned to be included in wmanIfBsSsActionsTable, 
                  which is to be part of the standard MIB
                - Custom actions defined for the purpose of private MIB only.
                The agent does not need to implement the storage for objects
                of this table as they are dynamic requests for an action.
                Due to the nature of the row of this table, defining independent
                actions the agent should expect the requests with partial sets
                for the rows of this table."
            ::= { asdmaxCps 2 }

        
        -- 1.3.6.1.4.1.989.1.16.2.4.1.2.2.1
        asdmaxSsActionsEntry OBJECT-TYPE
            SYNTAX AsdmaxSsActionsEntry
            MAX-ACCESS not-accessible
            STATUS current
            DESCRIPTION
                "Description."
            INDEX { asdmaxSsActionsMacAddress }
            ::= { asdmaxSsActionsTable 1 }

        
        AsdmaxSsActionsEntry ::=
            SEQUENCE { 
                asdmaxSsActionsMacAddress
                    VariableMacAddress,
                asdmaxSsActionsResetSs
                    INTEGER,
                asdmaxSsActionsDeReRegSs
                    INTEGER,
                asdmaxSsActionsDeReRegSsCode
                    INTEGER,
                asdmaxSsActionsDeleteSsConfig
                    INTEGER,
                asdmaxSsActionsRowStatus
                    RowStatus
             }

        -- 1.3.6.1.4.1.989.1.16.2.4.1.2.2.1.1
        asdmaxSsActionsMacAddress OBJECT-TYPE
            SYNTAX VariableMacAddress
            MAX-ACCESS not-accessible
            STATUS current
            DESCRIPTION
                "MAC Address of SS to apply the action to. 
                Depending on the action this MAC Address 
                will refer either to provisioned SS or registered SS."
            ::= { asdmaxSsActionsEntry 1 }

        
        -- 1.3.6.1.4.1.989.1.16.2.4.1.2.2.1.2
        asdmaxSsActionsResetSs OBJECT-TYPE
            SYNTAX INTEGER
                {
                actionsResetSsNoAction(0),
                actionsResetSs(1)
                }
            MAX-ACCESS read-create
            STATUS current
            DESCRIPTION
                "This object should be implemented as follows:
                - When set to actionsResetSs value, instructs BS 
                  to send RES-CMD to SS.
                  The RES-CMD message shall be transmitted by the BS on an
                  SS Basic CID to force the SS to reset itself,
                  reinitialize its MAC, and repeat initial system access.
                - When set to value different than actionsResetSs
                  it should be ignored
                - When read it should return actionsResetSsNoAction
                "
            REFERENCE
                "Section 6.3.2.3.22 in IEEE 802.16-2004"
            ::= { asdmaxSsActionsEntry 2 }

        
        -- 1.3.6.1.4.1.989.1.16.2.4.1.2.2.1.3
        asdmaxSsActionsDeReRegSs OBJECT-TYPE
            SYNTAX INTEGER
                {
                actionsDeReRegSsNoAction(0),
                actionsDeReRegSs(1)
                }
            MAX-ACCESS read-create
            STATUS current
            DESCRIPTION
                "This object should be implemented as follows:
                - When set to actionsDeReRegSs value, instructs BS to
                  send DREG-CMD to SS with specified action code.
                  The DREG-CMD message shall be transmitted by the BS on an
                  SS Basic CID to force the SS to change its access state.
                  Upon receiving a DREG-CMD, the SS shall take the action
                  indicated by the action code defined 
                  by wmanIfBsSsActionsDeReRegSsCode.
                - When set to value different than actionsDeReRegSs it
                  should be ignored
                - When read it should return actionsDeReRegSsNoAction
                "
            REFERENCE
                "Section 6.3.2.3.26 in IEEE 802.16-2004"
            ::= { asdmaxSsActionsEntry 3 }

        
        -- 1.3.6.1.4.1.989.1.16.2.4.1.2.2.1.4
        asdmaxSsActionsDeReRegSsCode OBJECT-TYPE
            SYNTAX INTEGER
                {
                actionsDeReRegSsCodeChangeChan(0),
                actionsDeReRegSsCodeNoTransmit(1),
                actionsDeReRegSsCodeLtdTransmit(2),
                actionsDeReRegSsCodeResume(3)
                }
            MAX-ACCESS read-create
            STATUS current
            DESCRIPTION
                "This object defined the action code for
                wmanIfBsSsActionsDeReRegSs action. 
                The codes are defined as follows:
                actionsDeReRegSsCodeChangeChan - SS shall leave the
                  current channel and attempt to access another channel.
                actionsDeReRegSsCodeNoTransmit - SS shall listen to the
                  current channel but shall not transmit until an
                  RES-CMD message or DREG_CMD with an Action Code that
                  allows transmission is received.
                actionsDeReRegSsCodeLtdTransmit - SS shall listen to the
                  current channel but only transmit on the Basic,
                  Primary Management and 2nd Management Connections.
                actionsDeReRegSsCodeResume - SS shall return to normal
                  operation and may transmit on any of its active connections."
            REFERENCE
                "Section 6.3.2.3.26, table 55 in IEEE 802.16-2004"
            ::= { asdmaxSsActionsEntry 4 }

        
        -- 1.3.6.1.4.1.989.1.16.2.4.1.2.2.1.5
        asdmaxSsActionsDeleteSsConfig OBJECT-TYPE
            SYNTAX INTEGER
                {
                actionsDeleteSsConfigNoAction(0),
                actionsDeleteSsConfig(1)
                }
            MAX-ACCESS read-create
            STATUS current
            DESCRIPTION
                "This object should be implemented as follows:
                - When set to actionsDeleteSsConfig value, instructs BS 
                  to delete all rows in all tables indexed directly 
                  or indirectly fo this SS, which where created for 
                  this SS by NMS provisioning/configuration action 
                  (read-create access). This includes Service Flows, 
                  Classifier Rules, SS Configuration and mapping to VLANs.
                  The relevant objects should be deleted from volotile 
                  as well as from persistant storage.
                - When set to value different than actionsResetSs
                  it should be ignored
                - When read it should return actionsResetSsNoAction
                "
            ::= { asdmaxSsActionsEntry 5 }

        
        -- 1.3.6.1.4.1.989.1.16.2.4.1.2.2.1.6
        asdmaxSsActionsRowStatus OBJECT-TYPE
            SYNTAX RowStatus
            MAX-ACCESS read-create
            STATUS current
            DESCRIPTION
                "Description."
            ::= { asdmaxSsActionsEntry 6 }

        
        -- 1.3.6.1.4.1.989.1.16.2.4.1.2.3
        asdmaxSsStatusTable OBJECT-TYPE
            SYNTAX SEQUENCE OF AsdmaxSsStatusEntry
            MAX-ACCESS not-accessible
            STATUS current
            DESCRIPTION
                "This table contains SS related status information not present
                in standard MIB. There is one row for every SS registered with BS.
                This table effectively extends the table wmanIfBsRegisteredSsTable.
                The objects in this table are mainly for debugging purposes."
            ::= { asdmaxCps 3 }

        
        -- 1.3.6.1.4.1.989.1.16.2.4.1.2.3.1
        asdmaxSsStatusEntry OBJECT-TYPE
            SYNTAX AsdmaxSsStatusEntry
            MAX-ACCESS not-accessible
            STATUS current
            DESCRIPTION
                "Description."
            INDEX { asdmaxProvSsMacAddress }
            ::= { asdmaxSsStatusTable 1 }

        
        AsdmaxSsStatusEntry ::=
            SEQUENCE { 
                asdmaxSsStatusSsId
                    Unsigned32,
                asdmaxSsStatusMcastPollCid
                    AsmaxConnectionId,
                asdmaxSsStatusNextMcastPollCid
                    AsmaxConnectionId,
                asdmaxSsStatusIpAddrType
                    InetAddressType,
                asdmaxSsStatusIpAddr
                    InetAddress,
                asdmaxSsStatusUlBasicSduCount
                    Counter64,
                asdmaxSsStatusDlBasicSduCount
                    Counter64,
                asdmaxSsStatusUlPrimarySduCount
                    Counter64,
                asdmaxSsStatusDlPrimarySduCount
                    Counter64,
                asdmaxSsStatusUlSecondarySduCount
                    Counter64,
                asdmaxSsStatusDlSecondarySduCount
                    Counter64,
                asdmaxSsStatusProductCode
                    OCTET STRING,
                asdmaxSsStatusHwRevision
                    INTEGER,
                asdmaxSsStatusSwVersion
                    DisplayString,
                asdmaxSsStatusWiFiApIpAddrType
                    InetAddressType,
                asdmaxSsStatusWiFiApIpAddress
                    InetAddress,
                asdmaxSsStatusWiFiApMacAddress
                    MacAddress,
                asdmaxSsStatusEasyVoiceIpAddrType
                    InetAddressType,
                asdmaxSsStatusEasyVoiceIpAddress
                    InetAddress,
                asdmaxSsStatusEasyVoiceMacAddress
                    MacAddress
             }

        -- 1.3.6.1.4.1.989.1.16.2.4.1.2.3.1.1
        asdmaxSsStatusSsId OBJECT-TYPE
            SYNTAX Unsigned32 (1..2147483647)
            MAX-ACCESS read-only
            STATUS current
            DESCRIPTION
                "This object is used as an index in multiple tables reporting
                SS related data in the standard MIB (e.g. wmanIfBsSsIdIndex 
                in the table wmanIfBsRegisteredSsTable)."
            ::= { asdmaxSsStatusEntry 1 }

        
        -- 1.3.6.1.4.1.989.1.16.2.4.1.2.3.1.2
        asdmaxSsStatusMcastPollCid OBJECT-TYPE
            SYNTAX AsmaxConnectionId
            MAX-ACCESS read-only
            STATUS current
            DESCRIPTION
                "Multicast polling CID."
            ::= { asdmaxSsStatusEntry 2 }

        
        -- 1.3.6.1.4.1.989.1.16.2.4.1.2.3.1.3
        asdmaxSsStatusNextMcastPollCid OBJECT-TYPE
            SYNTAX AsmaxConnectionId
            MAX-ACCESS read-only
            STATUS current
            DESCRIPTION
                "Next Multicast polling CID."
            ::= { asdmaxSsStatusEntry 3 }

        
        -- 1.3.6.1.4.1.989.1.16.2.4.1.2.3.1.4
        asdmaxSsStatusIpAddrType OBJECT-TYPE
            SYNTAX InetAddressType
            MAX-ACCESS read-only
            STATUS current
            DESCRIPTION
                "The type of address reported in the asdmaxSsStatusIpAddr object."
            ::= { asdmaxSsStatusEntry 4 }

        
        -- 1.3.6.1.4.1.989.1.16.2.4.1.2.3.1.5
        asdmaxSsStatusIpAddr OBJECT-TYPE
            SYNTAX InetAddress
            MAX-ACCESS read-only
            STATUS current
            DESCRIPTION
                "IP address of the SS obtained dynamically during DHCP/TFTP phase
                of NetEntry. BS can obtain this address using two methods: DHCP snooping/proxing
                or from reports coming from SS. Both methods should update this field.
                Both empty string and 0xFFFFFFFF will be treated as if address is unknown."
            DEFVAL { ''b }
            ::= { asdmaxSsStatusEntry 5 }

        
        -- 1.3.6.1.4.1.989.1.16.2.4.1.2.3.1.6
        asdmaxSsStatusUlBasicSduCount OBJECT-TYPE
            SYNTAX Counter64
            MAX-ACCESS read-only
            STATUS obsolete
            DESCRIPTION
                "Packet count on SS basic management uplink (to BS) connection."
            ::= { asdmaxSsStatusEntry 6 }

        
        -- 1.3.6.1.4.1.989.1.16.2.4.1.2.3.1.7
        asdmaxSsStatusDlBasicSduCount OBJECT-TYPE
            SYNTAX Counter64
            MAX-ACCESS read-only
            STATUS obsolete
            DESCRIPTION
                "Packet count on SS basic management downlink (from BS) connection."
            ::= { asdmaxSsStatusEntry 7 }

        
        -- 1.3.6.1.4.1.989.1.16.2.4.1.2.3.1.8
        asdmaxSsStatusUlPrimarySduCount OBJECT-TYPE
            SYNTAX Counter64
            MAX-ACCESS read-only
            STATUS obsolete
            DESCRIPTION
                "Packet count on SS primary management uplink (to BS) connection."
            ::= { asdmaxSsStatusEntry 8 }

        
        -- 1.3.6.1.4.1.989.1.16.2.4.1.2.3.1.9
        asdmaxSsStatusDlPrimarySduCount OBJECT-TYPE
            SYNTAX Counter64
            MAX-ACCESS read-only
            STATUS obsolete
            DESCRIPTION
                "Packet count on SS primary management downlink (from BS) connection."
            ::= { asdmaxSsStatusEntry 9 }

        
        -- 1.3.6.1.4.1.989.1.16.2.4.1.2.3.1.10
        asdmaxSsStatusUlSecondarySduCount OBJECT-TYPE
            SYNTAX Counter64
            MAX-ACCESS read-only
            STATUS obsolete
            DESCRIPTION
                "Packet count on SS secondary management uplink (to BS) connection."
            ::= { asdmaxSsStatusEntry 10 }

        
        -- 1.3.6.1.4.1.989.1.16.2.4.1.2.3.1.11
        asdmaxSsStatusDlSecondarySduCount OBJECT-TYPE
            SYNTAX Counter64
            MAX-ACCESS read-only
            STATUS obsolete
            DESCRIPTION
                "Packet count on SS secondary management downlink (from BS) connection."
            ::= { asdmaxSsStatusEntry 11 }

        
        -- 1.3.6.1.4.1.989.1.16.2.4.1.2.3.1.12
        asdmaxSsStatusProductCode OBJECT-TYPE
            SYNTAX OCTET STRING (SIZE (0..64))
            MAX-ACCESS read-only
            STATUS current
            DESCRIPTION
                "String based code identifying SS product e.g. EASYST"
            ::= { asdmaxSsStatusEntry 12 }

        
        -- 1.3.6.1.4.1.989.1.16.2.4.1.2.3.1.13
        asdmaxSsStatusHwRevision OBJECT-TYPE
            SYNTAX INTEGER (0..65535)
            MAX-ACCESS read-only
            STATUS current
            DESCRIPTION
                "SS Hardware revision reported using custom TLV type 2 of REG-RSP.
                "
            REFERENCE
                "ASMAX Proprietary TLV r9.doc"
            DEFVAL { 0 }
            ::= { asdmaxSsStatusEntry 13 }

        
        -- 1.3.6.1.4.1.989.1.16.2.4.1.2.3.1.14
        asdmaxSsStatusSwVersion OBJECT-TYPE
            SYNTAX DisplayString
            MAX-ACCESS read-only
            STATUS current
            DESCRIPTION
                "SW version SS is currently running, reported using custom TLV type 3 of REG-RSP.
                BS shall send a trap asMaxBsSocReportedSsStatusChanged on each change 
                in the value of this object."
            REFERENCE
                "ASMAX Proprietary TLV r9.doc"
            ::= { asdmaxSsStatusEntry 14 }

        
        -- 1.3.6.1.4.1.989.1.16.2.4.1.2.3.1.15
        asdmaxSsStatusWiFiApIpAddrType OBJECT-TYPE
            SYNTAX InetAddressType
            MAX-ACCESS read-only
            STATUS current
            DESCRIPTION
                "The type of InetAddress used by asMaxBsSocSsWiFiApIpAddress. Typically it refers to IPv4
                but is defined in fully flexible way to satisfy SNMP MIB guidelines."
            DEFVAL { ipv4 }
            ::= { asdmaxSsStatusEntry 15 }

        
        -- 1.3.6.1.4.1.989.1.16.2.4.1.2.3.1.16
        asdmaxSsStatusWiFiApIpAddress OBJECT-TYPE
            SYNTAX InetAddress
            MAX-ACCESS read-only
            STATUS current
            DESCRIPTION
                "IP address of SS integrated WiFi AP, 
                reported using custom TLV type 2.5 of CNFG-RSP.
                When address hasn't been reported yet the object shall read 0xFFFFFFFF.
                BS shall send a trap asMaxBsSocReportedSsStatusChanged on each change 
                in the value of this object."
            REFERENCE
                "ASMAX Proprietary TLV r9.doc"
            DEFVAL { 'FFFFFFFF'h }
            ::= { asdmaxSsStatusEntry 16 }

        
        -- 1.3.6.1.4.1.989.1.16.2.4.1.2.3.1.17
        asdmaxSsStatusWiFiApMacAddress OBJECT-TYPE
            SYNTAX MacAddress
            MAX-ACCESS read-only
            STATUS current
            DESCRIPTION
                "MAC Address of SS integrated WiFi AP, 
                reported using custom TLV type 2.7 of CNFG-RSP.
                When address hasn't been reported yet the object shall read FF:FF:FF:FF:FF:FF.
                BS shall send a trap asMaxBsSocReportedSsStatusChanged on each change 
                in the value of this object."
            REFERENCE
                "ASMAX Proprietary TLV r9.doc"
            ::= { asdmaxSsStatusEntry 17 }

        
        -- 1.3.6.1.4.1.989.1.16.2.4.1.2.3.1.18
        asdmaxSsStatusEasyVoiceIpAddrType OBJECT-TYPE
            SYNTAX InetAddressType
            MAX-ACCESS read-only
            STATUS current
            DESCRIPTION
                "The type of InetAddress used by asMaxBsSocSsEasyVoiceIpAddress. Typically it refers to IPv4
                but is defined in fully flexible way to satisfy SNMP MIB guidelines."
            DEFVAL { ipv4 }
            ::= { asdmaxSsStatusEntry 18 }

        
        -- 1.3.6.1.4.1.989.1.16.2.4.1.2.3.1.19
        asdmaxSsStatusEasyVoiceIpAddress OBJECT-TYPE
            SYNTAX InetAddress
            MAX-ACCESS read-only
            STATUS current
            DESCRIPTION
                "IP address of SS integrated EasyVoice product (residential VoIP gateway), 
                reported using custom TLV type 2.6 of CNFG-RSP.
                When address hasn't been reported yet the object shall read 0xFFFFFFFF.
                BS shall send a trap asMaxBsSocReportedSsStatusChanged on each change 
                in the value of this object."
            REFERENCE
                "ASMAX Proprietary TLV r9.doc"
            DEFVAL { 'FFFFFFFF'h }
            ::= { asdmaxSsStatusEntry 19 }

        
        -- 1.3.6.1.4.1.989.1.16.2.4.1.2.3.1.20
        asdmaxSsStatusEasyVoiceMacAddress OBJECT-TYPE
            SYNTAX MacAddress
            MAX-ACCESS read-only
            STATUS current
            DESCRIPTION
                "MAC Address of SS integrated EasyVoice product (residential VoIP gateway), 
                reported using custom TLV type 2.8 of CNFG-RSP.
                When address hasn't been reported yet the object shall read FF:FF:FF:FF:FF:FF.
                BS shall send a trap asMaxBsSocReportedSsStatusChanged on each change 
                in the value of this object."
            REFERENCE
                "ASMAX Proprietary TLV r9.doc"
            ::= { asdmaxSsStatusEntry 20 }

        
        -- 1.3.6.1.4.1.989.1.16.2.4.1.2.4
        asdmaxBsConfigExtTable OBJECT-TYPE
            SYNTAX SEQUENCE OF AsdmaxBsConfigExtEntry
            MAX-ACCESS not-accessible
            STATUS current
            DESCRIPTION
                "This tables contains general configuration objects of the BS 'Sector'.
                The table contains all the objects not present in Draft1 
                of the standard MIB but present or planned for next drafts
                (table wmanIfBsConfigExtTable).
                
                The BS is responsible for creating a row in this table for each 
                interface index of type propBWAp2Mp.
                The NMS can modify values in this table."
            ::= { asdmaxCps 4 }

        
        -- 1.3.6.1.4.1.989.1.16.2.4.1.2.4.1
        asdmaxBsConfigExtEntry OBJECT-TYPE
            SYNTAX AsdmaxBsConfigExtEntry
            MAX-ACCESS not-accessible
            STATUS current
            DESCRIPTION
                "Description."
            INDEX { ifIndex }
            ::= { asdmaxBsConfigExtTable 1 }

        
        AsdmaxBsConfigExtEntry ::=
            SEQUENCE { 
                asdmaxBsCfg2ndMgmtDlQoSProfileIndex
                    INTEGER,
                asdmaxBsCfg2ndMgmtUlQoSProfileIndex
                    INTEGER,
                asdmaxBsCfgAutoSfidEnabled
                    INTEGER,
                asdmaxBsCfgAutoSfidRangeMin
                    Unsigned32,
                asdmaxBsCfgAutoSfidRangeMax
                    Unsigned32,
                asdmaxBsCfgResetSector
                    INTEGER,
                asdmaxBsCfgUncheckedBcastSfid
                    Unsigned32,
                asdmaxBsCfgUncheckedBcastServiceClassIndex
                    INTEGER,
                asdmaxBsCfgAllowSsAddressedTraffic
                    INTEGER,
                asdmaxBsCfgPrimMgmtDlQoSProfileIndex
                    INTEGER,
                asdmaxBsCfgPrimMgmtUlQoSProfileIndex
                    INTEGER,
                asdmaxBsCfgBasicMgmtDlQoSProfileIndex
                    INTEGER,
                asdmaxBsCfgBasicMgmtUlQoSProfileIndex
                    INTEGER,
                asdmaxBsCfgAutoScEnabled
                    INTEGER,
                asdmaxBsCfgAutoScIndexRangeMin
                    INTEGER,
                asdmaxBsCfgAutoScIndexRangeMax
                    INTEGER,
                asdmaxBsCfgArqTransmitterDelay
                    INTEGER,
                asdmaxBsCfgArqReceiverDelay
                    INTEGER,
                asdmaxBsCfgArqMinimumRemoteDelay
                    INTEGER
             }

        -- 1.3.6.1.4.1.989.1.16.2.4.1.2.4.1.1
        asdmaxBsCfg2ndMgmtDlQoSProfileIndex OBJECT-TYPE
            SYNTAX INTEGER (0..65535)
            MAX-ACCESS read-write
            STATUS current
            DESCRIPTION
                "This object defines the index of a row in
                wmanIfBsServiceClassTable which is used to obtain all QoS
                parameters required for the BS downlink scheduler to
                properly allocate and manage the bandwidth and schedule
                the 2nd Management Connection traffic. A value of zero
                selects built-in defaults."
            DEFVAL { 0 }
            ::= { asdmaxBsConfigExtEntry 1 }

        
        -- 1.3.6.1.4.1.989.1.16.2.4.1.2.4.1.2
        asdmaxBsCfg2ndMgmtUlQoSProfileIndex OBJECT-TYPE
            SYNTAX INTEGER (0..65535)
            MAX-ACCESS read-write
            STATUS current
            DESCRIPTION
                "This object defines the index of a row in
                wmanIfBsServiceClassTable which is used to obtain all QoS
                parameters required for the BS uplink scheduler to
                properly allocate and manage the bandwidth and schedule
                the 2nd Management Connection traffic. A value of zero
                selects built-in defaults."
            DEFVAL { 0 }
            ::= { asdmaxBsConfigExtEntry 2 }

        
        -- 1.3.6.1.4.1.989.1.16.2.4.1.2.4.1.3
        asdmaxBsCfgAutoSfidEnabled OBJECT-TYPE
            SYNTAX INTEGER
                {
                autoSfidDisabled(0),
                autoSfidEnabled(1)
                }
            MAX-ACCESS read-write
            STATUS current
            DESCRIPTION
                "This object defines whether the BS is allowed to
                autonomously allocate SFIDs. When the object is set to
                autoSfidEnabled, the BS is allowed to autonomously allocate
                SFIDs from the range of allowed values defined by
                asdmaxBsCfgExtAutoSfidRangeMin and 
                asdmaxBsCfgExtAutoSfidRangeMax."
            REFERENCE
                "Section 11.13.1 in IEEE 802.16-2004"
            DEFVAL { autoSfidDisabled }
            ::= { asdmaxBsConfigExtEntry 3 }

        
        -- 1.3.6.1.4.1.989.1.16.2.4.1.2.4.1.4
        asdmaxBsCfgAutoSfidRangeMin OBJECT-TYPE
            SYNTAX Unsigned32 (1..2147483647)
            MAX-ACCESS read-write
            STATUS current
            DESCRIPTION
                "The minimum value of the range of SFID
                values allocated for the BS sector for the purpose of
                autonomous creation of service flows."
            REFERENCE
                "Section 11.13.1 in IEEE 802.16-2004"
            ::= { asdmaxBsConfigExtEntry 4 }

        
        -- 1.3.6.1.4.1.989.1.16.2.4.1.2.4.1.5
        asdmaxBsCfgAutoSfidRangeMax OBJECT-TYPE
            SYNTAX Unsigned32 (1..2147483647)
            MAX-ACCESS read-write
            STATUS current
            DESCRIPTION
                "The maximum value of the range of SFID
                values allocated for the BS sector for the purpose of
                autonomous creation of service flows."
            REFERENCE
                "Section 11.13.1 in IEEE 802.16-2004"
            ::= { asdmaxBsConfigExtEntry 5 }

        
        -- 1.3.6.1.4.1.989.1.16.2.4.1.2.4.1.6
        asdmaxBsCfgResetSector OBJECT-TYPE
            SYNTAX INTEGER
                {
                actionResetSectorNoAction(0),
                actionResetSector(1)
                }
            MAX-ACCESS read-write
            STATUS current
            DESCRIPTION
                "This object should be implemented as follows:
                - When set to actionsResetSector value, instructs BS to
                  reset the sector identified by ifIndex. As a result of
                  this action the Phy and Mac of this sector should be
                  reinitialised.
                - When set to value different than actionsResetSector it
                  should be ignored
                - When read it should return actionsResetSectorNoAction"
            ::= { asdmaxBsConfigExtEntry 6 }

        
        -- 1.3.6.1.4.1.989.1.16.2.4.1.2.4.1.7
        asdmaxBsCfgUncheckedBcastSfid OBJECT-TYPE
            SYNTAX Unsigned32 (0..2147483647)
            MAX-ACCESS read-write
            STATUS current
            DESCRIPTION
                "SFID of the service flow provisioned for the unchecked 
                broadcast VLAN traffic. The parameters of this service 
                flow are defined by asdmaxBsCfgUncheckedBcastServiceClassIndex 
                object.
                A value of zero disables the channel."
            ::= { asdmaxBsConfigExtEntry 7 }

        
        -- 1.3.6.1.4.1.989.1.16.2.4.1.2.4.1.8
        asdmaxBsCfgUncheckedBcastServiceClassIndex OBJECT-TYPE
            SYNTAX INTEGER (1..1000)
            MAX-ACCESS read-write
            STATUS current
            DESCRIPTION
                "Defines Service Class to use for the unchecked 
                Broadcast Service Flow."
            ::= { asdmaxBsConfigExtEntry 8 }

        
        -- 1.3.6.1.4.1.989.1.16.2.4.1.2.4.1.9
        asdmaxBsCfgAllowSsAddressedTraffic OBJECT-TYPE
            SYNTAX INTEGER (0..1)
            MAX-ACCESS read-write
            STATUS current
            DESCRIPTION
                "If set to 1, traffic that appears on the BS traffic port
                that is addressed to the SS is routed as normal traffic if
                it is not otherwise routed to the secondary management channel.
                Note that enabling this feature compromises security.
                This is debug object."
            ::= { asdmaxBsConfigExtEntry 9 }

        
        -- 1.3.6.1.4.1.989.1.16.2.4.1.2.4.1.10
        asdmaxBsCfgPrimMgmtDlQoSProfileIndex OBJECT-TYPE
            SYNTAX INTEGER (0 | 1..65535)
            MAX-ACCESS read-write
            STATUS current
            DESCRIPTION
                "This object defines the index of a row in
                wmanIfBsServiceClassTable which is used to obtain all QoS
                parameters required for the BS downlink scheduler to
                properly allocate and manage the bandwidth and schedule
                the Primary Management Connection traffic.
                Value 0 means use internal policy."
            DEFVAL { 0 }
            ::= { asdmaxBsConfigExtEntry 10 }

        
        -- 1.3.6.1.4.1.989.1.16.2.4.1.2.4.1.11
        asdmaxBsCfgPrimMgmtUlQoSProfileIndex OBJECT-TYPE
            SYNTAX INTEGER (0 | 1..65535)
            MAX-ACCESS read-write
            STATUS current
            DESCRIPTION
                "This object defines the index of a row in
                wmanIfBsServiceClassTable which is used to obtain all QoS
                parameters required for the BS uplink scheduler to
                properly allocate and manage the bandwidth and schedule
                the Primary Management Connection traffic.
                Value 0 means use internal policy."
            DEFVAL { 0 }
            ::= { asdmaxBsConfigExtEntry 11 }

        
        -- 1.3.6.1.4.1.989.1.16.2.4.1.2.4.1.12
        asdmaxBsCfgBasicMgmtDlQoSProfileIndex OBJECT-TYPE
            SYNTAX INTEGER (0 | 1..65535)
            MAX-ACCESS read-write
            STATUS current
            DESCRIPTION
                "This object defines the index of a row in
                wmanIfBsServiceClassTable which is used to obtain all QoS
                parameters required for the BS downlink scheduler to
                properly allocate and manage the bandwidth and schedule
                the Basic Management Connection traffic.
                Value 0 means use internal policy."
            DEFVAL { 0 }
            ::= { asdmaxBsConfigExtEntry 12 }

        
        -- 1.3.6.1.4.1.989.1.16.2.4.1.2.4.1.13
        asdmaxBsCfgBasicMgmtUlQoSProfileIndex OBJECT-TYPE
            SYNTAX INTEGER (0 | 1..65535)
            MAX-ACCESS read-write
            STATUS current
            DESCRIPTION
                "This object defines the index of a row in
                wmanIfBsServiceClassTable which is used to obtain all QoS
                parameters required for the BS uplink scheduler to
                properly allocate and manage the bandwidth and schedule
                the Basic Management Connection traffic.
                Value 0 means use internal policy."
            DEFVAL { 0 }
            ::= { asdmaxBsConfigExtEntry 13 }

        
        -- 1.3.6.1.4.1.989.1.16.2.4.1.2.4.1.14
        asdmaxBsCfgAutoScEnabled OBJECT-TYPE
            SYNTAX INTEGER
                {
                autoScDisabled(0),
                autoScEnabled(1)
                }
            MAX-ACCESS read-write
            STATUS obsolete
            DESCRIPTION
                "Obsoleted: auto creation of named service class is not allowed 
                - flat QoS params can be used instead.
                This object defines whether the BS is allowed to
                autonomously allocate create ServiceClasses. When the object is set to
                autoScEnabled, the BS is allowed to autonomously create
                Service classes from the range of allowed values defined by
                asdmaxBsCfgExtAutoScIndexRangeMin and 
                asdmaxBsCfgExtAutoScIndexRangeMax."
            REFERENCE
                "Section 11.13.1 in IEEE 802.16-2004"
            DEFVAL { autoScDisabled }
            ::= { asdmaxBsConfigExtEntry 14 }

        
        -- 1.3.6.1.4.1.989.1.16.2.4.1.2.4.1.15
        asdmaxBsCfgAutoScIndexRangeMin OBJECT-TYPE
            SYNTAX INTEGER (1..65535)
            MAX-ACCESS read-write
            STATUS obsolete
            DESCRIPTION
                "Obsoleted: auto creation of named service class is not allowed 
                - flat QoS params can be used instead.
                The minimum value of the range of Service Class index
                values allocated for the purpose of
                autonomous creation of service classes."
            REFERENCE
                "Section 11.13.1 in IEEE 802.16-2004"
            ::= { asdmaxBsConfigExtEntry 15 }

        
        -- 1.3.6.1.4.1.989.1.16.2.4.1.2.4.1.16
        asdmaxBsCfgAutoScIndexRangeMax OBJECT-TYPE
            SYNTAX INTEGER (1..65535)
            MAX-ACCESS read-write
            STATUS obsolete
            DESCRIPTION
                "Obsoleted: auto creation of named service class is not allowed 
                - flat QoS params can be used instead.
                The maximum value of the range of Service Class index
                values allocated for for the purpose of
                autonomous creation of service classes."
            REFERENCE
                "Section 11.13.1 in IEEE 802.16-2004"
            DEFVAL { 65535 }
            ::= { asdmaxBsConfigExtEntry 16 }

        
        -- 1.3.6.1.4.1.989.1.16.2.4.1.2.4.1.17
        asdmaxBsCfgArqTransmitterDelay OBJECT-TYPE
            SYNTAX INTEGER (0..65535)
            MAX-ACCESS read-write
            STATUS current
            DESCRIPTION
                "The maximum time taken for an ARQ fragment to be
                transmitted over the air after it has been
                scheduled.  In units of 10us."
            REFERENCE
                "Section 11.13.18.3 in IEEE 802.16-2004"
            DEFVAL { 2000 }
            ::= { asdmaxBsConfigExtEntry 17 }

        
        -- 1.3.6.1.4.1.989.1.16.2.4.1.2.4.1.18
        asdmaxBsCfgArqReceiverDelay OBJECT-TYPE
            SYNTAX INTEGER (0..65535)
            MAX-ACCESS read-write
            STATUS current
            DESCRIPTION
                "The maximum time taken for an ARQ fragment to be
                processed after it has been received over the air.
                In units of 10us."
            REFERENCE
                "Section 11.13.18.3 in IEEE 802.16-2004"
            DEFVAL { 2000 }
            ::= { asdmaxBsConfigExtEntry 18 }

        
        -- 1.3.6.1.4.1.989.1.16.2.4.1.2.4.1.19
        asdmaxBsCfgArqMinimumRemoteDelay OBJECT-TYPE
            SYNTAX INTEGER (0..65535)
            MAX-ACCESS read-write
            STATUS current
            DESCRIPTION
                "The minimum value for the ARQ transmitter or receiver
                delay parameters received from an SS during connection
                service flow negotiation. In units of 10us."
            REFERENCE
                "Section 11.13.18.3 in IEEE 802.16-2004"
            DEFVAL { 3000 }
            ::= { asdmaxBsConfigExtEntry 19 }

        
        -- 1.3.6.1.4.1.989.1.16.2.4.1.2.5
        asdmaxCustomConfigTable OBJECT-TYPE
            SYNTAX SEQUENCE OF AsdmaxCustomConfigEntry
            MAX-ACCESS not-accessible
            STATUS current
            DESCRIPTION
                "This table contains object not defined in the standard MIB 
                and not planned in any future drafts of standard MIB.
                They fall into category of custom, implementation specific objects.
                
                The BS is responsible for creating a row in this table for each 
                interface index of type propBWAp2Mp.
                The NMS can modify values in this table."
            ::= { asdmaxCps 5 }

        
        -- 1.3.6.1.4.1.989.1.16.2.4.1.2.5.1
        asdmaxCustomConfigEntry OBJECT-TYPE
            SYNTAX AsdmaxCustomConfigEntry
            MAX-ACCESS not-accessible
            STATUS current
            DESCRIPTION
                "Description."
            INDEX { ifIndex }
            ::= { asdmaxCustomConfigTable 1 }

        
        AsdmaxCustomConfigEntry ::=
            SEQUENCE { 
                asdmaxCustomRngBackoffStart
                    INTEGER,
                asdmaxCustomRngBackoffEnd
                    INTEGER,
                asdmaxCustomReqBackoffStart
                    INTEGER,
                asdmaxCustomReqBackoffEnd
                    INTEGER,
                asdmaxCustomDuplex
                    INTEGER,
                asdmaxCustomFastPowerCtrl
                    INTEGER,
                asdmaxCustomMinPowerToRaise
                    Integer32,
                asdmaxCustomMaxPowerToLower
                    Integer32,
                asdmaxCustomMinFreqOffset
                    Integer32,
                asdmaxCustomMaxFreqOffset
                    Integer32,
                asdmaxCustomMinTimingOffset
                    Integer32,
                asdmaxCustomMaxTimingOffset
                    Integer32,
                asdmaxCustomSnrChangeForUlBurstProfile
                    Integer32,
                asdmaxCustomTransmitterEnabled
                    INTEGER,
                asdmaxCustomLicenced
                    INTEGER,
                asdmaxCustomLinkUpdatePeriod
                    INTEGER,
                asdmaxCustomLinkUpdateNumSs
                    INTEGER,
                asdmaxCustomTrafficPortMode
                    AsmaxTrafficPortVlanMode,
                asdmaxCustomTddDownlinkPercentage
                    INTEGER,
                asdmaxCustomAllowInsecureSs
                    INTEGER,
                asdmaxCustomUplinkOverbookingRatio
                    INTEGER,
                asdmaxCustomDownlinkOverbookingRatio
                    INTEGER,
                asdmaxCustomUplinkRadioEfficiency
                    INTEGER,
                asdmaxCustomDownlinkRadioEfficiency
                    INTEGER,
                asdmaxCustomMinRangingTosPerSec
                    INTEGER,
                asdmaxCustomMinSubchReqRegionFullTxOpp
                    INTEGER,
                asdmaxCustomChannelBandwidth
                    INTEGER,
                asdmaxCustomRxGain
                    INTEGER,
                asdmaxCustomTxGain
                    INTEGER,
                asdmaxCustomGainRf
                    INTEGER,
                asdmaxCustomGainPc8520
                    INTEGER,
                asdmaxCustomAllocStartTime
                    INTEGER,
                asdmaxCustomMaxBroadcastSize
                    INTEGER,
                asdmaxCustomInitialBurstTailGap
                    INTEGER,
                asdmaxCustomFastPeriodicRangingExchange
                    INTEGER,
                asdmaxCustomDlMapPeriod
                    INTEGER,
                asdmaxCustomTargetTxPower
                    INTEGER,
                asdmaxCustomTargetRxGain
                    INTEGER,
                asdmaxCustomUplinkRxSetPoint
                    INTEGER,
                asdmaxCustomUplinkRxSetPointSpread
                    INTEGER,
                asdmaxCustomUplinkRxInitialRangingSpread
                    INTEGER,
                asdmaxCustomCommissioningMode
                    INTEGER,
                asdmaxCustomCommissioningFrameNumber
                    INTEGER,
                asdmaxCustomUlMaxAllocSize
                    INTEGER,
                asdmaxCustomUlAdjacentAllocGap
                    INTEGER,
                asdmaxCustomUseDlPreambles
                    INTEGER,
                asdmaxCustomRxGainB
                    INTEGER,
                asdmaxCustomTxGainB
                    INTEGER,
                asdmaxCustomRxDiversity
                    INTEGER,
                asdmaxCustomDlMaxBurstSize
                    INTEGER,
                asdmaxCustomAchievedTxPower
                    INTEGER,
                asdmaxCustomAchievedRxGain
                    INTEGER,
                asdmaxCustomContentionPeriodTtg
                    INTEGER,
                asdmaxCustomInitialBurstTtg
                    INTEGER,
                asdmaxCustomDlMaxAllocSize
                    INTEGER,
                asdmaxCustomStrictConformance
                    INTEGER,
                asdmaxCustomUlMidambles
                    INTEGER,
                asdmaxCustomTimingSource
                    INTEGER,
                asdmaxCustomCarrierSenseThreshold
                    INTEGER,
                asdmaxCustomCarrierSenseBackoffFrames
                    Integer32,
                asdmaxCustomStcMode
                    INTEGER,
                asdmaxCustomTransmitFrameGap
                    INTEGER,
                asdmaxCustomCidAllocationNumSss
                    INTEGER,
                asdmaxCustomGlobalEncryptionMode
                    AsdmaxEncryptionMode,
                asdmaxCustomBridgeEntriesPerBs
                    Unsigned32,
                asdmaxCustomBridgeEntriesPerSs
                    Unsigned32,
                asdmaxCustomPacketCounterUpdatePeriod
                    Unsigned32,
                asdmaxCustomScrtPowerUpDelay
                    INTEGER,
                asdmaxCustomAdvertisedIeeeVersion
                    INTEGER,
                asdmaxCustomCidQuarantinePeriod
                    INTEGER,
                asdmaxCustomSasNumBeams
                    INTEGER,
                asdmaxCustomStcFramesBetweenShifts
                    INTEGER,
                asdmaxCustomStcMinimumShift
                    INTEGER,
                asdmaxCustomEarliestStcStartTime
                    INTEGER,
                asdmaxCustomMinimumRegToStcGap
                    INTEGER,
                asdmaxCustomPadDownlinkFrame
                    INTEGER,
                asdmaxCustomUlSnrDownwardAlpha
                    INTEGER,
                asdmaxCustomUlSnrUpwardAlpha
                    INTEGER,
                asdmaxCustomImplementsHomeBasestation
                    AsmaxBooleanSwitch,
                asdmaxCustomBridgeTimeout
                    INTEGER,
                asdmaxCustomBridgeFloodingEnabled
                    AsmaxBooleanSwitch,
                asdmaxCustomReuseGroup
                    INTEGER,
                asdmaxCustomActiveEncryptionMode
                    AsdmaxEncryptionMode,
                asdmaxCustomGpsloopShift
                    Integer32,
                asdmaxCustomActiveRxDiversity
                    INTEGER,
                asdmaxCustomActiveStcMode
                    INTEGER,
                asdmaxCustomScrtRedundancyEnabled
                    AsmaxBooleanSwitch
             }

        -- 1.3.6.1.4.1.989.1.16.2.4.1.2.5.1.1
        asdmaxCustomRngBackoffStart OBJECT-TYPE
            SYNTAX INTEGER (0..15)
            UNITS "^2"
            MAX-ACCESS read-write
            STATUS current
            DESCRIPTION
                "Ranging backoff start, expressed as a power of 2"
            ::= { asdmaxCustomConfigEntry 1 }

        
        -- 1.3.6.1.4.1.989.1.16.2.4.1.2.5.1.2
        asdmaxCustomRngBackoffEnd OBJECT-TYPE
            SYNTAX INTEGER (0..15)
            UNITS "^2"
            MAX-ACCESS read-write
            STATUS current
            DESCRIPTION
                "Ranging backoff end, expressed as a power of 2"
            ::= { asdmaxCustomConfigEntry 2 }

        
        -- 1.3.6.1.4.1.989.1.16.2.4.1.2.5.1.3
        asdmaxCustomReqBackoffStart OBJECT-TYPE
            SYNTAX INTEGER (0..15)
            UNITS "^2"
            MAX-ACCESS read-write
            STATUS current
            DESCRIPTION
                "Request backoff start, expressed as a power of 2"
            ::= { asdmaxCustomConfigEntry 3 }

        
        -- 1.3.6.1.4.1.989.1.16.2.4.1.2.5.1.4
        asdmaxCustomReqBackoffEnd OBJECT-TYPE
            SYNTAX INTEGER (0..15)
            UNITS "^2"
            MAX-ACCESS read-write
            STATUS current
            DESCRIPTION
                "Request backoff end, expressed as a power of 2"
            ::= { asdmaxCustomConfigEntry 4 }

        
        -- 1.3.6.1.4.1.989.1.16.2.4.1.2.5.1.5
        asdmaxCustomDuplex OBJECT-TYPE
            SYNTAX INTEGER
                {
                duplexFdd(0),
                duplexTdd(1)
                }
            MAX-ACCESS read-write
            STATUS current
            DESCRIPTION
                "Selects FDD or TDD operation"
            ::= { asdmaxCustomConfigEntry 5 }

        
        -- 1.3.6.1.4.1.989.1.16.2.4.1.2.5.1.6
        asdmaxCustomFastPowerCtrl OBJECT-TYPE
            SYNTAX INTEGER
                {
                fastPowerControlOff(0),
                fastPowerControlOn(1)
                }
            MAX-ACCESS read-write
            STATUS current
            DESCRIPTION
                "Fast Power Control On/Off flag"
            ::= { asdmaxCustomConfigEntry 6 }

        
        -- 1.3.6.1.4.1.989.1.16.2.4.1.2.5.1.7
        asdmaxCustomMinPowerToRaise OBJECT-TYPE
            SYNTAX Integer32
            MAX-ACCESS read-write
            STATUS obsolete
            DESCRIPTION
                "Minimum power level before SS is asked to raise its power.
                Obsoleted. Value calculated internally by BS from other objects."
            ::= { asdmaxCustomConfigEntry 7 }

        
        -- 1.3.6.1.4.1.989.1.16.2.4.1.2.5.1.8
        asdmaxCustomMaxPowerToLower OBJECT-TYPE
            SYNTAX Integer32
            MAX-ACCESS read-write
            STATUS obsolete
            DESCRIPTION
                "Maximum power level before SS is asked to lower its power.
                Obsoleted. Value calculated internally by BS from other objects."
            ::= { asdmaxCustomConfigEntry 8 }

        
        -- 1.3.6.1.4.1.989.1.16.2.4.1.2.5.1.9
        asdmaxCustomMinFreqOffset OBJECT-TYPE
            SYNTAX Integer32
            MAX-ACCESS read-write
            STATUS current
            DESCRIPTION
                "Minimum frequency offset from nominal (usually negative).
                "
            ::= { asdmaxCustomConfigEntry 9 }

        
        -- 1.3.6.1.4.1.989.1.16.2.4.1.2.5.1.10
        asdmaxCustomMaxFreqOffset OBJECT-TYPE
            SYNTAX Integer32
            MAX-ACCESS read-write
            STATUS current
            DESCRIPTION
                "Maximum frequency offset from nominal (usually positive)."
            ::= { asdmaxCustomConfigEntry 10 }

        
        -- 1.3.6.1.4.1.989.1.16.2.4.1.2.5.1.11
        asdmaxCustomMinTimingOffset OBJECT-TYPE
            SYNTAX Integer32
            MAX-ACCESS read-write
            STATUS current
            DESCRIPTION
                "Minimum timing offset from nominal (usually positive)."
            ::= { asdmaxCustomConfigEntry 11 }

        
        -- 1.3.6.1.4.1.989.1.16.2.4.1.2.5.1.12
        asdmaxCustomMaxTimingOffset OBJECT-TYPE
            SYNTAX Integer32
            MAX-ACCESS read-write
            STATUS current
            DESCRIPTION
                "Maximum timing offset from nominal (usually positive)."
            ::= { asdmaxCustomConfigEntry 12 }

        
        -- 1.3.6.1.4.1.989.1.16.2.4.1.2.5.1.13
        asdmaxCustomSnrChangeForUlBurstProfile OBJECT-TYPE
            SYNTAX Integer32
            UNITS "0.25 dB"
            MAX-ACCESS read-write
            STATUS current
            DESCRIPTION
                "Size of SNR change before recalculating the uplink burst profile."
            DEFVAL { 8 }
            ::= { asdmaxCustomConfigEntry 13 }

        
        -- 1.3.6.1.4.1.989.1.16.2.4.1.2.5.1.14
        asdmaxCustomTransmitterEnabled OBJECT-TYPE
            SYNTAX INTEGER
                {
                transmitterDisabled(0),
                transmitterEnabled(1)
                }
            MAX-ACCESS read-write
            STATUS current
            DESCRIPTION
                "Instructs BS to enable/disable the transmitter for given interface."
            ::= { asdmaxCustomConfigEntry 14 }

        
        -- 1.3.6.1.4.1.989.1.16.2.4.1.2.5.1.15
        asdmaxCustomLicenced OBJECT-TYPE
            SYNTAX INTEGER
                {
                unlicenced(0),
                licenced(1)
                }
            MAX-ACCESS read-write
            STATUS current
            DESCRIPTION
                "Tells BS on what object to use to configure 
                channel frequency (wmanIfCmnOfdmChannelNumber 
                or wmanIfCmnOfdmDownlinkCenterFreq).
                "
            ::= { asdmaxCustomConfigEntry 15 }

        
        -- 1.3.6.1.4.1.989.1.16.2.4.1.2.5.1.16
        asdmaxCustomLinkUpdatePeriod OBJECT-TYPE
            SYNTAX INTEGER (1..65535)
            UNITS "ms"
            MAX-ACCESS read-write
            STATUS current
            DESCRIPTION
                "The period BS scans a number of SSs 
                (defined by asdmaxCustomLinkUpdateNumSs) for their
                uplink level adjustments."
            ::= { asdmaxCustomConfigEntry 16 }

        
        -- 1.3.6.1.4.1.989.1.16.2.4.1.2.5.1.17
        asdmaxCustomLinkUpdateNumSs OBJECT-TYPE
            SYNTAX INTEGER (0..255)
            MAX-ACCESS read-write
            STATUS current
            DESCRIPTION
                "The number of SSs being scanned by BS for their
                uplink level adjustments, every 
                asdmaxCustomLinkUpdatePeriod."
            ::= { asdmaxCustomConfigEntry 17 }

        
        -- 1.3.6.1.4.1.989.1.16.2.4.1.2.5.1.18
        asdmaxCustomTrafficPortMode OBJECT-TYPE
            SYNTAX AsmaxTrafficPortVlanMode
            MAX-ACCESS read-write
            STATUS current
            DESCRIPTION
                "Defines how the Ethernet frames are encoded 
                on local traffic Ethernet port.
                When configured with value of vlanModeDot1q alternative objects
                in table asdmaxBsQPortTable define the behaviour of this bridge port."
            DEFVAL { vlanModeRaw }
            ::= { asdmaxCustomConfigEntry 18 }

        
        -- 1.3.6.1.4.1.989.1.16.2.4.1.2.5.1.19
        asdmaxCustomTddDownlinkPercentage OBJECT-TYPE
            SYNTAX INTEGER (0..100)
            UNITS "%"
            MAX-ACCESS read-write
            STATUS current
            DESCRIPTION
                "The percentage of the TDD frame to be
                used for the downlink"
            DEFVAL { 50 }
            ::= { asdmaxCustomConfigEntry 19 }

        
        -- 1.3.6.1.4.1.989.1.16.2.4.1.2.5.1.20
        asdmaxCustomAllowInsecureSs OBJECT-TYPE
            SYNTAX INTEGER
                {
                insecureSsNotAllowed(0),
                insecureSsAllowed(1)
                }
            MAX-ACCESS read-write
            STATUS current
            DESCRIPTION
                "Controls whether the BS will allow SSs that do not
                support the IEEE802.16 security access to the network."
            ::= { asdmaxCustomConfigEntry 20 }

        
        -- 1.3.6.1.4.1.989.1.16.2.4.1.2.5.1.21
        asdmaxCustomUplinkOverbookingRatio OBJECT-TYPE
            SYNTAX INTEGER (1..10000)
            MAX-ACCESS read-write
            STATUS current
            DESCRIPTION
                "The multiplier (in 1/10ths) applied to the uplink radio capacity 
                when checking that a committed information rate is allowed."
            ::= { asdmaxCustomConfigEntry 21 }

        
        -- 1.3.6.1.4.1.989.1.16.2.4.1.2.5.1.22
        asdmaxCustomDownlinkOverbookingRatio OBJECT-TYPE
            SYNTAX INTEGER (1..10000)
            MAX-ACCESS read-write
            STATUS current
            DESCRIPTION
                "The multiplier (in 1/10ths) applied to the downlink radio capacity 
                when checking that a committed information rate is allowed."
            ::= { asdmaxCustomConfigEntry 22 }

        
        -- 1.3.6.1.4.1.989.1.16.2.4.1.2.5.1.23
        asdmaxCustomUplinkRadioEfficiency OBJECT-TYPE
            SYNTAX INTEGER (0..100)
            UNITS "%"
            MAX-ACCESS read-write
            STATUS current
            DESCRIPTION
                "An estimate of the percentage of the uplink bandwidth
                that actually carries traffic."
            ::= { asdmaxCustomConfigEntry 23 }

        
        -- 1.3.6.1.4.1.989.1.16.2.4.1.2.5.1.24
        asdmaxCustomDownlinkRadioEfficiency OBJECT-TYPE
            SYNTAX INTEGER (0..100)
            UNITS "%"
            MAX-ACCESS read-write
            STATUS current
            DESCRIPTION
                "An estimate of the percentage of the downlink bandwidth
                that actually carries traffic."
            ::= { asdmaxCustomConfigEntry 24 }

        
        -- 1.3.6.1.4.1.989.1.16.2.4.1.2.5.1.25
        asdmaxCustomMinRangingTosPerSec OBJECT-TYPE
            SYNTAX INTEGER (0..1000)
            UNITS "1/s"
            MAX-ACCESS read-write
            STATUS current
            DESCRIPTION
                "This object defines the number of ranging transmit
                opportunities to be planted per second in the uplink map."
            ::= { asdmaxCustomConfigEntry 25 }

        
        -- 1.3.6.1.4.1.989.1.16.2.4.1.2.5.1.26
        asdmaxCustomMinSubchReqRegionFullTxOpp OBJECT-TYPE
            SYNTAX INTEGER (0..65535)
            UNITS "1/s"
            MAX-ACCESS read-write
            STATUS current
            DESCRIPTION
                "The minimum number of sub-channelised Req-Region Full
                Transmit opportunities scheduled in the UL per second."
            ::= { asdmaxCustomConfigEntry 26 }

        
        -- 1.3.6.1.4.1.989.1.16.2.4.1.2.5.1.27
        asdmaxCustomChannelBandwidth OBJECT-TYPE
            SYNTAX INTEGER
                {
                bandwidth1m75(0),
                bandwidth3m5(1),
                bandwidth5m(2),
                bandwidth7m(3),
                bandwidth10m(4)
                }
            MAX-ACCESS read-write
            STATUS current
            DESCRIPTION
                "The bandwidth of the radio channel."
            ::= { asdmaxCustomConfigEntry 27 }

        
        -- 1.3.6.1.4.1.989.1.16.2.4.1.2.5.1.28
        asdmaxCustomRxGain OBJECT-TYPE
            SYNTAX INTEGER (0..255)
            MAX-ACCESS read-write
            STATUS current
            DESCRIPTION
                "The gain of the receiver in arbitary units.
                Internal - calculated by BS if characterisation 
                table available otherwise debug input."
            ::= { asdmaxCustomConfigEntry 28 }

        
        -- 1.3.6.1.4.1.989.1.16.2.4.1.2.5.1.29
        asdmaxCustomTxGain OBJECT-TYPE
            SYNTAX INTEGER (0..4095)
            MAX-ACCESS read-write
            STATUS current
            DESCRIPTION
                "The gain of the transmitter in arbitary units.
                Internal - calculated by BS if characterisation 
                table available otherwise debug input."
            ::= { asdmaxCustomConfigEntry 29 }

        
        -- 1.3.6.1.4.1.989.1.16.2.4.1.2.5.1.30
        asdmaxCustomGainRf OBJECT-TYPE
            SYNTAX INTEGER (0..65535)
            UNITS "1/100th of dB"
            MAX-ACCESS read-write
            STATUS current
            DESCRIPTION
                "The gain of the RF card in 1/100ths of dB.
                Internal - set during characterisation."
            DEFVAL { 6700 }
            ::= { asdmaxCustomConfigEntry 30 }

        
        -- 1.3.6.1.4.1.989.1.16.2.4.1.2.5.1.31
        asdmaxCustomGainPc8520 OBJECT-TYPE
            SYNTAX INTEGER (0..65535)
            UNITS "1/100th of dB"
            MAX-ACCESS read-write
            STATUS current
            DESCRIPTION
                "The gain of the PC8520 in 1/100ths of dB.
                Internal - set during characterisation."
            DEFVAL { 5680 }
            ::= { asdmaxCustomConfigEntry 31 }

        
        -- 1.3.6.1.4.1.989.1.16.2.4.1.2.5.1.32
        asdmaxCustomAllocStartTime OBJECT-TYPE
            SYNTAX INTEGER (0..65535)
            UNITS "PS"
            MAX-ACCESS read-write
            STATUS current
            DESCRIPTION
                "The allocation start time for the UL-MAP in PSs.
                For debug purposes only, Make sure you know what
                you are doing before changing this.
                Value 0 means automatic allocation.
                This is debug feature in Draft 1S+."
            DEFVAL { 0 }
            ::= { asdmaxCustomConfigEntry 32 }

        
        -- 1.3.6.1.4.1.989.1.16.2.4.1.2.5.1.33
        asdmaxCustomMaxBroadcastSize OBJECT-TYPE
            SYNTAX INTEGER (0..100)
            UNITS "%"
            MAX-ACCESS read-write
            STATUS obsolete
            DESCRIPTION
                "The maximum amount of broadcast traffic that will be
                placed in a single frame, as a percentage of the frame."
            DEFVAL { 10 }
            ::= { asdmaxCustomConfigEntry 33 }

        
        -- 1.3.6.1.4.1.989.1.16.2.4.1.2.5.1.34
        asdmaxCustomInitialBurstTailGap OBJECT-TYPE
            SYNTAX INTEGER (0..1000)
            UNITS "Symbol"
            MAX-ACCESS read-write
            STATUS current
            DESCRIPTION
                "The size of the gap between the initial burst and the
                second burst (if it exists), in symbols.
                This is debug feature in Draft 1S."
            DEFVAL { 0 }
            ::= { asdmaxCustomConfigEntry 34 }

        
        -- 1.3.6.1.4.1.989.1.16.2.4.1.2.5.1.35
        asdmaxCustomFastPeriodicRangingExchange OBJECT-TYPE
            SYNTAX INTEGER
                {
                regularPeriodicRanging(0),
                fastPeriodicRanging(1)
                }
            MAX-ACCESS read-write
            STATUS current
            DESCRIPTION
                "Set to 0 for regular (D3) periodic ranging.  Set to
                1 for fast (D4) mode where the BS sends only a RNG-RESP
                witht the SUCCESS code to make adjustments."
            DEFVAL { regularPeriodicRanging }
            ::= { asdmaxCustomConfigEntry 35 }

        
        -- 1.3.6.1.4.1.989.1.16.2.4.1.2.5.1.36
        asdmaxCustomDlMapPeriod OBJECT-TYPE
            SYNTAX INTEGER (0..10000)
            UNITS "ms"
            MAX-ACCESS read-write
            STATUS current
            DESCRIPTION
                "Specifies the period at which DL maps must be
                included in the downlink, in milliseconds.  A
                value of 0 turns off the inclusion of empty ones.
                SS may require map to be sent in every frame - 
                in this case set the value to 1 ms less than frame duration
                (e.g. 9 for 10 ms frame)."
            DEFVAL { 250 }
            ::= { asdmaxCustomConfigEntry 36 }

        
        -- 1.3.6.1.4.1.989.1.16.2.4.1.2.5.1.37
        asdmaxCustomTargetTxPower OBJECT-TYPE
            SYNTAX INTEGER (0..152)
            UNITS "0.25 dBm"
            MAX-ACCESS read-write
            STATUS current
            DESCRIPTION
                "The required output power of the BS transmitter
                in 1/4dBm.  If this object is present and the BS
                has calibration tables available to it, this object
                is used to calculate the TX gain and the 
                asdmaxCustomTxGain object is ignored."
            ::= { asdmaxCustomConfigEntry 37 }

        
        -- 1.3.6.1.4.1.989.1.16.2.4.1.2.5.1.38
        asdmaxCustomTargetRxGain OBJECT-TYPE
            SYNTAX INTEGER (0..1000)
            UNITS "0.25 dB"
            MAX-ACCESS read-write
            STATUS current
            DESCRIPTION
                "The required receiver gain of the BS transmitter
                in 1/4dB.  If this object is present and the BS
                has calibration tables available to it, this object
                is used to calculate the RX gain and the 
                asdmaxCustomRxGain object is ignored.
                Internal - set during characterisation."
            ::= { asdmaxCustomConfigEntry 38 }

        
        -- 1.3.6.1.4.1.989.1.16.2.4.1.2.5.1.39
        asdmaxCustomUplinkRxSetPoint OBJECT-TYPE
            SYNTAX INTEGER (-440..200)
            UNITS "0.25 dBm"
            MAX-ACCESS read-write
            STATUS current
            DESCRIPTION
                "The uplink receive level set point, in 1/4 dBm.
                This object replaces asdmaxCustomMinPowerToRaise
                and asdmaxCustomMinPowerToLower."
            ::= { asdmaxCustomConfigEntry 39 }

        
        -- 1.3.6.1.4.1.989.1.16.2.4.1.2.5.1.40
        asdmaxCustomUplinkRxSetPointSpread OBJECT-TYPE
            SYNTAX INTEGER (0..200)
            UNITS "0.25 dBm"
            MAX-ACCESS read-write
            STATUS current
            DESCRIPTION
                "The spread around the asdmaxCustomUplinkRxSetPoint
                in 1/4 dBm that the BS will allow before power
                adjustment is performed during periodic ranging."
            ::= { asdmaxCustomConfigEntry 40 }

        
        -- 1.3.6.1.4.1.989.1.16.2.4.1.2.5.1.41
        asdmaxCustomUplinkRxInitialRangingSpread OBJECT-TYPE
            SYNTAX INTEGER (0..200)
            UNITS "0.25 dBm"
            MAX-ACCESS read-write
            STATUS current
            DESCRIPTION
                "The spread around the asdmaxCustomUplinkRxSetPoint
                in 1/4 dBm that the BS will allow before power
                adjustment is performed during initial ranging."
            ::= { asdmaxCustomConfigEntry 41 }

        
        -- 1.3.6.1.4.1.989.1.16.2.4.1.2.5.1.42
        asdmaxCustomCommissioningMode OBJECT-TYPE
            SYNTAX INTEGER
                {
                modeNormal(0),
                modeCommissioning(1)
                }
            MAX-ACCESS read-write
            STATUS current
            DESCRIPTION
                "Local configuration object.
                Set to 1 to enable commissioning mode, 0 for 
                normal operating mode."
            ::= { asdmaxCustomConfigEntry 42 }

        
        -- 1.3.6.1.4.1.989.1.16.2.4.1.2.5.1.43
        asdmaxCustomCommissioningFrameNumber OBJECT-TYPE
            SYNTAX INTEGER (0..15)
            MAX-ACCESS read-write
            STATUS current
            DESCRIPTION
                "Local configuration object.
                Selects the frame number (modulo 16) that
                commissioning mode uplink transmissions are
                to be received on."
            ::= { asdmaxCustomConfigEntry 43 }

        
        -- 1.3.6.1.4.1.989.1.16.2.4.1.2.5.1.44
        asdmaxCustomUlMaxAllocSize OBJECT-TYPE
            SYNTAX INTEGER (64..65535)
            UNITS "byte"
            MAX-ACCESS read-write
            STATUS current
            DESCRIPTION
                "Specifies, in bytes, the maximum size of uplink
                allocation that will be given to an SS in one grant."
            DEFVAL { 40000 }
            ::= { asdmaxCustomConfigEntry 44 }

        
        -- 1.3.6.1.4.1.989.1.16.2.4.1.2.5.1.45
        asdmaxCustomUlAdjacentAllocGap OBJECT-TYPE
            SYNTAX INTEGER (0..16)
            UNITS "symbol"
            MAX-ACCESS read-write
            STATUS current
            DESCRIPTION
                "When two uplink allocations for the same SS are
                adjacent in the uplink map, this object specifies
                the size of the gap, in symbols, that will be
                inserted between them."
            DEFVAL { 2 }
            ::= { asdmaxCustomConfigEntry 45 }

        
        -- 1.3.6.1.4.1.989.1.16.2.4.1.2.5.1.46
        asdmaxCustomUseDlPreambles OBJECT-TYPE
            SYNTAX INTEGER
                {
                dlPreambleOmit(0),
                dlPreambleInclude(1)
                }
            MAX-ACCESS read-write
            STATUS current
            DESCRIPTION
                "Controls whether preambles are included in
                downlink bursts.  Set to 1 to include them,
                0 to omit them."
            DEFVAL { dlPreambleOmit }
            ::= { asdmaxCustomConfigEntry 46 }

        
        -- 1.3.6.1.4.1.989.1.16.2.4.1.2.5.1.47
        asdmaxCustomRxGainB OBJECT-TYPE
            SYNTAX INTEGER (0..255)
            MAX-ACCESS read-write
            STATUS current
            DESCRIPTION
                "The gain of the receiver B channel in arbitary units.
                Internal - calculated by BS if characterisation 
                table available otherwise debug input."
            ::= { asdmaxCustomConfigEntry 47 }

        
        -- 1.3.6.1.4.1.989.1.16.2.4.1.2.5.1.48
        asdmaxCustomTxGainB OBJECT-TYPE
            SYNTAX INTEGER (0..4095)
            MAX-ACCESS read-write
            STATUS current
            DESCRIPTION
                "The gain of the transmitter B channel in arbitary units.
                Internal - calculated by BS if characterisation 
                table available otherwise debug input."
            ::= { asdmaxCustomConfigEntry 48 }

        
        -- 1.3.6.1.4.1.989.1.16.2.4.1.2.5.1.49
        asdmaxCustomRxDiversity OBJECT-TYPE
            SYNTAX INTEGER
                {
                diversityOff(0),
                diversityMrc(1)
                }
            MAX-ACCESS read-write
            STATUS current
            DESCRIPTION
                "The receive diversity mode.  0 for off, 1 for MRC."
            DEFVAL { diversityOff }
            ::= { asdmaxCustomConfigEntry 49 }

        
        -- 1.3.6.1.4.1.989.1.16.2.4.1.2.5.1.50
        asdmaxCustomDlMaxBurstSize OBJECT-TYPE
            SYNTAX INTEGER (2..4096)
            UNITS "symbol"
            MAX-ACCESS read-write
            STATUS current
            DESCRIPTION
                "Debug object.
                The maximum size, in symbols, of a downlink burst."
            ::= { asdmaxCustomConfigEntry 50 }

        
        -- 1.3.6.1.4.1.989.1.16.2.4.1.2.5.1.51
        asdmaxCustomAchievedTxPower OBJECT-TYPE
            SYNTAX INTEGER (0..152)
            UNITS "0.25 dBm"
            MAX-ACCESS read-only
            STATUS current
            DESCRIPTION
                "The achieved output power of the BS transmitter
                in 1/4dBm.  This is the result of the calibration
                calculation, if performed., Zero otherwise."
            ::= { asdmaxCustomConfigEntry 51 }

        
        -- 1.3.6.1.4.1.989.1.16.2.4.1.2.5.1.52
        asdmaxCustomAchievedRxGain OBJECT-TYPE
            SYNTAX INTEGER (0..1000)
            UNITS "0.25 dB"
            MAX-ACCESS read-only
            STATUS current
            DESCRIPTION
                "The achieved receiver gain of the BS transmitter
                in 1/4dB.  This is the result of the calibration
                calculation, if performed.  Zero otherwise."
            ::= { asdmaxCustomConfigEntry 52 }

        
        -- 1.3.6.1.4.1.989.1.16.2.4.1.2.5.1.53
        asdmaxCustomContentionPeriodTtg OBJECT-TYPE
            SYNTAX INTEGER (0..32000)
            UNITS "PS"
            MAX-ACCESS read-write
            STATUS current
            DESCRIPTION
                "The transmitter to receiver turn-around gap used
                between the end of the last downlink burst and the
                uplink contention slots at the end of the uplink sub-frame"
            DEFVAL { 660 }
            ::= { asdmaxCustomConfigEntry 53 }

        
        -- 1.3.6.1.4.1.989.1.16.2.4.1.2.5.1.54
        asdmaxCustomInitialBurstTtg OBJECT-TYPE
            SYNTAX INTEGER (0..32000)
            UNITS "PS"
            MAX-ACCESS read-write
            STATUS current
            DESCRIPTION
                "The transmitter to receiver turn-around gap used
                between the end of the initial downlink burst and the
                start of the uplink in TDD mode"
            DEFVAL { 1960 }
            ::= { asdmaxCustomConfigEntry 54 }

        
        -- 1.3.6.1.4.1.989.1.16.2.4.1.2.5.1.55
        asdmaxCustomDlMaxAllocSize OBJECT-TYPE
            SYNTAX INTEGER (64..32000)
            UNITS "byte"
            MAX-ACCESS read-write
            STATUS current
            DESCRIPTION
                "Specifies, in bytes, the maximum size of a downlink
                allocation that will be given to an SS before other SSs
                are considered."
            DEFVAL { 1530 }
            ::= { asdmaxCustomConfigEntry 55 }

        
        -- 1.3.6.1.4.1.989.1.16.2.4.1.2.5.1.56
        asdmaxCustomStrictConformance OBJECT-TYPE
            SYNTAX INTEGER
                {
                normal(0),
                strictConformance(1)
                }
            MAX-ACCESS read-write
            STATUS current
            DESCRIPTION
                "When set to 1, the BS behaves strictly according to the
                wimax conformance tests."
            DEFVAL { normal }
            ::= { asdmaxCustomConfigEntry 56 }

        
        -- 1.3.6.1.4.1.989.1.16.2.4.1.2.5.1.57
        asdmaxCustomUlMidambles OBJECT-TYPE
            SYNTAX INTEGER
                {
                disabled(0),
                afterEvery4DataSymbols(1),
                afterEvery8DataSymbols(2),
                afterEvery16DataSymbols(3)
                }
            MAX-ACCESS read-write
            STATUS current
            DESCRIPTION
                "Selects the uplink midamble mode to use inthe BS.
                Labels of enumeration corrected based on 802.16e-2005."
            DEFVAL { disabled }
            ::= { asdmaxCustomConfigEntry 57 }

        
        -- 1.3.6.1.4.1.989.1.16.2.4.1.2.5.1.58
        asdmaxCustomTimingSource OBJECT-TYPE
            SYNTAX INTEGER
                {
                sourceGpsWithSuppress(0),
                sourceGpsNoSuppress(1),
                sourceInternal(2)
                }
            MAX-ACCESS read-write
            STATUS current
            DESCRIPTION
                "Controls the source of the 1PPS signal and, in the case of GPS,
                whether the RF output should be suppressed if teh source fails."
            DEFVAL { sourceInternal }
            ::= { asdmaxCustomConfigEntry 58 }

        
        -- 1.3.6.1.4.1.989.1.16.2.4.1.2.5.1.59
        asdmaxCustomCarrierSenseThreshold OBJECT-TYPE
            SYNTAX INTEGER (-512..-120)
            UNITS "0.25 dBm"
            MAX-ACCESS read-write
            STATUS current
            DESCRIPTION
                "The power level in units of 1/4dBm of the detected wideband RSSI at which
                interfering carrier is deemed to have been detected and thus triggers
                the carrier sense detection mechanism.
                "
            DEFVAL { -120 }
            ::= { asdmaxCustomConfigEntry 59 }

        
        -- 1.3.6.1.4.1.989.1.16.2.4.1.2.5.1.60
        asdmaxCustomCarrierSenseBackoffFrames OBJECT-TYPE
            SYNTAX Integer32 (1..2147483647)
            MAX-ACCESS read-write
            STATUS current
            DESCRIPTION
                "This is used to control the number of frames (x) to back off in case 
                the interference is detected."
            DEFVAL { 1 }
            ::= { asdmaxCustomConfigEntry 60 }

        
        -- 1.3.6.1.4.1.989.1.16.2.4.1.2.5.1.61
        asdmaxCustomStcMode OBJECT-TYPE
            SYNTAX INTEGER
                {
                stcNone(0),
                stcMode1(1),
                stcMode2(2),
                delayMode1(3),
                hybridMode1(4),
                hybridMode2(5)
                }
            MAX-ACCESS read-write
            STATUS current
            DESCRIPTION
                "Specifies the STC mode. Mode 1 assumes all SSs support STC,
                all unicast bursts are in the STC zone but not the broadcasts
                or maps."
            DEFVAL { stcNone }
            ::= { asdmaxCustomConfigEntry 61 }

        
        -- 1.3.6.1.4.1.989.1.16.2.4.1.2.5.1.62
        asdmaxCustomTransmitFrameGap OBJECT-TYPE
            SYNTAX INTEGER (0..65000)
            UNITS "ps"
            MAX-ACCESS read-write
            STATUS current
            DESCRIPTION
                "The gap between the end of the downlink transmission in
                one frame and the start of the downlink preamble of the next,
                in PS."
            DEFVAL { 600 }
            ::= { asdmaxCustomConfigEntry 62 }

        
        -- 1.3.6.1.4.1.989.1.16.2.4.1.2.5.1.63
        asdmaxCustomCidAllocationNumSss OBJECT-TYPE
            SYNTAX INTEGER (0..24000)
            MAX-ACCESS read-write
            STATUS current
            DESCRIPTION
                "Defines the number of SSs that the CID allocater uses for the 'm'
                value as described in section 10 of the standard.  It controls the
                segregation of the CID space into basic, primary and traffic
                areas.  A value of zero fills only the traffic area.  If the basic
                or primary areas are empty, the traffic area is used.  A value of
                zero is therefore the same as the original algorithm but is not
                strictly standards compliant.  Only effective after a reboot."
            DEFVAL { 0 }
            ::= { asdmaxCustomConfigEntry 63 }

        
        -- 1.3.6.1.4.1.989.1.16.2.4.1.2.5.1.64
        asdmaxCustomGlobalEncryptionMode OBJECT-TYPE
            SYNTAX AsdmaxEncryptionMode
            MAX-ACCESS read-write
            STATUS current
            DESCRIPTION
                "Configures the 'maximum' encryption mode that the
                BS will permit for an SS.  The no XOR IV mode
                selects the non-standard DES mode used by early
                Rosedale software."
            ::= { asdmaxCustomConfigEntry 64 }

        
        -- 1.3.6.1.4.1.989.1.16.2.4.1.2.5.1.65
        asdmaxCustomBridgeEntriesPerBs OBJECT-TYPE
            SYNTAX Unsigned32 (1..64000)
            MAX-ACCESS read-write
            STATUS current
            DESCRIPTION
                "Number of mac entries (downlink machines) allowed in rtmac 
                bridge table for a single bs"
            DEFVAL { 64000 }
            ::= { asdmaxCustomConfigEntry 65 }

        
        -- 1.3.6.1.4.1.989.1.16.2.4.1.2.5.1.66
        asdmaxCustomBridgeEntriesPerSs OBJECT-TYPE
            SYNTAX Unsigned32
            MAX-ACCESS read-write
            STATUS current
            DESCRIPTION
                "Number of mac entries (downlink machines) allowed in rtmac 
                bridge table for a single ss"
            DEFVAL { 64 }
            ::= { asdmaxCustomConfigEntry 66 }

        
        -- 1.3.6.1.4.1.989.1.16.2.4.1.2.5.1.67
        asdmaxCustomPacketCounterUpdatePeriod OBJECT-TYPE
            SYNTAX Unsigned32
            UNITS "ms"
            MAX-ACCESS read-write
            STATUS current
            DESCRIPTION
                "Delay (in ms) between each cid update in the BsSsPacketCounterTable.
                0 = no updates at all."
            DEFVAL { 0 }
            ::= { asdmaxCustomConfigEntry 67 }

        
        -- 1.3.6.1.4.1.989.1.16.2.4.1.2.5.1.68
        asdmaxCustomScrtPowerUpDelay OBJECT-TYPE
            SYNTAX INTEGER (0..60)
            MAX-ACCESS read-write
            STATUS current
            DESCRIPTION
                "Values 1..60 define the delay in minutes BS powers up SCRT automatically 
                after the protection shutdown.
                Value 0 means that BS never powers up SCRT automatically 
                after the protection shut down."
            ::= { asdmaxCustomConfigEntry 68 }

        
        -- 1.3.6.1.4.1.989.1.16.2.4.1.2.5.1.69
        asdmaxCustomAdvertisedIeeeVersion OBJECT-TYPE
            SYNTAX INTEGER
                {
                ieee802Dot16-2004(4),
                ieee802Dot16-2004Cor1(5)
                }
            MAX-ACCESS read-write
            STATUS current
            DESCRIPTION
                "The IEEE 802.16 version number that is advertised
                in the DCD and RNG-REQ messages.  Default is ieee802Dot16-2004Cor1 (5) 
                which corresponds to the latest corrigenda. 
                The value configured using this object is automatically 
                copied by BS to object wmanIfCmnOfdmMacVersion. 
                This is a debug parameter that probably shouldn't be exposed
                through Netspan."
            DEFVAL { ieee802Dot16-2004Cor1 }
            ::= { asdmaxCustomConfigEntry 69 }

        
        -- 1.3.6.1.4.1.989.1.16.2.4.1.2.5.1.70
        asdmaxCustomCidQuarantinePeriod OBJECT-TYPE
            SYNTAX INTEGER (0..32768)
            UNITS "s"
            MAX-ACCESS read-write
            STATUS current
            DESCRIPTION
                "The period, in seconds, that a CID is placed in quarantine
                before it is reused.  Zero means no quarantine period.  The
                default is 10 minutes.
                This object is for debug purposes only."
            DEFVAL { 600 }
            ::= { asdmaxCustomConfigEntry 70 }

        
        -- 1.3.6.1.4.1.989.1.16.2.4.1.2.5.1.71
        asdmaxCustomSasNumBeams OBJECT-TYPE
            SYNTAX INTEGER (0..4)
            MAX-ACCESS read-write
            STATUS current
            DESCRIPTION
                "Number of beams in SAS mode. A value of 0 or 1 indicates SAS is disabled "
            DEFVAL { 1 }
            ::= { asdmaxCustomConfigEntry 71 }

        
        -- 1.3.6.1.4.1.989.1.16.2.4.1.2.5.1.72
        asdmaxCustomStcFramesBetweenShifts OBJECT-TYPE
            SYNTAX INTEGER (0..65535)
            MAX-ACCESS read-write
            STATUS current
            DESCRIPTION
                "Minimum number of frames between shifts of the STC zone start time (STC mode 2 only)."
            DEFVAL { 1 }
            ::= { asdmaxCustomConfigEntry 72 }

        
        -- 1.3.6.1.4.1.989.1.16.2.4.1.2.5.1.73
        asdmaxCustomStcMinimumShift OBJECT-TYPE
            SYNTAX INTEGER (0..65535)
            MAX-ACCESS read-write
            STATUS current
            DESCRIPTION
                "Minimum number of symbols by which to shift the STC zone start time (STC mode 2 only)."
            DEFVAL { 1 }
            ::= { asdmaxCustomConfigEntry 73 }

        
        -- 1.3.6.1.4.1.989.1.16.2.4.1.2.5.1.74
        asdmaxCustomEarliestStcStartTime OBJECT-TYPE
            SYNTAX INTEGER (5..255)
            MAX-ACCESS read-write
            STATUS current
            DESCRIPTION
                "Earliest allowable start time for the STC zone (in symbols, from the beginning of the frame)."
            DEFVAL { 5 }
            ::= { asdmaxCustomConfigEntry 74 }

        
        -- 1.3.6.1.4.1.989.1.16.2.4.1.2.5.1.75
        asdmaxCustomMinimumRegToStcGap OBJECT-TYPE
            SYNTAX INTEGER (0..255)
            MAX-ACCESS read-write
            STATUS current
            DESCRIPTION
                "Minimum number of gap symbols between the regular and STC zones."
            DEFVAL { 0 }
            ::= { asdmaxCustomConfigEntry 75 }

        
        -- 1.3.6.1.4.1.989.1.16.2.4.1.2.5.1.76
        asdmaxCustomPadDownlinkFrame OBJECT-TYPE
            SYNTAX INTEGER
                {
                paddingOff(0),
                paddingOn(1)
                }
            MAX-ACCESS read-write
            STATUS current
            DESCRIPTION
                "Set to 1 to fill the whole downlink frame with padding."
            DEFVAL { 0 }
            ::= { asdmaxCustomConfigEntry 76 }

        
        -- 1.3.6.1.4.1.989.1.16.2.4.1.2.5.1.77
        asdmaxCustomUlSnrDownwardAlpha OBJECT-TYPE
            SYNTAX INTEGER (1..32)
            MAX-ACCESS read-write
            STATUS current
            DESCRIPTION
                "Uplink SNR averaging alpha control parameter in the downward direction.
                "
            DEFVAL { 8 }
            ::= { asdmaxCustomConfigEntry 77 }

        
        -- 1.3.6.1.4.1.989.1.16.2.4.1.2.5.1.78
        asdmaxCustomUlSnrUpwardAlpha OBJECT-TYPE
            SYNTAX INTEGER (1..32)
            MAX-ACCESS read-write
            STATUS current
            DESCRIPTION
                "Uplink SNR averaging alpha control parameter in the upward direction"
            DEFVAL { 8 }
            ::= { asdmaxCustomConfigEntry 78 }

        
        -- 1.3.6.1.4.1.989.1.16.2.4.1.2.5.1.79
        asdmaxCustomImplementsHomeBasestation OBJECT-TYPE
            SYNTAX AsmaxBooleanSwitch
            MAX-ACCESS read-write
            STATUS current
            DESCRIPTION
                "Controls the BS behaviour when an SS that has signed on
                receives no service flow configuration.  When set to on,
                the SS is instructed to deregister and try another BS."
            DEFVAL { booleanFalse }
            ::= { asdmaxCustomConfigEntry 79 }

        
        -- 1.3.6.1.4.1.989.1.16.2.4.1.2.5.1.80
        asdmaxCustomBridgeTimeout OBJECT-TYPE
            SYNTAX INTEGER (10..1000000)
            UNITS "s"
            MAX-ACCESS read-write
            STATUS current
            DESCRIPTION
                "Bridge MAC address aging timeout, in seconds"
            DEFVAL { 300 }
            ::= { asdmaxCustomConfigEntry 80 }

        
        -- 1.3.6.1.4.1.989.1.16.2.4.1.2.5.1.81
        asdmaxCustomBridgeFloodingEnabled OBJECT-TYPE
            SYNTAX AsmaxBooleanSwitch
            MAX-ACCESS read-write
            STATUS current
            DESCRIPTION
                "Enables/Disables flooding of packets with unknown 
                destination address"
            DEFVAL { booleanFalse }
            ::= { asdmaxCustomConfigEntry 81 }

        
        -- 1.3.6.1.4.1.989.1.16.2.4.1.2.5.1.82
        asdmaxCustomReuseGroup OBJECT-TYPE
            SYNTAX INTEGER
                {
                reuseGroupDisabled(0),
                reuseGroupA(1),
                reuseGroupB(2),
                reuseGroupC(3)
                }
            MAX-ACCESS read-write
            STATUS current
            DESCRIPTION
                "Defines the frequency reuse group the BS belongs to"
            DEFVAL { reuseGroupDisabled }
            ::= { asdmaxCustomConfigEntry 82 }

        
        -- 1.3.6.1.4.1.989.1.16.2.4.1.2.5.1.83
        asdmaxCustomActiveEncryptionMode OBJECT-TYPE
            SYNTAX AsdmaxEncryptionMode
            MAX-ACCESS read-only
            STATUS current
            DESCRIPTION
                "Reports the active 'maximum' encryption mode that is allowed by 
                export licence and configured using asdmaxCustomGlobalEncryptionMode."
            ::= { asdmaxCustomConfigEntry 83 }

        
        -- 1.3.6.1.4.1.989.1.16.2.4.1.2.5.1.84
        asdmaxCustomGpsloopShift OBJECT-TYPE
            SYNTAX Integer32
            MAX-ACCESS read-write
            STATUS current
            DESCRIPTION
                "GPS loop shift value in PSs can be negative or positive."
            ::= { asdmaxCustomConfigEntry 84 }

        
        -- 1.3.6.1.4.1.989.1.16.2.4.1.2.5.1.85
        asdmaxCustomActiveRxDiversity OBJECT-TYPE
            SYNTAX INTEGER
                {
                diversityOff(0),
                diversityMrc(1)
                }
            MAX-ACCESS read-only
            STATUS current
            DESCRIPTION
                "The active receive diversity mode.  0 for off, 1 for MRC.
                Reports the mode choosen by BS based on requested mode configured 
                in asdmaxCustomRxDiversity and on availability of operational SCRTs.
                "
            ::= { asdmaxCustomConfigEntry 85 }

        
        -- 1.3.6.1.4.1.989.1.16.2.4.1.2.5.1.86
        asdmaxCustomActiveStcMode OBJECT-TYPE
            SYNTAX INTEGER
                {
                stcNone(0),
                stcMode1(1),
                stcMode2(2),
                delayMode1(3),
                hybridMode1(4),
                hybridMode2(5)
                }
            MAX-ACCESS read-only
            STATUS current
            DESCRIPTION
                "The active transmit diversity mode.
                Reports the mode choosen by BS based on requested mode configured 
                in asdmaxCustomStcMode and on availability of operational SCRTs."
            ::= { asdmaxCustomConfigEntry 86 }

        
        -- 1.3.6.1.4.1.989.1.16.2.4.1.2.5.1.87
        asdmaxCustomScrtRedundancyEnabled OBJECT-TYPE
            SYNTAX AsmaxBooleanSwitch
            MAX-ACCESS read-write
            STATUS current
            DESCRIPTION
                "Enables redundancy proptection mechanizm. 
                When SCRT failure is detected the other SCRT takes over.
                When diversity is provisioned ON and SCRT failure is detected, the diversity 
                is disabled internally until BS is rebooted."
            DEFVAL { booleanFalse }
            ::= { asdmaxCustomConfigEntry 87 }

        
        -- 1.3.6.1.4.1.989.1.16.2.4.1.2.6
        asdmaxProvMcastPollGroupTable OBJECT-TYPE
            SYNTAX SEQUENCE OF AsdmaxProvMcastPollGroupEntry
            MAX-ACCESS not-accessible
            STATUS current
            DESCRIPTION
                "Description."
            ::= { asdmaxCps 6 }

        
        -- 1.3.6.1.4.1.989.1.16.2.4.1.2.6.1
        asdmaxProvMcastPollGroupEntry OBJECT-TYPE
            SYNTAX AsdmaxProvMcastPollGroupEntry
            MAX-ACCESS not-accessible
            STATUS current
            DESCRIPTION
                "Description."
            INDEX { asdmaxProvMcastPollGroupId }
            ::= { asdmaxProvMcastPollGroupTable 1 }

        
        AsdmaxProvMcastPollGroupEntry ::=
            SEQUENCE { 
                asdmaxProvMcastPollGroupId
                    AsmaxPollGroupId,
                asdmaxProvMcastPollGroupToSize
                    INTEGER,
                asdmaxProvMcastPollGroupFrameOffset
                    INTEGER,
                asdmaxProvMcastPollGroupFrameDivisor
                    INTEGER,
                asdmaxProvMcastPollGroupFocused
                    INTEGER,
                asdmaxProvMcastPollGroupRowStatus
                    RowStatus
             }

        -- 1.3.6.1.4.1.989.1.16.2.4.1.2.6.1.1
        asdmaxProvMcastPollGroupId OBJECT-TYPE
            SYNTAX AsmaxPollGroupId
            MAX-ACCESS not-accessible
            STATUS current
            DESCRIPTION
                "The polling group IDs are subject to custom implementation 
                This ID should be unique withing the BS domain.
                BS will created assotiated Multicast Polling CIDs
                mapping to the group identifiers provisioned by NMS.
                The mapping is reported in the table asdmaxMcastPollGroupStatusTable."
            ::= { asdmaxProvMcastPollGroupEntry 1 }

        
        -- 1.3.6.1.4.1.989.1.16.2.4.1.2.6.1.2
        asdmaxProvMcastPollGroupToSize OBJECT-TYPE
            SYNTAX INTEGER (0..65535)
            MAX-ACCESS read-create
            STATUS current
            DESCRIPTION
                "Transmit Opportunity Size for this Multicast Polling Group."
            ::= { asdmaxProvMcastPollGroupEntry 2 }

        
        -- 1.3.6.1.4.1.989.1.16.2.4.1.2.6.1.3
        asdmaxProvMcastPollGroupFrameOffset OBJECT-TYPE
            SYNTAX INTEGER (0..65535)
            MAX-ACCESS read-create
            STATUS current
            DESCRIPTION
                "When the remainder of the frame number divided by the
                divisor equals the offset, a multicast polling opportunity
                is generated."
            ::= { asdmaxProvMcastPollGroupEntry 3 }

        
        -- 1.3.6.1.4.1.989.1.16.2.4.1.2.6.1.4
        asdmaxProvMcastPollGroupFrameDivisor OBJECT-TYPE
            SYNTAX INTEGER (0..65535)
            MAX-ACCESS read-create
            STATUS current
            DESCRIPTION
                "When the remainder of the frame number divided by the
                divisor equals the offset, a multicast polling opportunity
                is generated."
            ::= { asdmaxProvMcastPollGroupEntry 4 }

        
        -- 1.3.6.1.4.1.989.1.16.2.4.1.2.6.1.5
        asdmaxProvMcastPollGroupFocused OBJECT-TYPE
            SYNTAX INTEGER
                {
                asdmaxProvMcastPollGroupFullReq(0),
                asdmaxProvMcastPollGroupFocusedReq(1)
                }
            MAX-ACCESS read-create
            STATUS current
            DESCRIPTION
                "Controls whether a full or focused contention request
                opportunity is created"
            ::= { asdmaxProvMcastPollGroupEntry 5 }

        
        -- 1.3.6.1.4.1.989.1.16.2.4.1.2.6.1.6
        asdmaxProvMcastPollGroupRowStatus OBJECT-TYPE
            SYNTAX RowStatus
            MAX-ACCESS read-create
            STATUS current
            DESCRIPTION
                "Description."
            ::= { asdmaxProvMcastPollGroupEntry 6 }

        
        -- 1.3.6.1.4.1.989.1.16.2.4.1.2.7
        asdmaxMcastPollGroupStatusTable OBJECT-TYPE
            SYNTAX SEQUENCE OF AsdmaxMcastPollGroupStatusEntry
            MAX-ACCESS not-accessible
            STATUS current
            DESCRIPTION
                "This table reports basic status of created connections 
                for Multicast Polling Groups."
            ::= { asdmaxCps 7 }

        
        -- 1.3.6.1.4.1.989.1.16.2.4.1.2.7.1
        asdmaxMcastPollGroupStatusEntry OBJECT-TYPE
            SYNTAX AsdmaxMcastPollGroupStatusEntry
            MAX-ACCESS not-accessible
            STATUS current
            DESCRIPTION
                "Description."
            INDEX { asdmaxProvMcastPollGroupId }
            ::= { asdmaxMcastPollGroupStatusTable 1 }

        
        AsdmaxMcastPollGroupStatusEntry ::=
            SEQUENCE { 
                asdmaxMcastPollGroupStatusCid
                    AsmaxConnectionId
             }

        -- 1.3.6.1.4.1.989.1.16.2.4.1.2.7.1.1
        asdmaxMcastPollGroupStatusCid OBJECT-TYPE
            SYNTAX AsmaxConnectionId
            MAX-ACCESS read-only
            STATUS current
            DESCRIPTION
                "Conenction ID (CID) allocated for the given 
                Multicast Polling Group."
            ::= { asdmaxMcastPollGroupStatusEntry 1 }

        
        -- 1.3.6.1.4.1.989.1.16.2.4.1.2.8
        asdmaxServiceClassStatusTable OBJECT-TYPE
            SYNTAX SEQUENCE OF AsdmaxServiceClassStatusEntry
            MAX-ACCESS not-accessible
            STATUS current
            DESCRIPTION
                "This table contains debugging information reporting status 
                of Service Class managed by BS. It contains a row for each 
                class used in the Service Flow definition no matter 
                whether it is provisioned or not in the table
                wmanIfBsServiceClassTable in the standard MIB.
                "
            ::= { asdmaxCps 8 }

        
        -- 1.3.6.1.4.1.989.1.16.2.4.1.2.8.1
        asdmaxServiceClassStatusEntry OBJECT-TYPE
            SYNTAX AsdmaxServiceClassStatusEntry
            MAX-ACCESS not-accessible
            STATUS current
            DESCRIPTION
                "Description."
            INDEX { wmanIfBsQoSProfileIndex }
            ::= { asdmaxServiceClassStatusTable 1 }

        
        AsdmaxServiceClassStatusEntry ::=
            SEQUENCE { 
                asdmaxServiceClassStatusConfigured
                    INTEGER
             }

        -- 1.3.6.1.4.1.989.1.16.2.4.1.2.8.1.1
        asdmaxServiceClassStatusConfigured OBJECT-TYPE
            SYNTAX INTEGER
                {
                serviceClassNotConfigured(0),
                serviceClassConfigured(1)
                }
            MAX-ACCESS read-only
            STATUS current
            DESCRIPTION
                "Description."
            ::= { asdmaxServiceClassStatusEntry 1 }

        
        -- 1.3.6.1.4.1.989.1.16.2.4.1.2.9
        asdmaxSfStatusTable OBJECT-TYPE
            SYNTAX SEQUENCE OF AsdmaxSfStatusEntry
            MAX-ACCESS not-accessible
            STATUS current
            DESCRIPTION
                "This table contains debugging information reporting status 
                of the Service Flow managed by BS. It contains a row for each 
                Service Flow created. This table effectively extends 
                the table wmanIfCmnCpsServiceFlowTable."
            ::= { asdmaxCps 9 }

        
        -- 1.3.6.1.4.1.989.1.16.2.4.1.2.9.1
        asdmaxSfStatusEntry OBJECT-TYPE
            SYNTAX AsdmaxSfStatusEntry
            MAX-ACCESS not-accessible
            STATUS current
            DESCRIPTION
                "Description."
            INDEX { wmanIfCmnCpsSfId }
            ::= { asdmaxSfStatusTable 1 }

        
        AsdmaxSfStatusEntry ::=
            SEQUENCE { 
                asdmaxSfStatusProvisioned
                    INTEGER
             }

        -- 1.3.6.1.4.1.989.1.16.2.4.1.2.9.1.1
        asdmaxSfStatusProvisioned OBJECT-TYPE
            SYNTAX INTEGER
                {
                sfStatusNotProvisioned(0),
                sfStatusProvisioned(1)
                }
            MAX-ACCESS read-only
            STATUS current
            DESCRIPTION
                "This object indicates whether the Service Flow was 
                provisioned (table wmanIfBsProvisionedSfTable) 
                or not i.e. autonomly created by BS."
            ::= { asdmaxSfStatusEntry 1 }

        
        -- 1.3.6.1.4.1.989.1.16.2.4.1.2.10
        asdmaxServiceClassExtTable OBJECT-TYPE
            SYNTAX SEQUENCE OF AsdmaxServiceClassExtEntry
            MAX-ACCESS not-accessible
            STATUS current
            DESCRIPTION
                "This table contains extensions to the standard MIB's service class table.
                "
            ::= { asdmaxCps 10 }

        
        -- 1.3.6.1.4.1.989.1.16.2.4.1.2.10.1
        asdmaxServiceClassExtEntry OBJECT-TYPE
            SYNTAX AsdmaxServiceClassExtEntry
            MAX-ACCESS not-accessible
            STATUS current
            DESCRIPTION
                "Externally indexed."
            INDEX { wmanIfBsQoSProfileIndex }
            ::= { asdmaxServiceClassExtTable 1 }

        
        AsdmaxServiceClassExtEntry ::=
            SEQUENCE { 
                asdmaxServiceClassExtPollPeriod
                    INTEGER,
                asdmaxServiceClassExtRowStatus
                    RowStatus,
                asdmaxServiceClassExtFlags
                    BITS,
                asdmaxServiceClassExtUplinkVlan
                    AsmaxExtendedVlanId,
                asdmaxServiceClassExtUplinkDSField
                    AsmaxDSFieldValue
             }

        -- 1.3.6.1.4.1.989.1.16.2.4.1.2.10.1.1
        asdmaxServiceClassExtPollPeriod OBJECT-TYPE
            SYNTAX INTEGER (1..60000)
            UNITS "ms"
            MAX-ACCESS read-create
            STATUS current
            DESCRIPTION
                "Poll period (in miliseconds) used by RTPS, nRTPS and UGS (sometimes) to 
                define the grant repetition rate."
            DEFVAL { 1000 }
            ::= { asdmaxServiceClassExtEntry 1 }

        
        -- 1.3.6.1.4.1.989.1.16.2.4.1.2.10.1.2
        asdmaxServiceClassExtRowStatus OBJECT-TYPE
            SYNTAX RowStatus
            MAX-ACCESS read-create
            STATUS current
            DESCRIPTION
                "Description."
            ::= { asdmaxServiceClassExtEntry 2 }

        
        -- 1.3.6.1.4.1.989.1.16.2.4.1.2.10.1.3
        asdmaxServiceClassExtFlags OBJECT-TYPE
            SYNTAX BITS
                {
                serviceClassExtFlagsUplinkVlanValid(0),
                serviceClassExtFlagsUplinkDSFieldValid(1)
                }
            MAX-ACCESS read-create
            STATUS current
            DESCRIPTION
                "This object specifies which other fields of the extended service class configuration
                are used, the bits are as follows:
                serviceClassExtFlagsUplinkVlanValid - When this flag is set the
                  fieldasdmaxServiceClassExtUplinkVlan field is in use.
                serviceClassExtFlagsUplinkDSFieldValid - When this flag is set the
                  asdmaxServiceClassExtUplinkDSField field is in use."
            ::= { asdmaxServiceClassExtEntry 3 }

        
        -- 1.3.6.1.4.1.989.1.16.2.4.1.2.10.1.4
        asdmaxServiceClassExtUplinkVlan OBJECT-TYPE
            SYNTAX AsmaxExtendedVlanId
            MAX-ACCESS read-create
            STATUS current
            DESCRIPTION
                "This object defines the VLAN Id that will be applied to untagged traffic received
                on the uplink."
            ::= { asdmaxServiceClassExtEntry 4 }

        
        -- 1.3.6.1.4.1.989.1.16.2.4.1.2.10.1.5
        asdmaxServiceClassExtUplinkDSField OBJECT-TYPE
            SYNTAX AsmaxDSFieldValue
            MAX-ACCESS read-create
            STATUS current
            DESCRIPTION
                "This object defines the differential service field value that will be applied to
                traffic received on the uplink."
            ::= { asdmaxServiceClassExtEntry 5 }

        
        -- 1.3.6.1.4.1.989.1.16.2.4.1.2.11
        asdmaxBsChannelMeasurementTable OBJECT-TYPE
            SYNTAX SEQUENCE OF AsdmaxBsChannelMeasurementEntry
            MAX-ACCESS not-accessible
            STATUS current
            DESCRIPTION
                "This table contains channel measurement information as
                derived from BS measurement of uplink signal from SS,
                and the downlink signal as reported from SS using
                REP-REQ/RSP messages. The table shall be maintained as
                FIFO to store measurement samples that can be used to
                create RSSI and CINR histogram report. When the
                measurement entry for a SS reaches the limit, the oldest
                entry shall be deleted as the new entry is added to the
                table.
                The table definition was based on table wmanIfBsChannelMeasurementTable
                from Draft6 WMAN-IF-MIB. Draft1 MIB channel measurements table
                should not be used."
            REFERENCE
                "6.3.2.3.33 in IEEE 802.16-2004"
            ::= { asdmaxCps 11 }

        
        -- 1.3.6.1.4.1.989.1.16.2.4.1.2.11.1
        asdmaxBsChannelMeasurementEntry OBJECT-TYPE
            SYNTAX AsdmaxBsChannelMeasurementEntry
            MAX-ACCESS not-accessible
            STATUS current
            DESCRIPTION
                "Each entry in the table contains RSSI and CINR
                signal quality measurement on signal received from the SS.
                The primary index is the ifIndex with ifType of propBWAp2Mp
                identifing the BS sector. wmanIfBsSsMacAddress identifies
                the SS from which the signal was received.
                wmanIfBsChannelDirection is the index to the direction of
                the channel. wmanIfBsHistogramIndex is the index to
                histogram samples. Since there is no time stamp in the
                table, wmanIfBsHistogramIndex should be increased
                monotonically, and wraps around when it reaches the
                implementation specific limit."
            INDEX { ifIndex, asdmaxProvSsMacAddress, asdmaxBsChannelDirection, asdmaxBsHistogramIndex }
            ::= { asdmaxBsChannelMeasurementTable 1 }

        
        AsdmaxBsChannelMeasurementEntry ::=
            SEQUENCE { 
                asdmaxBsChannelDirection
                    INTEGER,
                asdmaxBsHistogramIndex
                    Unsigned32,
                asdmaxBsChannelNumber
                    AsmaxWmanIfChannelNumber,
                asdmaxBsStartFrame
                    INTEGER,
                asdmaxBsDuration
                    INTEGER,
                asdmaxBsBasicReport
                    BITS,
                asdmaxBsMeanCinrReport
                    INTEGER,
                asdmaxBsMeanRssiReport
                    INTEGER,
                asdmaxBsStdDeviationCinrReport
                    INTEGER,
                asdmaxBsStdDeviationRssiReport
                    INTEGER
             }

        -- 1.3.6.1.4.1.989.1.16.2.4.1.2.11.1.1
        asdmaxBsChannelDirection OBJECT-TYPE
            SYNTAX INTEGER
                {
                downstream(1),
                upstream(2)
                }
            MAX-ACCESS not-accessible
            STATUS current
            DESCRIPTION
                "wmanIfBsChannelDirection identifies the direction of a
                a channel where the measurement takes place."
            ::= { asdmaxBsChannelMeasurementEntry 1 }

        
        -- 1.3.6.1.4.1.989.1.16.2.4.1.2.11.1.2
        asdmaxBsHistogramIndex OBJECT-TYPE
            SYNTAX Unsigned32 (1..2147483647)
            MAX-ACCESS read-only
            STATUS current
            DESCRIPTION
                "wmanIfBsHistogramIndex identifies the histogram samples
                in the table for each subscriber station."
            ::= { asdmaxBsChannelMeasurementEntry 2 }

        
        -- 1.3.6.1.4.1.989.1.16.2.4.1.2.11.1.3
        asdmaxBsChannelNumber OBJECT-TYPE
            SYNTAX AsmaxWmanIfChannelNumber
            MAX-ACCESS read-only
            STATUS current
            DESCRIPTION
                "Physical channel number to be reported on is only
                applicable to license exempt band. For licensed band,
                this parameter should be null."
            REFERENCE
                "Subclause 11.12 in IEEE 802.16-2004"
            ::= { asdmaxBsChannelMeasurementEntry 3 }

        
        -- 1.3.6.1.4.1.989.1.16.2.4.1.2.11.1.4
        asdmaxBsStartFrame OBJECT-TYPE
            SYNTAX INTEGER (0..65535)
            MAX-ACCESS read-only
            STATUS current
            DESCRIPTION
                "Frame number in which measurement for this channel
                started."
            REFERENCE
                "Subclause 11.12 in IEEE 802.16-2004"
            ::= { asdmaxBsChannelMeasurementEntry 4 }

        
        -- 1.3.6.1.4.1.989.1.16.2.4.1.2.11.1.5
        asdmaxBsDuration OBJECT-TYPE
            SYNTAX INTEGER (0..16777215)
            MAX-ACCESS read-only
            STATUS current
            DESCRIPTION
                "Cumulative measurement duration on the channel in
                multiples of Ts. For any value exceeding 0xFFFFFF,
                report 0xFFFFFF."
            REFERENCE
                "Subclause 11.12 in IEEE 802.16-2004"
            ::= { asdmaxBsChannelMeasurementEntry 5 }

        
        -- 1.3.6.1.4.1.989.1.16.2.4.1.2.11.1.6
        asdmaxBsBasicReport OBJECT-TYPE
            SYNTAX BITS
                {
                wirelessHuman(0),
                unknownTransmission(1),
                primaryUser(2),
                channelNotMeasured(3)
                }
            MAX-ACCESS read-only
            STATUS current
            DESCRIPTION
                "Bit #0: WirelessHUMAN detected on the channel
                Bit #1: Unknown transmissions detected on the channel
                Bit #2: Primary User detected on the channel
                Bit #3: Unmeasured. Channel not measured"
            REFERENCE
                "Subclause 11.12 in IEEE 802.16-2004"
            ::= { asdmaxBsChannelMeasurementEntry 6 }

        
        -- 1.3.6.1.4.1.989.1.16.2.4.1.2.11.1.7
        asdmaxBsMeanCinrReport OBJECT-TYPE
            SYNTAX INTEGER (0..41)
            UNITS "dB"
            MAX-ACCESS read-only
            STATUS current
            DESCRIPTION
                "Mean CINR report."
            REFERENCE
                "Subclause 8.2.2, 8.3.9 in IEEE 802.16-2004"
            ::= { asdmaxBsChannelMeasurementEntry 7 }

        
        -- 1.3.6.1.4.1.989.1.16.2.4.1.2.11.1.8
        asdmaxBsMeanRssiReport OBJECT-TYPE
            SYNTAX INTEGER (0..83)
            UNITS "dBm"
            MAX-ACCESS read-only
            STATUS current
            DESCRIPTION
                "Mean RSSI report."
            REFERENCE
                "Subclause 8.2.2, 8.3.9 in IEEE 802.16-2004"
            ::= { asdmaxBsChannelMeasurementEntry 8 }

        
        -- 1.3.6.1.4.1.989.1.16.2.4.1.2.11.1.9
        asdmaxBsStdDeviationCinrReport OBJECT-TYPE
            SYNTAX INTEGER (0..41)
            UNITS "dB"
            MAX-ACCESS read-only
            STATUS current
            DESCRIPTION
                "Standard deviation CINR report."
            REFERENCE
                "Subclause 8.2.2, 8.3.9 in IEEE 802.16-2004"
            ::= { asdmaxBsChannelMeasurementEntry 9 }

        
        -- 1.3.6.1.4.1.989.1.16.2.4.1.2.11.1.10
        asdmaxBsStdDeviationRssiReport OBJECT-TYPE
            SYNTAX INTEGER (0..83)
            UNITS "dB"
            MAX-ACCESS read-only
            STATUS current
            DESCRIPTION
                "Standard deviation RSSI report."
            REFERENCE
                "Subclause 8.2.2, 8.3.9 in IEEE 802.16-2004"
            ::= { asdmaxBsChannelMeasurementEntry 10 }

        
        -- 1.3.6.1.4.1.989.1.16.2.4.1.2.12
        asdmaxBsSsModSubChanStatsTable OBJECT-TYPE
            SYNTAX SEQUENCE OF AsdmaxBsSsModSubChanStatsEntry
            MAX-ACCESS not-accessible
            STATUS current
            DESCRIPTION
                "This table contains modulation and sub-channelisation information per SS per Sector.
                It shows distribution of uplink and downlink modulation and uplink sub-channelisation widths.
                Each measurement gives the percentage of recent frames using the particular modulation or 
                sub-channelisation width."
            ::= { asdmaxCps 12 }

        
        -- 1.3.6.1.4.1.989.1.16.2.4.1.2.12.1
        asdmaxBsSsModSubChanStatsEntry OBJECT-TYPE
            SYNTAX AsdmaxBsSsModSubChanStatsEntry
            MAX-ACCESS not-accessible
            STATUS current
            DESCRIPTION
                "Description."
            INDEX { ifIndex, asdmaxProvSsMacAddress }
            ::= { asdmaxBsSsModSubChanStatsTable 1 }

        
        AsdmaxBsSsModSubChanStatsEntry ::=
            SEQUENCE { 
                asdmaxBsSsModSubChanStatsDlModBpsk
                    Integer32,
                asdmaxBsSsModSubChanStatsDlModQpsk12
                    Integer32,
                asdmaxBsSsModSubChanStatsDlModQpsk34
                    Integer32,
                asdmaxBsSsModSubChanStatsDlMod16Qam12
                    Integer32,
                asdmaxBsSsModSubChanStatsDlMod16Qam34
                    Integer32,
                asdmaxBsSsModSubChanStatsDlMod64Qam23
                    Integer32,
                asdmaxBsSsModSubChanStatsDlMod64Qam34
                    Integer32,
                asdmaxBsSsModSubChanStatsUlModBpsk
                    Integer32,
                asdmaxBsSsModSubChanStatsUlModQpsk12
                    Integer32,
                asdmaxBsSsModSubChanStatsUlModQpsk34
                    Integer32,
                asdmaxBsSsModSubChanStatsUlMod16Qam12
                    Integer32,
                asdmaxBsSsModSubChanStatsUlMod16Qam34
                    Integer32,
                asdmaxBsSsModSubChanStatsUlMod64Qam23
                    Integer32,
                asdmaxBsSsModSubChanStatsUlMod64Qam34
                    Integer32,
                asdmaxBsSsModSubChanStatsUlScwSixteenth
                    Integer32,
                asdmaxBsSsModSubChanStatsUlScwEighth
                    Integer32,
                asdmaxBsSsModSubChanStatsUlScwQuarter
                    Integer32,
                asdmaxBsSsModSubChanStatsUlScwHalf
                    Integer32,
                asdmaxBsSsModSubChanStatsUlScwFull
                    Integer32
             }

        -- 1.3.6.1.4.1.989.1.16.2.4.1.2.12.1.1
        asdmaxBsSsModSubChanStatsDlModBpsk OBJECT-TYPE
            SYNTAX Integer32 (0..100)
            MAX-ACCESS read-only
            STATUS current
            DESCRIPTION
                "Percentage of downlink frames using BPSK modulation.
                "
            ::= { asdmaxBsSsModSubChanStatsEntry 1 }

        
        -- 1.3.6.1.4.1.989.1.16.2.4.1.2.12.1.2
        asdmaxBsSsModSubChanStatsDlModQpsk12 OBJECT-TYPE
            SYNTAX Integer32 (0..100)
            MAX-ACCESS read-only
            STATUS current
            DESCRIPTION
                "Percentage of downlink frames using QPSK 1/2 modulation."
            ::= { asdmaxBsSsModSubChanStatsEntry 2 }

        
        -- 1.3.6.1.4.1.989.1.16.2.4.1.2.12.1.3
        asdmaxBsSsModSubChanStatsDlModQpsk34 OBJECT-TYPE
            SYNTAX Integer32 (0..100)
            MAX-ACCESS read-only
            STATUS current
            DESCRIPTION
                "Percentage of downlink frames using QPSK 3/4 modulation."
            ::= { asdmaxBsSsModSubChanStatsEntry 3 }

        
        -- 1.3.6.1.4.1.989.1.16.2.4.1.2.12.1.4
        asdmaxBsSsModSubChanStatsDlMod16Qam12 OBJECT-TYPE
            SYNTAX Integer32 (0..100)
            MAX-ACCESS read-only
            STATUS current
            DESCRIPTION
                "Percentage of downlink frames using 16 QAM 1/2 modulation."
            ::= { asdmaxBsSsModSubChanStatsEntry 4 }

        
        -- 1.3.6.1.4.1.989.1.16.2.4.1.2.12.1.5
        asdmaxBsSsModSubChanStatsDlMod16Qam34 OBJECT-TYPE
            SYNTAX Integer32 (0..100)
            MAX-ACCESS read-only
            STATUS current
            DESCRIPTION
                "Percentage of downlink frames using 16 QAM 3/4 modulation."
            ::= { asdmaxBsSsModSubChanStatsEntry 5 }

        
        -- 1.3.6.1.4.1.989.1.16.2.4.1.2.12.1.6
        asdmaxBsSsModSubChanStatsDlMod64Qam23 OBJECT-TYPE
            SYNTAX Integer32 (0..100)
            MAX-ACCESS read-only
            STATUS current
            DESCRIPTION
                "Percentage of downlink frames using 64 QAM 2/3 modulation."
            ::= { asdmaxBsSsModSubChanStatsEntry 6 }

        
        -- 1.3.6.1.4.1.989.1.16.2.4.1.2.12.1.7
        asdmaxBsSsModSubChanStatsDlMod64Qam34 OBJECT-TYPE
            SYNTAX Integer32 (0..100)
            MAX-ACCESS read-only
            STATUS current
            DESCRIPTION
                "Percentage of downlink frames using 64 QAM 3/4 modulation."
            ::= { asdmaxBsSsModSubChanStatsEntry 7 }

        
        -- 1.3.6.1.4.1.989.1.16.2.4.1.2.12.1.8
        asdmaxBsSsModSubChanStatsUlModBpsk OBJECT-TYPE
            SYNTAX Integer32 (0..100)
            MAX-ACCESS read-only
            STATUS current
            DESCRIPTION
                "Percentage of uplink frames using BPSK modulation.
                "
            ::= { asdmaxBsSsModSubChanStatsEntry 8 }

        
        -- 1.3.6.1.4.1.989.1.16.2.4.1.2.12.1.9
        asdmaxBsSsModSubChanStatsUlModQpsk12 OBJECT-TYPE
            SYNTAX Integer32 (0..100)
            MAX-ACCESS read-only
            STATUS current
            DESCRIPTION
                "Percentage of uplink frames using QPSK 1/2 modulation."
            ::= { asdmaxBsSsModSubChanStatsEntry 9 }

        
        -- 1.3.6.1.4.1.989.1.16.2.4.1.2.12.1.10
        asdmaxBsSsModSubChanStatsUlModQpsk34 OBJECT-TYPE
            SYNTAX Integer32 (0..100)
            MAX-ACCESS read-only
            STATUS current
            DESCRIPTION
                "Percentage of uplink frames using QPSK 3/4 modulation."
            ::= { asdmaxBsSsModSubChanStatsEntry 10 }

        
        -- 1.3.6.1.4.1.989.1.16.2.4.1.2.12.1.11
        asdmaxBsSsModSubChanStatsUlMod16Qam12 OBJECT-TYPE
            SYNTAX Integer32 (0..100)
            MAX-ACCESS read-only
            STATUS current
            DESCRIPTION
                "Percentage of uplink frames using 16 QAM 1/2 modulation."
            ::= { asdmaxBsSsModSubChanStatsEntry 11 }

        
        -- 1.3.6.1.4.1.989.1.16.2.4.1.2.12.1.12
        asdmaxBsSsModSubChanStatsUlMod16Qam34 OBJECT-TYPE
            SYNTAX Integer32 (0..100)
            MAX-ACCESS read-only
            STATUS current
            DESCRIPTION
                "Percentage of uplink frames using 16 QAM 3/4 modulation."
            ::= { asdmaxBsSsModSubChanStatsEntry 12 }

        
        -- 1.3.6.1.4.1.989.1.16.2.4.1.2.12.1.13
        asdmaxBsSsModSubChanStatsUlMod64Qam23 OBJECT-TYPE
            SYNTAX Integer32 (0..100)
            MAX-ACCESS read-only
            STATUS current
            DESCRIPTION
                "Percentage of uplink frames using 64 QAM 2/3 modulation."
            ::= { asdmaxBsSsModSubChanStatsEntry 13 }

        
        -- 1.3.6.1.4.1.989.1.16.2.4.1.2.12.1.14
        asdmaxBsSsModSubChanStatsUlMod64Qam34 OBJECT-TYPE
            SYNTAX Integer32 (0..100)
            MAX-ACCESS read-only
            STATUS current
            DESCRIPTION
                "Percentage of uplink frames using 64 QAM 3/4 modulation."
            ::= { asdmaxBsSsModSubChanStatsEntry 14 }

        
        -- 1.3.6.1.4.1.989.1.16.2.4.1.2.12.1.15
        asdmaxBsSsModSubChanStatsUlScwSixteenth OBJECT-TYPE
            SYNTAX Integer32 (0..100)
            MAX-ACCESS read-only
            STATUS current
            DESCRIPTION
                "Percentage of uplink frames using 1/16 sub-channelisation width."
            ::= { asdmaxBsSsModSubChanStatsEntry 15 }

        
        -- 1.3.6.1.4.1.989.1.16.2.4.1.2.12.1.16
        asdmaxBsSsModSubChanStatsUlScwEighth OBJECT-TYPE
            SYNTAX Integer32 (0..100)
            MAX-ACCESS read-only
            STATUS current
            DESCRIPTION
                "Percentage of uplink frames using 1/8 sub-channelisation width."
            ::= { asdmaxBsSsModSubChanStatsEntry 16 }

        
        -- 1.3.6.1.4.1.989.1.16.2.4.1.2.12.1.17
        asdmaxBsSsModSubChanStatsUlScwQuarter OBJECT-TYPE
            SYNTAX Integer32 (0..100)
            MAX-ACCESS read-only
            STATUS current
            DESCRIPTION
                "Percentage of uplink frames using 1/4 sub-channelisation width."
            ::= { asdmaxBsSsModSubChanStatsEntry 17 }

        
        -- 1.3.6.1.4.1.989.1.16.2.4.1.2.12.1.18
        asdmaxBsSsModSubChanStatsUlScwHalf OBJECT-TYPE
            SYNTAX Integer32 (0..100)
            MAX-ACCESS read-only
            STATUS current
            DESCRIPTION
                "Percentage of uplink frames using 1/2 sub-channelisation width."
            ::= { asdmaxBsSsModSubChanStatsEntry 18 }

        
        -- 1.3.6.1.4.1.989.1.16.2.4.1.2.12.1.19
        asdmaxBsSsModSubChanStatsUlScwFull OBJECT-TYPE
            SYNTAX Integer32 (0..100)
            MAX-ACCESS read-only
            STATUS current
            DESCRIPTION
                "Percentage of uplink frames using no sub-channelisation."
            ::= { asdmaxBsSsModSubChanStatsEntry 19 }

        
        -- 1.3.6.1.4.1.989.1.16.2.4.1.2.13
        asdmaxBsSsPacketCounterTable OBJECT-TYPE
            SYNTAX SEQUENCE OF AsdmaxBsSsPacketCounterEntry
            MAX-ACCESS not-accessible
            STATUS current
            DESCRIPTION
                "This table contains SS traffic count information.
                There is one row for every SS registered with BS.
                This table effectively extends the table wmanIfBsRegisteredSsTable.
                The objects in this table are for statistical purposes."
            ::= { asdmaxCps 13 }

        
        -- 1.3.6.1.4.1.989.1.16.2.4.1.2.13.1
        asdmaxBsSsPacketCounterEntry OBJECT-TYPE
            SYNTAX AsdmaxBsSsPacketCounterEntry
            MAX-ACCESS not-accessible
            STATUS current
            DESCRIPTION
                "Description."
            INDEX { asdmaxProvSsMacAddress }
            ::= { asdmaxBsSsPacketCounterTable 1 }

        
        AsdmaxBsSsPacketCounterEntry ::=
            SEQUENCE { 
                asdmaxBsSsUlBasicSduCount
                    Counter64,
                asdmaxBsSsDlBasicSduCount
                    Counter64,
                asdmaxBsSsUlPrimarySduCount
                    Counter64,
                asdmaxBsSsDlPrimarySduCount
                    Counter64,
                asdmaxBsSsUlSecondarySduCount
                    Counter64,
                asdmaxBsSsDlSecondarySduCount
                    Counter64,
                asdmaxBsSsUplinkSduCount
                    Counter64,
                asdmaxBsSsDownlinkSduCount
                    Counter64,
                asdmaxBsSsUlBasicOctetCount
                    Counter64,
                asdmaxBsSsDlBasicOctetCount
                    Counter64,
                asdmaxBsSsUlPrimaryOctetCount
                    Counter64,
                asdmaxBsSsDlPrimaryOctetCount
                    Counter64,
                asdmaxBsSsUlSecondaryOctetCount
                    Counter64,
                asdmaxBsSsDlSecondaryOctetCount
                    Counter64,
                asdmaxBsSsUplinkOctetCount
                    Counter64,
                asdmaxBsSsDownlinkOctetCount
                    Counter64
             }

        -- 1.3.6.1.4.1.989.1.16.2.4.1.2.13.1.1
        asdmaxBsSsUlBasicSduCount OBJECT-TYPE
            SYNTAX Counter64
            MAX-ACCESS read-only
            STATUS current
            DESCRIPTION
                "SDU count on SS basic management uplink (to BS) connection."
            ::= { asdmaxBsSsPacketCounterEntry 1 }

        
        -- 1.3.6.1.4.1.989.1.16.2.4.1.2.13.1.2
        asdmaxBsSsDlBasicSduCount OBJECT-TYPE
            SYNTAX Counter64
            MAX-ACCESS read-only
            STATUS current
            DESCRIPTION
                "SDU count on SS basic management downlink (from BS) connection."
            ::= { asdmaxBsSsPacketCounterEntry 2 }

        
        -- 1.3.6.1.4.1.989.1.16.2.4.1.2.13.1.3
        asdmaxBsSsUlPrimarySduCount OBJECT-TYPE
            SYNTAX Counter64
            MAX-ACCESS read-only
            STATUS current
            DESCRIPTION
                "SDU count on SS primary management uplink (to BS) connection."
            ::= { asdmaxBsSsPacketCounterEntry 3 }

        
        -- 1.3.6.1.4.1.989.1.16.2.4.1.2.13.1.4
        asdmaxBsSsDlPrimarySduCount OBJECT-TYPE
            SYNTAX Counter64
            MAX-ACCESS read-only
            STATUS current
            DESCRIPTION
                "SDU count on SS primary management downlink (from BS) connection."
            ::= { asdmaxBsSsPacketCounterEntry 4 }

        
        -- 1.3.6.1.4.1.989.1.16.2.4.1.2.13.1.5
        asdmaxBsSsUlSecondarySduCount OBJECT-TYPE
            SYNTAX Counter64
            MAX-ACCESS read-only
            STATUS current
            DESCRIPTION
                "SDU count on SS secondary management uplink (to BS) connection."
            ::= { asdmaxBsSsPacketCounterEntry 5 }

        
        -- 1.3.6.1.4.1.989.1.16.2.4.1.2.13.1.6
        asdmaxBsSsDlSecondarySduCount OBJECT-TYPE
            SYNTAX Counter64
            MAX-ACCESS read-only
            STATUS current
            DESCRIPTION
                "SDU count on SS secondary management downlink (from BS) connection."
            ::= { asdmaxBsSsPacketCounterEntry 6 }

        
        -- 1.3.6.1.4.1.989.1.16.2.4.1.2.13.1.7
        asdmaxBsSsUplinkSduCount OBJECT-TYPE
            SYNTAX Counter64
            MAX-ACCESS read-only
            STATUS current
            DESCRIPTION
                "SDU count on SS uplink (to BS) connection.
                This does not include management traffic."
            ::= { asdmaxBsSsPacketCounterEntry 7 }

        
        -- 1.3.6.1.4.1.989.1.16.2.4.1.2.13.1.8
        asdmaxBsSsDownlinkSduCount OBJECT-TYPE
            SYNTAX Counter64
            MAX-ACCESS read-only
            STATUS current
            DESCRIPTION
                "SDU count on SS downlink (from BS) connection.
                This reports only unicast and not broadcast/multicast or management traffic."
            ::= { asdmaxBsSsPacketCounterEntry 8 }

        
        -- 1.3.6.1.4.1.989.1.16.2.4.1.2.13.1.9
        asdmaxBsSsUlBasicOctetCount OBJECT-TYPE
            SYNTAX Counter64
            MAX-ACCESS read-only
            STATUS current
            DESCRIPTION
                "Octet count on SS basic management uplink (to BS) connection."
            ::= { asdmaxBsSsPacketCounterEntry 9 }

        
        -- 1.3.6.1.4.1.989.1.16.2.4.1.2.13.1.10
        asdmaxBsSsDlBasicOctetCount OBJECT-TYPE
            SYNTAX Counter64
            MAX-ACCESS read-only
            STATUS current
            DESCRIPTION
                "Octet count on SS basic management downlink (from BS) connection."
            ::= { asdmaxBsSsPacketCounterEntry 10 }

        
        -- 1.3.6.1.4.1.989.1.16.2.4.1.2.13.1.11
        asdmaxBsSsUlPrimaryOctetCount OBJECT-TYPE
            SYNTAX Counter64
            MAX-ACCESS read-only
            STATUS current
            DESCRIPTION
                "Octet count on SS primary management uplink (to BS) connection."
            ::= { asdmaxBsSsPacketCounterEntry 11 }

        
        -- 1.3.6.1.4.1.989.1.16.2.4.1.2.13.1.12
        asdmaxBsSsDlPrimaryOctetCount OBJECT-TYPE
            SYNTAX Counter64
            MAX-ACCESS read-only
            STATUS current
            DESCRIPTION
                "Octet count on SS primary management downlink (from BS) connection."
            ::= { asdmaxBsSsPacketCounterEntry 12 }

        
        -- 1.3.6.1.4.1.989.1.16.2.4.1.2.13.1.13
        asdmaxBsSsUlSecondaryOctetCount OBJECT-TYPE
            SYNTAX Counter64
            MAX-ACCESS read-only
            STATUS current
            DESCRIPTION
                "Octet count on SS secondary management uplink (to BS) connection."
            ::= { asdmaxBsSsPacketCounterEntry 13 }

        
        -- 1.3.6.1.4.1.989.1.16.2.4.1.2.13.1.14
        asdmaxBsSsDlSecondaryOctetCount OBJECT-TYPE
            SYNTAX Counter64
            MAX-ACCESS read-only
            STATUS current
            DESCRIPTION
                "Octet count on SS secondary management downlink (from BS) connection."
            ::= { asdmaxBsSsPacketCounterEntry 14 }

        
        -- 1.3.6.1.4.1.989.1.16.2.4.1.2.13.1.15
        asdmaxBsSsUplinkOctetCount OBJECT-TYPE
            SYNTAX Counter64
            MAX-ACCESS read-only
            STATUS current
            DESCRIPTION
                "Octet count on SS uplink (to BS) connection.
                This does not include management traffic."
            ::= { asdmaxBsSsPacketCounterEntry 15 }

        
        -- 1.3.6.1.4.1.989.1.16.2.4.1.2.13.1.16
        asdmaxBsSsDownlinkOctetCount OBJECT-TYPE
            SYNTAX Counter64
            MAX-ACCESS read-only
            STATUS current
            DESCRIPTION
                "Octet count on SS downlink (from BS) connection.
                This reports only unicast and not broadcast/multicast or management traffic."
            ::= { asdmaxBsSsPacketCounterEntry 16 }

        
        -- 1.3.6.1.4.1.989.1.16.2.4.1.2.14
        asdmaxBsIfStatsTable OBJECT-TYPE
            SYNTAX SEQUENCE OF AsdmaxBsIfStatsEntry
            MAX-ACCESS not-accessible
            STATUS current
            DESCRIPTION
                "This table contains uplink and downlink frame usage per interface.
                It contains downlink broadcast SDU and Octet counts as well."
            ::= { asdmaxCps 14 }

        
        -- 1.3.6.1.4.1.989.1.16.2.4.1.2.14.1
        asdmaxBsIfStatsEntry OBJECT-TYPE
            SYNTAX AsdmaxBsIfStatsEntry
            MAX-ACCESS not-accessible
            STATUS current
            DESCRIPTION
                "Description."
            INDEX { ifIndex }
            ::= { asdmaxBsIfStatsTable 1 }

        
        AsdmaxBsIfStatsEntry ::=
            SEQUENCE { 
                asdmaxBsIfDlFrameOverhead
                    Integer32,
                asdmaxBsIfDlFrameDataModBpsk
                    Integer32,
                asdmaxBsIfDlFrameDataModQpsk12
                    Integer32,
                asdmaxBsIfDlFrameDataModQpsk34
                    Integer32,
                asdmaxBsIfDlFrameDataMod16Qam12
                    Integer32,
                asdmaxBsIfDlFrameDataMod16Qam34
                    Integer32,
                asdmaxBsIfDlFrameDataMod64Qam23
                    Integer32,
                asdmaxBsIfDlFrameDataMod64Qam34
                    Integer32,
                asdmaxBsIfDlFrameAvailable
                    Integer32,
                asdmaxBsIfDlFrameContention
                    Integer32,
                asdmaxBsIfUlFrameOverhead
                    Integer32,
                asdmaxBsIfUlFrameDataModBpsk
                    Integer32,
                asdmaxBsIfUlFrameDataModQpsk12
                    Integer32,
                asdmaxBsIfUlFrameDataModQpsk34
                    Integer32,
                asdmaxBsIfUlFrameDataMod16Qam12
                    Integer32,
                asdmaxBsIfUlFrameDataMod16Qam34
                    Integer32,
                asdmaxBsIfUlFrameDataMod64Qam23
                    Integer32,
                asdmaxBsIfUlFrameDataMod64Qam34
                    Integer32,
                asdmaxBsIfUlFrameAvailable
                    Integer32,
                asdmaxBsIfUlFrameContention
                    Integer32,
                asdmaxBsIfUlFrameSize
                    Integer32,
                asdmaxBsIfBroadcastSduCount
                    Counter64,
                asdmaxBsIfBroadcastOctetCount
                    Counter64
             }

        -- 1.3.6.1.4.1.989.1.16.2.4.1.2.14.1.1
        asdmaxBsIfDlFrameOverhead OBJECT-TYPE
            SYNTAX Integer32 (0..100)
            MAX-ACCESS read-only
            STATUS current
            DESCRIPTION
                "The proportion of the downlink subframe that is used but does not carry user data
                - this includes the FCH, DLMAP, ULMAP, DCD, UCD, any preambles used on the downlink bursts, and any frame gaps.
                Note that it does not include PDUs that contain management messages
                - these are considered to be user data for frame usage purposes."
            ::= { asdmaxBsIfStatsEntry 1 }

        
        -- 1.3.6.1.4.1.989.1.16.2.4.1.2.14.1.2
        asdmaxBsIfDlFrameDataModBpsk OBJECT-TYPE
            SYNTAX Integer32 (0..100)
            MAX-ACCESS read-only
            STATUS current
            DESCRIPTION
                "Percentage of downlink frames using BPSK modulation."
            ::= { asdmaxBsIfStatsEntry 2 }

        
        -- 1.3.6.1.4.1.989.1.16.2.4.1.2.14.1.3
        asdmaxBsIfDlFrameDataModQpsk12 OBJECT-TYPE
            SYNTAX Integer32 (0..100)
            MAX-ACCESS read-only
            STATUS current
            DESCRIPTION
                "Percentage of downlink frames using QPSK 1/2 modulation."
            ::= { asdmaxBsIfStatsEntry 3 }

        
        -- 1.3.6.1.4.1.989.1.16.2.4.1.2.14.1.4
        asdmaxBsIfDlFrameDataModQpsk34 OBJECT-TYPE
            SYNTAX Integer32 (0..100)
            MAX-ACCESS read-only
            STATUS current
            DESCRIPTION
                "Percentage of downlink frames using QPSK 3/4 modulation."
            ::= { asdmaxBsIfStatsEntry 4 }

        
        -- 1.3.6.1.4.1.989.1.16.2.4.1.2.14.1.5
        asdmaxBsIfDlFrameDataMod16Qam12 OBJECT-TYPE
            SYNTAX Integer32 (0..100)
            MAX-ACCESS read-only
            STATUS current
            DESCRIPTION
                "Percentage of downlink frames using 16 QAM 1/2 modulation."
            ::= { asdmaxBsIfStatsEntry 5 }

        
        -- 1.3.6.1.4.1.989.1.16.2.4.1.2.14.1.6
        asdmaxBsIfDlFrameDataMod16Qam34 OBJECT-TYPE
            SYNTAX Integer32 (0..100)
            MAX-ACCESS read-only
            STATUS current
            DESCRIPTION
                "Percentage of downlink frames using 16 QAM 3/4 modulation."
            ::= { asdmaxBsIfStatsEntry 6 }

        
        -- 1.3.6.1.4.1.989.1.16.2.4.1.2.14.1.7
        asdmaxBsIfDlFrameDataMod64Qam23 OBJECT-TYPE
            SYNTAX Integer32 (0..100)
            MAX-ACCESS read-only
            STATUS current
            DESCRIPTION
                "Percentage of downlink frames using 64 QAM 2/3 modulation."
            ::= { asdmaxBsIfStatsEntry 7 }

        
        -- 1.3.6.1.4.1.989.1.16.2.4.1.2.14.1.8
        asdmaxBsIfDlFrameDataMod64Qam34 OBJECT-TYPE
            SYNTAX Integer32 (0..100)
            MAX-ACCESS read-only
            STATUS current
            DESCRIPTION
                "Percentage of downlink frames using 64 QAM 3/4 modulation."
            ::= { asdmaxBsIfStatsEntry 8 }

        
        -- 1.3.6.1.4.1.989.1.16.2.4.1.2.14.1.9
        asdmaxBsIfDlFrameAvailable OBJECT-TYPE
            SYNTAX Integer32 (0..100)
            MAX-ACCESS read-only
            STATUS current
            DESCRIPTION
                "The proportion of the downlink subframe that is unused (empty).
                "
            ::= { asdmaxBsIfStatsEntry 9 }

        
        -- 1.3.6.1.4.1.989.1.16.2.4.1.2.14.1.10
        asdmaxBsIfDlFrameContention OBJECT-TYPE
            SYNTAX Integer32 (0..100)
            MAX-ACCESS read-only
            STATUS current
            DESCRIPTION
                "The proportion of the downlink subframe that coincides with the uplink contention regions.
                The BS does not transmit in these regions so they are effectively occupied for downlink purposes.
                "
            ::= { asdmaxBsIfStatsEntry 10 }

        
        -- 1.3.6.1.4.1.989.1.16.2.4.1.2.14.1.11
        asdmaxBsIfUlFrameOverhead OBJECT-TYPE
            SYNTAX Integer32 (0..100)
            MAX-ACCESS read-only
            STATUS current
            DESCRIPTION
                "The proportion of the uplink subframe that is used but does not carry any data.
                - this is total of all preambles used on the uplink SS transmissions bursts, 
                plus any allocations made for non-data purposes (e.g. ranging).
                "
            ::= { asdmaxBsIfStatsEntry 11 }

        
        -- 1.3.6.1.4.1.989.1.16.2.4.1.2.14.1.12
        asdmaxBsIfUlFrameDataModBpsk OBJECT-TYPE
            SYNTAX Integer32 (0..100)
            MAX-ACCESS read-only
            STATUS current
            DESCRIPTION
                "Percentage of uplink frames using BPSK modulation.
                "
            ::= { asdmaxBsIfStatsEntry 12 }

        
        -- 1.3.6.1.4.1.989.1.16.2.4.1.2.14.1.13
        asdmaxBsIfUlFrameDataModQpsk12 OBJECT-TYPE
            SYNTAX Integer32 (0..100)
            MAX-ACCESS read-only
            STATUS current
            DESCRIPTION
                "Percentage of uplink frames using QPSK 1/2 modulation."
            ::= { asdmaxBsIfStatsEntry 13 }

        
        -- 1.3.6.1.4.1.989.1.16.2.4.1.2.14.1.14
        asdmaxBsIfUlFrameDataModQpsk34 OBJECT-TYPE
            SYNTAX Integer32 (0..100)
            MAX-ACCESS read-only
            STATUS current
            DESCRIPTION
                "Percentage of uplink frames using QPSK 3/4 modulation."
            ::= { asdmaxBsIfStatsEntry 14 }

        
        -- 1.3.6.1.4.1.989.1.16.2.4.1.2.14.1.15
        asdmaxBsIfUlFrameDataMod16Qam12 OBJECT-TYPE
            SYNTAX Integer32 (0..100)
            MAX-ACCESS read-only
            STATUS current
            DESCRIPTION
                "Percentage of uplink frames using 16 QAM 1/2 modulation."
            ::= { asdmaxBsIfStatsEntry 15 }

        
        -- 1.3.6.1.4.1.989.1.16.2.4.1.2.14.1.16
        asdmaxBsIfUlFrameDataMod16Qam34 OBJECT-TYPE
            SYNTAX Integer32 (0..100)
            MAX-ACCESS read-only
            STATUS current
            DESCRIPTION
                "Percentage of uplink frames using 16 QAM 3/4 modulation."
            ::= { asdmaxBsIfStatsEntry 16 }

        
        -- 1.3.6.1.4.1.989.1.16.2.4.1.2.14.1.17
        asdmaxBsIfUlFrameDataMod64Qam23 OBJECT-TYPE
            SYNTAX Integer32 (0..100)
            MAX-ACCESS read-only
            STATUS current
            DESCRIPTION
                "Percentage of uplink frames using 64 QAM 2/3 modulation."
            ::= { asdmaxBsIfStatsEntry 17 }

        
        -- 1.3.6.1.4.1.989.1.16.2.4.1.2.14.1.18
        asdmaxBsIfUlFrameDataMod64Qam34 OBJECT-TYPE
            SYNTAX Integer32 (0..100)
            MAX-ACCESS read-only
            STATUS current
            DESCRIPTION
                "Percentage of uplink frames using 64 QAM 3/4 modulation."
            ::= { asdmaxBsIfStatsEntry 18 }

        
        -- 1.3.6.1.4.1.989.1.16.2.4.1.2.14.1.19
        asdmaxBsIfUlFrameAvailable OBJECT-TYPE
            SYNTAX Integer32 (0..100)
            MAX-ACCESS read-only
            STATUS current
            DESCRIPTION
                "The proportion of the uplink subframe that is unused (empty).
                
                
                "
            ::= { asdmaxBsIfStatsEntry 19 }

        
        -- 1.3.6.1.4.1.989.1.16.2.4.1.2.14.1.20
        asdmaxBsIfUlFrameContention OBJECT-TYPE
            SYNTAX Integer32 (0..100)
            MAX-ACCESS read-only
            STATUS current
            DESCRIPTION
                "The proportion of the uplink subframe that is used for contention regions.
                "
            ::= { asdmaxBsIfStatsEntry 20 }

        
        -- 1.3.6.1.4.1.989.1.16.2.4.1.2.14.1.21
        asdmaxBsIfUlFrameSize OBJECT-TYPE
            SYNTAX Integer32 (0..100)
            MAX-ACCESS read-only
            STATUS current
            DESCRIPTION
                "The proportion of the whole frame period that the uplink subframe occupies.
                "
            ::= { asdmaxBsIfStatsEntry 21 }

        
        -- 1.3.6.1.4.1.989.1.16.2.4.1.2.14.1.22
        asdmaxBsIfBroadcastSduCount OBJECT-TYPE
            SYNTAX Counter64
            MAX-ACCESS read-only
            STATUS current
            DESCRIPTION
                "Downlink broadcast SDU count."
            ::= { asdmaxBsIfStatsEntry 22 }

        
        -- 1.3.6.1.4.1.989.1.16.2.4.1.2.14.1.23
        asdmaxBsIfBroadcastOctetCount OBJECT-TYPE
            SYNTAX Counter64
            MAX-ACCESS read-only
            STATUS current
            DESCRIPTION
                "Downlink broadcast octet count."
            ::= { asdmaxBsIfStatsEntry 23 }

        
        -- 1.3.6.1.4.1.989.1.16.2.4.1.2.15
        asdmaxCmnCpsServiceFlowTable OBJECT-TYPE
            SYNTAX SEQUENCE OF AsdmaxCmnCpsServiceFlowEntry
            MAX-ACCESS not-accessible
            STATUS current
            DESCRIPTION
                "This table contains Service Flow managed objects that
                are common in BS and SS.
                This is based on wmanIfCmnCpsServiceFlowTable from the Draft6 standard MIB."
            ::= { asdmaxCps 15 }

        
        -- 1.3.6.1.4.1.989.1.16.2.4.1.2.15.1
        asdmaxCmnCpsServiceFlowEntry OBJECT-TYPE
            SYNTAX AsdmaxCmnCpsServiceFlowEntry
            MAX-ACCESS not-accessible
            STATUS current
            DESCRIPTION
                "This table provides one row for each created service
                flow for a given MacAddress, and is doubly indexed by
                (asdmaxCmnCpsSfMacAddress, asdmaxCmnCpsSfId)"
            INDEX { ifIndex, asdmaxCmnCpsSfMacAddress, asdmaxCmnCpsSfId }
            ::= { asdmaxCmnCpsServiceFlowTable 1 }

        
        AsdmaxCmnCpsServiceFlowEntry ::=
            SEQUENCE { 
                asdmaxCmnCpsSfMacAddress
                    VariableMacAddress,
                asdmaxCmnCpsSfId
                    Unsigned32,
                asdmaxCmnCpsSfCid
                    AsmaxWmanIfCidType,
                asdmaxCmnCpsSfDirection
                    INTEGER,
                asdmaxCmnCpsSfState
                    AsmaxWmanIfSfState,
                asdmaxCmnCpsTrafficPriority
                    INTEGER,
                asdmaxCmnCpsMaxSustainedRate
                    Unsigned32,
                asdmaxCmnCpsMaxTrafficBurst
                    Unsigned32,
                asdmaxCmnCpsMinReservedRate
                    Unsigned32,
                asdmaxCmnCpsToleratedJitter
                    Unsigned32,
                asdmaxCmnCpsMaxLatency
                    Unsigned32,
                asdmaxCmnCpsFixedVsVariableSduInd
                    INTEGER,
                asdmaxCmnCpsSduSize
                    Unsigned32,
                asdmaxCmnCpsSfSchedulingType
                    WmanIfSfSchedulingType,
                asdmaxCmnCpsArqEnable
                    TruthValue,
                asdmaxCmnCpsArqWindowSize
                    INTEGER,
                asdmaxCmnCpsArqBlockLifetime
                    INTEGER,
                asdmaxCmnCpsArqSyncLossTimeout
                    INTEGER,
                asdmaxCmnCpsArqDeliverInOrder
                    TruthValue,
                asdmaxCmnCpsArqRxPurgeTimeout
                    INTEGER,
                asdmaxCmnCpsArqBlockSize
                    INTEGER,
                asdmaxCmnCpsMinRsvdTolerableRate
                    Unsigned32,
                asdmaxCmnCpsReqTxPolicy
                    BITS,
                asdmaxCmnSfCsSpecification
                    AsmaxWmanIfCsSpecification,
                asdmaxCmnCpsTargetSaid
                    INTEGER
             }

        -- 1.3.6.1.4.1.989.1.16.2.4.1.2.15.1.1
        asdmaxCmnCpsSfMacAddress OBJECT-TYPE
            SYNTAX VariableMacAddress
            MAX-ACCESS not-accessible
            STATUS current
            DESCRIPTION
                "This object contains the SS Mac address, the reported service
                flow was created for."
            ::= { asdmaxCmnCpsServiceFlowEntry 1 }

        
        -- 1.3.6.1.4.1.989.1.16.2.4.1.2.15.1.2
        asdmaxCmnCpsSfId OBJECT-TYPE
            SYNTAX Unsigned32 (1..2147483647)
            MAX-ACCESS read-only
            STATUS current
            DESCRIPTION
                "A 32 bit quantity that uniquely identifies a service flow
                to both the subscriber station and base station (BS)."
            ::= { asdmaxCmnCpsServiceFlowEntry 2 }

        
        -- 1.3.6.1.4.1.989.1.16.2.4.1.2.15.1.3
        asdmaxCmnCpsSfCid OBJECT-TYPE
            SYNTAX AsmaxWmanIfCidType
            MAX-ACCESS read-only
            STATUS current
            DESCRIPTION
                "A 16 bit channel identifier to identify the connection
                being created by DSA."
            ::= { asdmaxCmnCpsServiceFlowEntry 3 }

        
        -- 1.3.6.1.4.1.989.1.16.2.4.1.2.15.1.4
        asdmaxCmnCpsSfDirection OBJECT-TYPE
            SYNTAX INTEGER
                {
                downstream(1),
                upstream(2)
                }
            MAX-ACCESS read-only
            STATUS current
            DESCRIPTION
                "An attribute indicating the service flow is downstream or
                upstream."
            ::= { asdmaxCmnCpsServiceFlowEntry 4 }

        
        -- 1.3.6.1.4.1.989.1.16.2.4.1.2.15.1.5
        asdmaxCmnCpsSfState OBJECT-TYPE
            SYNTAX AsmaxWmanIfSfState
            MAX-ACCESS read-only
            STATUS current
            DESCRIPTION
                "asdmaxCmnCpsSfState indicates the service flow state:
                Authorized (1), Admitted (2), and Active (3) service
                flow state."
            REFERENCE
                "Subclause 6.3.14.6, in IEEE 802.16-2004"
            ::= { asdmaxCmnCpsServiceFlowEntry 5 }

        
        -- 1.3.6.1.4.1.989.1.16.2.4.1.2.15.1.6
        asdmaxCmnCpsTrafficPriority OBJECT-TYPE
            SYNTAX INTEGER (0..7)
            MAX-ACCESS read-only
            STATUS current
            DESCRIPTION
                "The value of this parameter specifies the priority
                assigned to a service flow. For uplink service flows,
                the BS should use this parameter when determining
                precedence in request service and grant generation,
                and the SS shall preferentially select contention
                Request opportunities for Priority Request CIDs
                based on this priority"
            REFERENCE
                "Subclause 11.13.5 in IEEE 802.16-2004"
            ::= { asdmaxCmnCpsServiceFlowEntry 6 }

        
        -- 1.3.6.1.4.1.989.1.16.2.4.1.2.15.1.7
        asdmaxCmnCpsMaxSustainedRate OBJECT-TYPE
            SYNTAX Unsigned32
            UNITS "b/s"
            MAX-ACCESS read-only
            STATUS current
            DESCRIPTION
                "This parameter defines the peak information rate
                of the service. The rate is expressed in bits per
                second and pertains to the SDUs at the input to
                the system."
            REFERENCE
                "Subclause 11.13.6 in IEEE 802.16-2004"
            ::= { asdmaxCmnCpsServiceFlowEntry 7 }

        
        -- 1.3.6.1.4.1.989.1.16.2.4.1.2.15.1.8
        asdmaxCmnCpsMaxTrafficBurst OBJECT-TYPE
            SYNTAX Unsigned32
            UNITS "byte"
            MAX-ACCESS read-only
            STATUS current
            DESCRIPTION
                "This parameter defines the maximum burst size that
                must be accommodated for the service."
            REFERENCE
                "Subclause 11.13.7 in IEEE 802.16-2004"
            ::= { asdmaxCmnCpsServiceFlowEntry 8 }

        
        -- 1.3.6.1.4.1.989.1.16.2.4.1.2.15.1.9
        asdmaxCmnCpsMinReservedRate OBJECT-TYPE
            SYNTAX Unsigned32
            UNITS "byte"
            MAX-ACCESS read-only
            STATUS current
            DESCRIPTION
                "This parameter specifies the minimum rate reserved
                for this service flow."
            REFERENCE
                "Subclause 11.13.8 in IEEE 802.16-2004"
            ::= { asdmaxCmnCpsServiceFlowEntry 9 }

        
        -- 1.3.6.1.4.1.989.1.16.2.4.1.2.15.1.10
        asdmaxCmnCpsToleratedJitter OBJECT-TYPE
            SYNTAX Unsigned32
            UNITS "millisecond"
            MAX-ACCESS read-only
            STATUS current
            DESCRIPTION
                "This parameter defines the Maximum delay 
                variation (jitter) for the connection."
            REFERENCE
                "Subclause 11.13.13 in IEEE 802.16-2004"
            ::= { asdmaxCmnCpsServiceFlowEntry 10 }

        
        -- 1.3.6.1.4.1.989.1.16.2.4.1.2.15.1.11
        asdmaxCmnCpsMaxLatency OBJECT-TYPE
            SYNTAX Unsigned32
            UNITS "millisecond"
            MAX-ACCESS read-only
            STATUS current
            DESCRIPTION
                "The value of this parameter specifies the maximum
                latency between the reception of a packet by the BS
                or SS on its network interface and the forwarding
                of the packet to its RF Interface."
            REFERENCE
                "Subclause 11.13.14 in IEEE 802.16-2004"
            ::= { asdmaxCmnCpsServiceFlowEntry 11 }

        
        -- 1.3.6.1.4.1.989.1.16.2.4.1.2.15.1.12
        asdmaxCmnCpsFixedVsVariableSduInd OBJECT-TYPE
            SYNTAX INTEGER
                {
                variableLength(0),
                fixedLength(1)
                }
            MAX-ACCESS read-only
            STATUS current
            DESCRIPTION
                "The value of this parameter specifies whether the SDUs
                on the service flow are variable-length (0) or 
                fixed-length (1). The parameter is used only if
                packing is on for the service flow. The default value
                is 0, i.e.,variable-length SDUs."
            REFERENCE
                "Subclause 11.13.15 in IEEE 802.16-2004"
            DEFVAL { variableLength }
            ::= { asdmaxCmnCpsServiceFlowEntry 12 }

        
        -- 1.3.6.1.4.1.989.1.16.2.4.1.2.15.1.13
        asdmaxCmnCpsSduSize OBJECT-TYPE
            SYNTAX Unsigned32
            UNITS "byte"
            MAX-ACCESS read-only
            STATUS current
            DESCRIPTION
                "The value of this parameter specifies the length of the
                SDU for a fixed-length SDU service flow. This parameter
                is used only if packing is on and the service flow is
                indicated as carrying fixed-length SDUs. The default
                value is 49 bytes, i.e., VC-switched ATM cells with PHS.
                The parameter is relevant for both ATM and Packet
                Convergence Sublayers."
            REFERENCE
                "Subclause 11.13.16 in IEEE 802.16-2004"
            DEFVAL { 49 }
            ::= { asdmaxCmnCpsServiceFlowEntry 13 }

        
        -- 1.3.6.1.4.1.989.1.16.2.4.1.2.15.1.14
        asdmaxCmnCpsSfSchedulingType OBJECT-TYPE
            SYNTAX WmanIfSfSchedulingType
            MAX-ACCESS read-only
            STATUS current
            DESCRIPTION
                "Specifies the upstream scheduling service used for
                upstream service flow. If the referenced parameter
                is not present in the corresponding 802.16 QOS
                Parameter Set of an upstream service flow, the
                default value of this object is bestEffort(2)."
            REFERENCE
                "Subclause 11.13.11 in IEEE 802.16-2004"
            DEFVAL { bestEffort }
            ::= { asdmaxCmnCpsServiceFlowEntry 14 }

        
        -- 1.3.6.1.4.1.989.1.16.2.4.1.2.15.1.15
        asdmaxCmnCpsArqEnable OBJECT-TYPE
            SYNTAX TruthValue
            MAX-ACCESS read-only
            STATUS current
            DESCRIPTION
                "True(1) ARQ enabling is requested for the connection."
            ::= { asdmaxCmnCpsServiceFlowEntry 15 }

        
        -- 1.3.6.1.4.1.989.1.16.2.4.1.2.15.1.16
        asdmaxCmnCpsArqWindowSize OBJECT-TYPE
            SYNTAX INTEGER (1..1024)
            MAX-ACCESS read-only
            STATUS current
            DESCRIPTION
                "Indicates the maximum number of unacknowledged 
                fragments at any time."
            ::= { asdmaxCmnCpsServiceFlowEntry 16 }

        
        -- 1.3.6.1.4.1.989.1.16.2.4.1.2.15.1.17
        asdmaxCmnCpsArqBlockLifetime OBJECT-TYPE
            SYNTAX INTEGER (0..65535)
            UNITS "10 us"
            MAX-ACCESS read-only
            STATUS current
            DESCRIPTION
                "The maximum time interval an ARQ fragment will be
                managed by the transmitter ARQ machine, once
                initial transmission of the fragment has occured.
                If transmission or retransmission of the fragment
                is not acknowledged by the receiver before the 
                time limit is reached, the fragment is discarded.
                A value of 0 means Infinite."
            ::= { asdmaxCmnCpsServiceFlowEntry 17 }

        
        -- 1.3.6.1.4.1.989.1.16.2.4.1.2.15.1.18
        asdmaxCmnCpsArqSyncLossTimeout OBJECT-TYPE
            SYNTAX INTEGER (0..65535)
            UNITS "10 us"
            MAX-ACCESS read-only
            STATUS current
            DESCRIPTION
                "The maximum interval before declaring a loss
                of synchronization of the sender and receiver
                state machines. A value of 0 means Infinite."
            ::= { asdmaxCmnCpsServiceFlowEntry 18 }

        
        -- 1.3.6.1.4.1.989.1.16.2.4.1.2.15.1.19
        asdmaxCmnCpsArqDeliverInOrder OBJECT-TYPE
            SYNTAX TruthValue
            MAX-ACCESS read-only
            STATUS current
            DESCRIPTION
                "Indicates whether or not data is to be delivered
                by the receiving MAC to its client application
                in the order in which data was handed off to the
                originating MAC."
            ::= { asdmaxCmnCpsServiceFlowEntry 19 }

        
        -- 1.3.6.1.4.1.989.1.16.2.4.1.2.15.1.20
        asdmaxCmnCpsArqRxPurgeTimeout OBJECT-TYPE
            SYNTAX INTEGER (0..65535)
            UNITS "10 us"
            MAX-ACCESS read-only
            STATUS current
            DESCRIPTION
                "Indicates the time interval the ARQ window is advanced
                after a fragment is received. A value of 0 means
                Infinite."
            ::= { asdmaxCmnCpsServiceFlowEntry 20 }

        
        -- 1.3.6.1.4.1.989.1.16.2.4.1.2.15.1.21
        asdmaxCmnCpsArqBlockSize OBJECT-TYPE
            SYNTAX INTEGER (1..2040)
            UNITS "byte"
            MAX-ACCESS read-only
            STATUS current
            DESCRIPTION
                "This value of this parameter specifies the size of an
                ARQ block. This parameter shall be established by
                negotiation during the connection creation dialog."
            REFERENCE
                "Subclause 11.13.18.8 in IEEE 802.16-2004"
            ::= { asdmaxCmnCpsServiceFlowEntry 21 }

        
        -- 1.3.6.1.4.1.989.1.16.2.4.1.2.15.1.22
        asdmaxCmnCpsMinRsvdTolerableRate OBJECT-TYPE
            SYNTAX Unsigned32
            UNITS "b/s"
            MAX-ACCESS read-only
            STATUS current
            DESCRIPTION
                "Minimum Tolerable Traffic Rate = R (bits/sec) with
                time base T(sec) means the following. Let S denote
                additional demand accumulated at the MAC SAP of the
                transmitter during an arbitrary time interval of the
                length T. Then the amount of data forwarded at the
                receiver to CS (in bits) during this interval should
                be not less than min {S, R * T}."
            REFERENCE
                "Subclause 11.13.9 in IEEE 802.16-2004"
            ::= { asdmaxCmnCpsServiceFlowEntry 22 }

        
        -- 1.3.6.1.4.1.989.1.16.2.4.1.2.15.1.23
        asdmaxCmnCpsReqTxPolicy OBJECT-TYPE
            SYNTAX BITS
                {
                noBroadcastBwReq(0),
                reserved1(1),
                noPiggybackReq(2),
                noFragmentData(3),
                noPHS(4),
                noSduPacking(5),
                noCrc(6),
                reserved2(7)
                }
            MAX-ACCESS read-only
            STATUS current
            DESCRIPTION
                "The value of this parameter provides the capability to
                specify certain attributes for the associated service
                flow. An attribute is enabled by setting the
                corresponding bit position to 1."
            REFERENCE
                "Subclause 11.13.12 in IEEE 802.16-2004"
            ::= { asdmaxCmnCpsServiceFlowEntry 23 }

        
        -- 1.3.6.1.4.1.989.1.16.2.4.1.2.15.1.24
        asdmaxCmnSfCsSpecification OBJECT-TYPE
            SYNTAX AsmaxWmanIfCsSpecification
            MAX-ACCESS read-only
            STATUS current
            DESCRIPTION
                "This parameter specifies the convergence sublayer
                encapsulation mode."
            REFERENCE
                "Subclause 11.13.19.1 in IEEE 802.16-2004"
            ::= { asdmaxCmnCpsServiceFlowEntry 24 }

        
        -- 1.3.6.1.4.1.989.1.16.2.4.1.2.15.1.25
        asdmaxCmnCpsTargetSaid OBJECT-TYPE
            SYNTAX INTEGER (0..65535)
            MAX-ACCESS read-only
            STATUS current
            DESCRIPTION
                "The target SAID parameter indicates the SAID onto
                which the service flow being set up shall be mapped."
            REFERENCE
                "Subclause 11.13.17 in IEEE 802.16-2004"
            ::= { asdmaxCmnCpsServiceFlowEntry 25 }

        
        -- 1.3.6.1.4.1.989.1.16.2.4.1.2.16
        asdmaxBsQPortTable OBJECT-TYPE
            SYNTAX SEQUENCE OF AsdmaxBsQPortEntry
            MAX-ACCESS not-accessible
            STATUS current
            DESCRIPTION
                "Configures operation of the Q bridge for BS port."
            ::= { asdmaxCps 16 }

        
        -- 1.3.6.1.4.1.989.1.16.2.4.1.2.16.1
        asdmaxBsQPortEntry OBJECT-TYPE
            SYNTAX AsdmaxBsQPortEntry
            MAX-ACCESS not-accessible
            STATUS current
            DESCRIPTION
                "Description."
            INDEX { asdmaxBsQPortIndex }
            ::= { asdmaxBsQPortTable 1 }

        
        AsdmaxBsQPortEntry ::=
            SEQUENCE { 
                asdmaxBsQPortIndex
                    INTEGER,
                asdmaxBsQPortMode
                    AsdmaxQPortMode,
                asdmaxBsQPvid
                    AsmaxExtendedVlanIdOrNone,
                asdmaxBsQIngressFilterEnabled
                    AsmaxBooleanSwitch,
                asdmaxBsQFrameTypes
                    AsdmaxQAllowedFrameTypes,
                asdmaxBsQDefaultPriority
                    Integer32
             }

        -- 1.3.6.1.4.1.989.1.16.2.4.1.2.16.1.1
        asdmaxBsQPortIndex OBJECT-TYPE
            SYNTAX INTEGER (1)
            MAX-ACCESS not-accessible
            STATUS current
            DESCRIPTION
                "Arbitrary index to the table with one row only."
            ::= { asdmaxBsQPortEntry 1 }

        
        -- 1.3.6.1.4.1.989.1.16.2.4.1.2.16.1.2
        asdmaxBsQPortMode OBJECT-TYPE
            SYNTAX AsdmaxQPortMode
            MAX-ACCESS read-write
            STATUS current
            DESCRIPTION
                "Configures standard (portModeVlan) behaviour or non standard 
                behaviour of the port (portModeRaw).
                In mode portModeRaw all port configuration and port Vlan list 
                are ignored. The traffic is allow to flow in and out unfiltered 
                and without changes to tagging."
            DEFVAL { portModeRaw }
            ::= { asdmaxBsQPortEntry 2 }

        
        -- 1.3.6.1.4.1.989.1.16.2.4.1.2.16.1.3
        asdmaxBsQPvid OBJECT-TYPE
            SYNTAX AsmaxExtendedVlanIdOrNone
            MAX-ACCESS read-write
            STATUS current
            DESCRIPTION
                "Extended port VID defined as follows:
                -values 1..4094 are used for standard PVID behaviour
                -values 0 (none) is used when only tagged frames are processed
                -value 4096 is used for backwards compatibility with older bridge implementations."
            DEFVAL { 0 }
            ::= { asdmaxBsQPortEntry 3 }

        
        -- 1.3.6.1.4.1.989.1.16.2.4.1.2.16.1.4
        asdmaxBsQIngressFilterEnabled OBJECT-TYPE
            SYNTAX AsmaxBooleanSwitch
            MAX-ACCESS read-write
            STATUS current
            DESCRIPTION
                "When disabled the frames arriving from the port (ingress) 
                are accepted regardles on the tag.
                When enabled the tags are checekd against port vlan list."
            DEFVAL { booleanTrue }
            ::= { asdmaxBsQPortEntry 4 }

        
        -- 1.3.6.1.4.1.989.1.16.2.4.1.2.16.1.5
        asdmaxBsQFrameTypes OBJECT-TYPE
            SYNTAX AsdmaxQAllowedFrameTypes
            MAX-ACCESS read-write
            STATUS current
            DESCRIPTION
                "Defines in general what frame types are allowed on ingress:
                all, tagged only or untagged only.
                For tagged only Pvid should be set to 0."
            DEFVAL { admitAll }
            ::= { asdmaxBsQPortEntry 5 }

        
        -- 1.3.6.1.4.1.989.1.16.2.4.1.2.16.1.6
        asdmaxBsQDefaultPriority OBJECT-TYPE
            SYNTAX Integer32 (0..7)
            MAX-ACCESS read-write
            STATUS current
            DESCRIPTION
                "Priority applied to VLAN tag for untagged framed 
                where PVID is used."
            DEFVAL { 0 }
            ::= { asdmaxBsQPortEntry 6 }

        
        -- 1.3.6.1.4.1.989.1.16.2.4.1.3
        asdmaxPkm OBJECT IDENTIFIER ::= { asdmaxMibObjects 3 }

        
        -- 1.3.6.1.4.1.989.1.16.2.4.1.3.1
        asdmaxPkmConfigTable OBJECT-TYPE
            SYNTAX SEQUENCE OF AsdmaxPkmConfigEntry
            MAX-ACCESS not-accessible
            STATUS current
            DESCRIPTION
                "This table contains the basic PKM configuration of the BS.
                The table is liley to be created for standard MIB 
                - here until standard MIB updated."
            ::= { asdmaxPkm 1 }

        
        -- 1.3.6.1.4.1.989.1.16.2.4.1.3.1.1
        asdmaxPkmConfigEntry OBJECT-TYPE
            SYNTAX AsdmaxPkmConfigEntry
            MAX-ACCESS not-accessible
            STATUS current
            DESCRIPTION
                "One row per BS sector."
            INDEX { ifIndex }
            ::= { asdmaxPkmConfigTable 1 }

        
        AsdmaxPkmConfigEntry ::=
            SEQUENCE { 
                asdmaxPkmConfigAuthGraceTime
                    Integer32,
                asdmaxPkmConfigTEKGraceTime
                    Integer32,
                asdmaxPkmConfigAuthWaitTimeout
                    Integer32,
                asdmaxPkmConfigReauthWaitTimeout
                    Integer32,
                asdmaxPkmConfigOpWaitTimeout
                    Integer32,
                asdmaxPkmConfigRekeyWaitTimeout
                    Integer32,
                asdmaxPkmConfigAuthRejectWaitTimeout
                    Integer32
             }

        -- 1.3.6.1.4.1.989.1.16.2.4.1.3.1.1.1
        asdmaxPkmConfigAuthGraceTime OBJECT-TYPE
            SYNTAX Integer32 (300..3024000)
            UNITS "seconds"
            MAX-ACCESS read-write
            STATUS current
            DESCRIPTION
                "The value of this object is the grace time for an
                authorization key.  A SS is expected to start trying to get
                a new authorization key beginning AuthGraceTime seconds
                before the authorization key actually expires."
            REFERENCE
                "Table 341 in IEEE 802.16REVd/D5-2004"
            DEFVAL { 600 }
            ::= { asdmaxPkmConfigEntry 1 }

        
        -- 1.3.6.1.4.1.989.1.16.2.4.1.3.1.1.2
        asdmaxPkmConfigTEKGraceTime OBJECT-TYPE
            SYNTAX Integer32 (300..3024000)
            UNITS "seconds"
            MAX-ACCESS read-write
            STATUS current
            DESCRIPTION
                "The value of this object is the grace time for the TEK in
                seconds. The SS is expected to start trying to acquire a
                new TEK beginning TEK GraceTime seconds before the
                expiration of the most recent TEK."
            REFERENCE
                "Table 341 in IEEE 802.16REVd/D5-2004"
            DEFVAL { 3600 }
            ::= { asdmaxPkmConfigEntry 2 }

        
        -- 1.3.6.1.4.1.989.1.16.2.4.1.3.1.1.3
        asdmaxPkmConfigAuthWaitTimeout OBJECT-TYPE
            SYNTAX Integer32 (2..30)
            UNITS "seconds"
            MAX-ACCESS read-write
            STATUS current
            DESCRIPTION
                "The value of this object is the Authorize Wait Timeout."
            REFERENCE
                "Table 341 in IEEE 802.16REVd/D5-2004"
            DEFVAL { 10 }
            ::= { asdmaxPkmConfigEntry 3 }

        
        -- 1.3.6.1.4.1.989.1.16.2.4.1.3.1.1.4
        asdmaxPkmConfigReauthWaitTimeout OBJECT-TYPE
            SYNTAX Integer32 (2..30)
            UNITS "seconds"
            MAX-ACCESS read-write
            STATUS current
            DESCRIPTION
                "The value of this object is the Reauthorize Wait Timeout
                in seconds."
            REFERENCE
                "Table 341 in IEEE 802.16REVd/D5-2004"
            DEFVAL { 10 }
            ::= { asdmaxPkmConfigEntry 4 }

        
        -- 1.3.6.1.4.1.989.1.16.2.4.1.3.1.1.5
        asdmaxPkmConfigOpWaitTimeout OBJECT-TYPE
            SYNTAX Integer32 (1..10)
            UNITS "seconds"
            MAX-ACCESS read-write
            STATUS current
            DESCRIPTION
                "The value of this object is the Operational Wait Timeout
                in seconds."
            REFERENCE
                "Table 341 in IEEE 802.16REVd/D5-2004"
            DEFVAL { 1 }
            ::= { asdmaxPkmConfigEntry 5 }

        
        -- 1.3.6.1.4.1.989.1.16.2.4.1.3.1.1.6
        asdmaxPkmConfigRekeyWaitTimeout OBJECT-TYPE
            SYNTAX Integer32 (1..10)
            UNITS "seconds"
            MAX-ACCESS read-write
            STATUS current
            DESCRIPTION
                "The value of this object is the Rekey Wait Timeout in
                seconds."
            REFERENCE
                "Table 341 in IEEE 802.16REVd/D5-2004"
            DEFVAL { 1 }
            ::= { asdmaxPkmConfigEntry 6 }

        
        -- 1.3.6.1.4.1.989.1.16.2.4.1.3.1.1.7
        asdmaxPkmConfigAuthRejectWaitTimeout OBJECT-TYPE
            SYNTAX Integer32 (10..600)
            UNITS "seconds"
            MAX-ACCESS read-write
            STATUS current
            DESCRIPTION
                "The value of this object is the Authorization Reject Wait
                Timeout in seconds."
            REFERENCE
                "Table 341 in IEEE 802.16REVd/D5-2004"
            DEFVAL { 60 }
            ::= { asdmaxPkmConfigEntry 7 }

        
        -- 1.3.6.1.4.1.989.1.16.2.4.1.4
        asdmaxNotification OBJECT IDENTIFIER ::= { asdmaxMibObjects 4 }

        
        -- 1.3.6.1.4.1.989.1.16.2.4.1.4.0
        asdmaxTrapPrefix OBJECT IDENTIFIER ::= { asdmaxNotification 0 }

        
        -- 1.3.6.1.4.1.989.1.16.2.4.1.4.0.1
        asdmaxCarrierSenseTrap NOTIFICATION-TYPE
            OBJECTS { ifIndex, asdmaxCarrierSenseStatus, asdmaxCarrierSenseCountStatus, asdmaxCarrierSenseTrapInfo }
            STATUS current
            DESCRIPTION 
                "Indicates that interfering Radio Signal was detected or no longer detected 
                When the interference is detected it may prevent reliable operation of BS.
                If this occurs continuously investigation to locate source of interferer 
                is required.
                Default severity: Major."
            ::= { asdmaxTrapPrefix 1 }

        
        -- 1.3.6.1.4.1.989.1.16.2.4.1.4.0.2
        asdmaxCarrierSenseFreqChangeTrap NOTIFICATION-TYPE
            OBJECTS { ifIndex, asdmaxCarrierSenseFreqChangeTrapInfo }
            STATUS current
            DESCRIPTION 
                "Raised to indicate that BS changed the carrier frequency to avoid 
                the interference."
            ::= { asdmaxTrapPrefix 2 }

        
        -- 1.3.6.1.4.1.989.1.16.2.4.1.4.0.3
        asdmax1ppsFrameLockTrap NOTIFICATION-TYPE
            OBJECTS { ifIndex, asdmax1ppsFrameLockStatus, asdmax1ppsClockDetected }
            STATUS current
            DESCRIPTION 
                "Trap Signifies that BS has lost/recovered timing lock with external (GPS) 
                timing source. If lock lost the BS will cease to transmit depending 
                on setting the of asdmaxTimingSourceControl.
                Default severity: Critical."
            ::= { asdmaxTrapPrefix 3 }

        
        -- 1.3.6.1.4.1.989.1.16.2.4.1.4.0.4
        asdmaxObsaiLinkTrap NOTIFICATION-TYPE
            OBJECTS { ifIndex, asdmaxObsaiLinkStatus, asdmaxObsaiLinkStatusInfo }
            STATUS current
            DESCRIPTION 
                "OBSAI link between SDR and SCRT link carry signalling and data traffic 
                has failed. If problem persists check optical cable connection.
                Default severity: Critical."
            ::= { asdmaxTrapPrefix 4 }

        
        -- 1.3.6.1.4.1.989.1.16.2.4.1.4.0.5
        asdmaxRfTransceiverFaultTrap NOTIFICATION-TYPE
            OBJECTS { ifIndex, asdmaxRfTransceiverFaultStatus, asdmaxRfTransceiverFaultStatusInfo }
            STATUS current
            DESCRIPTION 
                "Signifies that BS transmitter has bee disabled due to detection of a fault 
                indicated by ScrtRfTransceiverStatus object.
                Default Severity : Critical."
            ::= { asdmaxTrapPrefix 5 }

        
        -- 1.3.6.1.4.1.989.1.16.2.4.1.4.0.6
        asdmaxSsStatusChangedTrap NOTIFICATION-TYPE
            OBJECTS { asdmaxSsTrapStatusSsMacAddress, asdmaxSsStatusHwRevision, asdmaxSsStatusSwVersion, asdmaxSsStatusIpAddrType, asdmaxSsStatusIpAddr, 
                asdmaxSsStatusWiFiApIpAddrType, asdmaxSsStatusWiFiApIpAddress, asdmaxSsStatusWiFiApMacAddress, asdmaxSsStatusEasyVoiceIpAddrType, asdmaxSsStatusEasyVoiceIpAddress, 
                asdmaxSsStatusEasyVoiceMacAddress }
            STATUS current
            DESCRIPTION 
                "BS shall send this trap each time any of the critical to NMS operation
                status parameters changes: SW version, IP and MAC addresses of SS itself,
                WiFi AP and EasyVoice."
            ::= { asdmaxTrapPrefix 6 }

        
        -- 1.3.6.1.4.1.989.1.16.2.4.1.4.0.7
        asdmaxSsEventTrap NOTIFICATION-TYPE
            OBJECTS { asdmaxSsTrapStatusSsMacAddress, asdmaxSsTrapStatusSsEvent }
            STATUS current
            DESCRIPTION 
                "Trap to be sent by BS when an event is received from SS via TLV."
            ::= { asdmaxTrapPrefix 7 }

        
        -- 1.3.6.1.4.1.989.1.16.2.4.1.4.0.8
        asdmaxLicenceCertInvalidTrap NOTIFICATION-TYPE
            OBJECTS { asdmaxLicenceCertInvalid }
            STATUS current
            DESCRIPTION 
                "Trap sent to indicate a chane of the licence certification validity state.
                i.e. sent when the invalid certificate was first decoded (alarm raise)
                and when valid certificate replaced invalid one (clear)."
            ::= { asdmaxTrapPrefix 8 }

        
        -- 1.3.6.1.4.1.989.1.16.2.4.1.4.0.9
        asdmaxCarrierSenseV2Trap NOTIFICATION-TYPE
            OBJECTS { ifIndex, asdmaxCarrierSenseStatusV2, asdmaxCarrierSenseTrapInfo }
            STATUS current
            DESCRIPTION 
                "Indicates that interfering Radio Signal was frequently detected (high interference), 
                infrequently detected (low interference) or not detected at all. 
                When the interference is detected it may prevent reliable operation of BS.
                If this occurs continuously investigation to locate source of interferer 
                is required.
                Default severity: Major for frequent detection and Minor for infrequent detection."
            ::= { asdmaxTrapPrefix 9 }

        
        -- 1.3.6.1.4.1.989.1.16.2.4.1.4.0.10
        asdmaxRfPathStatusChangeTrap NOTIFICATION-TYPE
            OBJECTS { ifIndex, asdmaxRfPathStatus, asdmaxRfPathStatusBits, asdmaxRfPathStatusInfo }
            STATUS current
            DESCRIPTION 
                "Reports the change of the combined status of available RF paths 
                (physically associated with SCRTs).
                Used to generate alarm in NMS."
            ::= { asdmaxTrapPrefix 10 }

        
        -- 1.3.6.1.4.1.989.1.16.2.4.1.4.1
        asdmaxTrapControlTable OBJECT-TYPE
            SYNTAX SEQUENCE OF AsdmaxTrapControlEntry
            MAX-ACCESS not-accessible
            STATUS current
            DESCRIPTION
                "Defines enabled/disabled controls foreach traps independently. 
                The traps are enabled/disabled simulanously across the whole all sectors of BS."
            ::= { asdmaxNotification 1 }

        
        -- 1.3.6.1.4.1.989.1.16.2.4.1.4.1.1
        asdmaxTrapControlEntry OBJECT-TYPE
            SYNTAX AsdmaxTrapControlEntry
            MAX-ACCESS not-accessible
            STATUS current
            DESCRIPTION
                "Single row."
            INDEX { asdmaxTrapControlIndex }
            ::= { asdmaxTrapControlTable 1 }

        
        AsdmaxTrapControlEntry ::=
            SEQUENCE { 
                asdmaxTrapControlIndex
                    INTEGER,
                asdmaxCarrierSenseTrapEnabled
                    AsmaxBooleanSwitch,
                asdmaxCarrierSenseFreqChangeTrapEnabled
                    AsmaxBooleanSwitch,
                asdmax1ppsFrameLockTrapEnabled
                    AsmaxBooleanSwitch,
                asdmaxObsaiLinkTrapEnabled
                    AsmaxBooleanSwitch,
                asdmaxRfTransceiverFaultTrapEnabled
                    AsmaxBooleanSwitch,
                asdmaxCarrierSenseV2TrapEnabled
                    AsmaxBooleanSwitch,
                asdmaxRfPathStatusChangeTrapEnabled
                    AsmaxBooleanSwitch
             }

        -- 1.3.6.1.4.1.989.1.16.2.4.1.4.1.1.1
        asdmaxTrapControlIndex OBJECT-TYPE
            SYNTAX INTEGER (1)
            MAX-ACCESS not-accessible
            STATUS current
            DESCRIPTION
                "Arbitrary index - one row only."
            ::= { asdmaxTrapControlEntry 1 }

        
        -- 1.3.6.1.4.1.989.1.16.2.4.1.4.1.1.2
        asdmaxCarrierSenseTrapEnabled OBJECT-TYPE
            SYNTAX AsmaxBooleanSwitch
            MAX-ACCESS read-write
            STATUS current
            DESCRIPTION
                "Enables/disables asdmaxCarrierSenseTrap."
            DEFVAL { booleanTrue }
            ::= { asdmaxTrapControlEntry 2 }

        
        -- 1.3.6.1.4.1.989.1.16.2.4.1.4.1.1.3
        asdmaxCarrierSenseFreqChangeTrapEnabled OBJECT-TYPE
            SYNTAX AsmaxBooleanSwitch
            MAX-ACCESS read-write
            STATUS current
            DESCRIPTION
                "Enables/disables asdmaxCarrierSenseFreqChangeTrap."
            DEFVAL { booleanTrue }
            ::= { asdmaxTrapControlEntry 3 }

        
        -- 1.3.6.1.4.1.989.1.16.2.4.1.4.1.1.4
        asdmax1ppsFrameLockTrapEnabled OBJECT-TYPE
            SYNTAX AsmaxBooleanSwitch
            MAX-ACCESS read-write
            STATUS current
            DESCRIPTION
                "Enables/Disables 1ppsFrameLockTrap."
            DEFVAL { booleanTrue }
            ::= { asdmaxTrapControlEntry 4 }

        
        -- 1.3.6.1.4.1.989.1.16.2.4.1.4.1.1.5
        asdmaxObsaiLinkTrapEnabled OBJECT-TYPE
            SYNTAX AsmaxBooleanSwitch
            MAX-ACCESS read-write
            STATUS current
            DESCRIPTION
                "Enables/disables ObsaiLinkTrap"
            DEFVAL { booleanTrue }
            ::= { asdmaxTrapControlEntry 5 }

        
        -- 1.3.6.1.4.1.989.1.16.2.4.1.4.1.1.6
        asdmaxRfTransceiverFaultTrapEnabled OBJECT-TYPE
            SYNTAX AsmaxBooleanSwitch
            MAX-ACCESS read-write
            STATUS current
            DESCRIPTION
                "Enables/disables RfTransceiverFaultTrap"
            DEFVAL { booleanTrue }
            ::= { asdmaxTrapControlEntry 6 }

        
        -- 1.3.6.1.4.1.989.1.16.2.4.1.4.1.1.7
        asdmaxCarrierSenseV2TrapEnabled OBJECT-TYPE
            SYNTAX AsmaxBooleanSwitch
            MAX-ACCESS read-write
            STATUS current
            DESCRIPTION
                "Enables/disables asdmaxCarrierSenseV2Trap."
            DEFVAL { booleanTrue }
            ::= { asdmaxTrapControlEntry 7 }

        
        -- 1.3.6.1.4.1.989.1.16.2.4.1.4.1.1.8
        asdmaxRfPathStatusChangeTrapEnabled OBJECT-TYPE
            SYNTAX AsmaxBooleanSwitch
            MAX-ACCESS read-write
            STATUS current
            DESCRIPTION
                "Enables/disabled asdmaxRfPathStatusChangeTrap"
            DEFVAL { booleanTrue }
            ::= { asdmaxTrapControlEntry 8 }

        
        -- 1.3.6.1.4.1.989.1.16.2.4.1.4.2
        asdmaxTrapStatusTable OBJECT-TYPE
            SYNTAX SEQUENCE OF AsdmaxTrapStatusEntry
            MAX-ACCESS not-accessible
            STATUS current
            DESCRIPTION
                "Reports current status of objects associated with traps."
            ::= { asdmaxNotification 2 }

        
        -- 1.3.6.1.4.1.989.1.16.2.4.1.4.2.1
        asdmaxTrapStatusEntry OBJECT-TYPE
            SYNTAX AsdmaxTrapStatusEntry
            MAX-ACCESS not-accessible
            STATUS current
            DESCRIPTION
                "One row per BS sector."
            INDEX { ifIndex }
            ::= { asdmaxTrapStatusTable 1 }

        
        AsdmaxTrapStatusEntry ::=
            SEQUENCE { 
                asdmaxCarrierSenseStatus
                    INTEGER,
                asdmaxCarrierSenseCountStatus
                    Counter32,
                asdmaxCarrierSenseTrapInfo
                    DisplayString,
                asdmaxCarrierSenseFreqChangeTrapInfo
                    DisplayString,
                asdmax1ppsFrameLockStatus
                    INTEGER,
                asdmax1ppsClockDetected
                    INTEGER,
                asdmaxObsaiLinkStatus
                    INTEGER,
                asdmaxObsaiLinkStatusInfo
                    DisplayString,
                asdmaxRfTransceiverFaultStatus
                    INTEGER,
                asdmaxRfTransceiverFaultStatusInfo
                    DisplayString,
                asdmaxCarrierSenseStatusV2
                    INTEGER,
                asdmaxRfPathStatus
                    INTEGER,
                asdmaxRfPathStatusBits
                    BITS,
                asdmaxRfPathStatusInfo
                    DisplayString
             }

        -- 1.3.6.1.4.1.989.1.16.2.4.1.4.2.1.1
        asdmaxCarrierSenseStatus OBJECT-TYPE
            SYNTAX INTEGER
                {
                carrierInterferenceAbsent(0),
                carrierInterferencePresent(1)
                }
            MAX-ACCESS read-only
            STATUS current
            DESCRIPTION
                "Indicates whether interference is detected based on the the level threshold
                and count limit. Each change of this status will trigger trap sending."
            ::= { asdmaxTrapStatusEntry 1 }

        
        -- 1.3.6.1.4.1.989.1.16.2.4.1.4.2.1.2
        asdmaxCarrierSenseCountStatus OBJECT-TYPE
            SYNTAX Counter32
            MAX-ACCESS read-only
            STATUS current
            DESCRIPTION
                "Indicates the number of detections of interference withing the period defined
                by asdmaxCarrierSenseMonitorPeriod."
            ::= { asdmaxTrapStatusEntry 2 }

        
        -- 1.3.6.1.4.1.989.1.16.2.4.1.4.2.1.3
        asdmaxCarrierSenseTrapInfo OBJECT-TYPE
            SYNTAX DisplayString
            MAX-ACCESS read-only
            STATUS current
            DESCRIPTION
                "Implementation specific free text description of the trap raised.
                e.g. 'Interfering Carrier Detected'"
            ::= { asdmaxTrapStatusEntry 3 }

        
        -- 1.3.6.1.4.1.989.1.16.2.4.1.4.2.1.4
        asdmaxCarrierSenseFreqChangeTrapInfo OBJECT-TYPE
            SYNTAX DisplayString
            MAX-ACCESS read-only
            STATUS current
            DESCRIPTION
                "Implementation specific free text description of the trap raised.
                e.g. 'Interfering Carrier Threshold Exceeded Carrier Frequency 
                changed from xMhz to yMhz'"
            ::= { asdmaxTrapStatusEntry 4 }

        
        -- 1.3.6.1.4.1.989.1.16.2.4.1.4.2.1.5
        asdmax1ppsFrameLockStatus OBJECT-TYPE
            SYNTAX INTEGER
                {
                lockedToGps1pps(0),
                notLockedToGps1pps(1)
                }
            MAX-ACCESS read-only
            STATUS current
            DESCRIPTION
                "Indicates current status of timing frame lock."
            ::= { asdmaxTrapStatusEntry 5 }

        
        -- 1.3.6.1.4.1.989.1.16.2.4.1.4.2.1.6
        asdmax1ppsClockDetected OBJECT-TYPE
            SYNTAX INTEGER
                {
                notDetected1ppsClock(0),
                detected1ppsClock(1)
                }
            MAX-ACCESS read-only
            STATUS current
            DESCRIPTION
                "Indicates presence of external 1pps clock"
            ::= { asdmaxTrapStatusEntry 6 }

        
        -- 1.3.6.1.4.1.989.1.16.2.4.1.4.2.1.7
        asdmaxObsaiLinkStatus OBJECT-TYPE
            SYNTAX INTEGER
                {
                obsaiAllLinksOk(0),
                obsaiPartialFailure(1),
                obsaiAllLinksFailed(2)
                }
            MAX-ACCESS read-only
            STATUS current
            DESCRIPTION
                "Indicates the current state of the OBSAI links to the SCRTS as
                seen by the SDR.
                The trap can only be raised after a time of 60 seconds has elapsed after 
                power up/reset of BS to allow for startup process."
            ::= { asdmaxTrapStatusEntry 7 }

        
        -- 1.3.6.1.4.1.989.1.16.2.4.1.4.2.1.8
        asdmaxObsaiLinkStatusInfo OBJECT-TYPE
            SYNTAX DisplayString
            MAX-ACCESS read-only
            STATUS current
            DESCRIPTION
                "Provide additional textual information as in following examples:
                'OBSAI links Failed=None'
                'OBSAI links Failed=Link0'
                'OBSAI links Failed=Link0,Link1'"
            ::= { asdmaxTrapStatusEntry 8 }

        
        -- 1.3.6.1.4.1.989.1.16.2.4.1.4.2.1.9
        asdmaxRfTransceiverFaultStatus OBJECT-TYPE
            SYNTAX INTEGER
                {
                rfTransceiverOk(0),
                rfTransceiverPartialFault(1),
                rfTransceiverDisabled(2),
                rfTransceiverWarning(3)
                }
            MAX-ACCESS read-only
            STATUS current
            DESCRIPTION
                "Reports current status of RF Transceiver."
            ::= { asdmaxTrapStatusEntry 9 }

        
        -- 1.3.6.1.4.1.989.1.16.2.4.1.4.2.1.10
        asdmaxRfTransceiverFaultStatusInfo OBJECT-TYPE
            SYNTAX DisplayString
            MAX-ACCESS read-only
            STATUS current
            DESCRIPTION
                "Indicates the problem in text. Where practical multiple faults 
                can be indicated by a comma separated list e.g.:
                - SCRT(n) Initialisation error; e.g. Device driver hardware fault detected
                - SCRT(n) Calibration fault; e.g. missing Tx or Rx Cal tables
                - SCRT(n) PA Over-current detected
                - Tx switched off via MIB
                - SCRT(n) Unable to determine Board Type Frequency Variant
                - Tx disabled due to Timing Loss (Lock from GPS lost)
                Where n is the instance number of SCRT (0,1,...)."
            ::= { asdmaxTrapStatusEntry 10 }

        
        -- 1.3.6.1.4.1.989.1.16.2.4.1.4.2.1.11
        asdmaxCarrierSenseStatusV2 OBJECT-TYPE
            SYNTAX INTEGER
                {
                noInterference(0),
                highInterference(1),
                lowInterference(2)
                }
            MAX-ACCESS read-only
            STATUS current
            DESCRIPTION
                "Combined status of carrier sense interference detection for all SCRT instances.
                Individual instances status is defined in asdmaxScrtStatusCarrierSense.
                Each change of this status will trigger trap sending.
                When one SCRT reports highInterference and the other lowInterference 
                the resulting combined status is highInterference. 
                The details about insances are available in asdmaxCarrierSenseTrapInfo."
            ::= { asdmaxTrapStatusEntry 11 }

        
        -- 1.3.6.1.4.1.989.1.16.2.4.1.4.2.1.12
        asdmaxRfPathStatus OBJECT-TYPE
            SYNTAX INTEGER
                {
                rfPathAllOk(0),
                rfPathPartialFailure(1),
                rfPathAllFailed(2)
                }
            MAX-ACCESS read-only
            STATUS current
            DESCRIPTION
                "Reports overall status of RF paths. Used to test for alarm condition."
            ::= { asdmaxTrapStatusEntry 12 }

        
        -- 1.3.6.1.4.1.989.1.16.2.4.1.4.2.1.13
        asdmaxRfPathStatusBits OBJECT-TYPE
            SYNTAX BITS
                {
                rfPathDiversityForcedOff(0),
                rfPathScrt1Fault(1),
                rfPathScrt2Fault(2)
                }
            MAX-ACCESS read-only
            STATUS current
            DESCRIPTION
                "Detailed information about nature of reported issue in RF paths."
            ::= { asdmaxTrapStatusEntry 13 }

        
        -- 1.3.6.1.4.1.989.1.16.2.4.1.4.2.1.14
        asdmaxRfPathStatusInfo OBJECT-TYPE
            SYNTAX DisplayString
            MAX-ACCESS read-only
            STATUS current
            DESCRIPTION
                "Provide additional textual information as in following examples:
                'RF paths Failed=None'
                'RF paths Failed=Path0'
                'RF paths Failed=Path0, Path1'
                It may provide other useful hint."
            ::= { asdmaxTrapStatusEntry 14 }

        
        -- 1.3.6.1.4.1.989.1.16.2.4.1.4.3
        asdmaxTrapConfigTable OBJECT-TYPE
            SYNTAX SEQUENCE OF AsdmaxTrapConfigEntry
            MAX-ACCESS not-accessible
            STATUS current
            DESCRIPTION
                "Defines configuration of the system resposible for raising traps,"
            ::= { asdmaxNotification 3 }

        
        -- 1.3.6.1.4.1.989.1.16.2.4.1.4.3.1
        asdmaxTrapConfigEntry OBJECT-TYPE
            SYNTAX AsdmaxTrapConfigEntry
            MAX-ACCESS not-accessible
            STATUS current
            DESCRIPTION
                "One row per BS sector."
            INDEX { ifIndex }
            ::= { asdmaxTrapConfigTable 1 }

        
        AsdmaxTrapConfigEntry ::=
            SEQUENCE { 
                asdmaxCarrierSenseSamplingPeriod
                    Integer32,
                asdmaxCarrierSenseDetectionCountLimit
                    Integer32,
                asdmaxCarrierSenseMonitorPeriod
                    Integer32,
                asdmaxCarrierSenseHighThreshold
                    Integer32
             }

        -- 1.3.6.1.4.1.989.1.16.2.4.1.4.3.1.1
        asdmaxCarrierSenseSamplingPeriod OBJECT-TYPE
            SYNTAX Integer32 (1..86400)
            UNITS "s"
            MAX-ACCESS read-write
            STATUS deprecated
            DESCRIPTION
                "Defines period in seconds when the system counts frames with detected interference.
                Counter is reset at the begining of each sampling period."
            DEFVAL { 30 }
            ::= { asdmaxTrapConfigEntry 1 }

        
        -- 1.3.6.1.4.1.989.1.16.2.4.1.4.3.1.2
        asdmaxCarrierSenseDetectionCountLimit OBJECT-TYPE
            SYNTAX Integer32 (1..2147483647)
            UNITS "10"
            MAX-ACCESS read-write
            STATUS deprecated
            DESCRIPTION
                "Defines when CarrierSenseTrap should be raised. When interference counter goes
                above this value the CarrierSenseTrap is sent with appropriate objects. 
                When interferance counter goes below this value the clearing trap is sent."
            ::= { asdmaxTrapConfigEntry 2 }

        
        -- 1.3.6.1.4.1.989.1.16.2.4.1.4.3.1.3
        asdmaxCarrierSenseMonitorPeriod OBJECT-TYPE
            SYNTAX Integer32 (5..300)
            UNITS "s"
            MAX-ACCESS read-write
            STATUS current
            DESCRIPTION
                "The period in secs over which the FCC carrier sense activation count is monitored before a new trap is generated."
            DEFVAL { 30 }
            ::= { asdmaxTrapConfigEntry 3 }

        
        -- 1.3.6.1.4.1.989.1.16.2.4.1.4.3.1.4
        asdmaxCarrierSenseHighThreshold OBJECT-TYPE
            SYNTAX Integer32 (1..100)
            UNITS "%"
            MAX-ACCESS read-write
            STATUS current
            DESCRIPTION
                "The percentage muting at which the high level trap is raised."
            DEFVAL { 50 }
            ::= { asdmaxTrapConfigEntry 4 }

        
        -- 1.3.6.1.4.1.989.1.16.2.4.1.4.4
        asdmaxSsTrapStatusTable OBJECT-TYPE
            SYNTAX SEQUENCE OF AsdmaxSsTrapStatusEntry
            MAX-ACCESS not-accessible
            STATUS current
            DESCRIPTION
                "Description."
            ::= { asdmaxNotification 4 }

        
        -- 1.3.6.1.4.1.989.1.16.2.4.1.4.4.1
        asdmaxSsTrapStatusEntry OBJECT-TYPE
            SYNTAX AsdmaxSsTrapStatusEntry
            MAX-ACCESS not-accessible
            STATUS current
            DESCRIPTION
                "Description."
            INDEX { asdmaxSsTrapStatusSsMacAddress }
            ::= { asdmaxSsTrapStatusTable 1 }

        
        AsdmaxSsTrapStatusEntry ::=
            SEQUENCE { 
                asdmaxSsTrapStatusSsMacAddress
                    MacAddress,
                asdmaxSsTrapStatusSsEvent
                    INTEGER
             }

        -- 1.3.6.1.4.1.989.1.16.2.4.1.4.4.1.1
        asdmaxSsTrapStatusSsMacAddress OBJECT-TYPE
            SYNTAX MacAddress
            MAX-ACCESS read-only
            STATUS current
            DESCRIPTION
                "SS MAC address defintion used as atrap object."
            ::= { asdmaxSsTrapStatusEntry 1 }

        
        -- 1.3.6.1.4.1.989.1.16.2.4.1.4.4.1.2
        asdmaxSsTrapStatusSsEvent OBJECT-TYPE
            SYNTAX INTEGER { ssEventWiFiReset(0) }
            MAX-ACCESS read-only
            STATUS current
            DESCRIPTION
                "An event sent by SS to BS. BS should send trap asMaxBsSocSsEventTrap
                containing the definition of SS event."
            ::= { asdmaxSsTrapStatusEntry 2 }

        
        -- 1.3.6.1.4.1.989.1.16.2.4.1.5
        asdmaxOfdmPhy OBJECT IDENTIFIER ::= { asdmaxMibObjects 5 }

        
        -- 1.3.6.1.4.1.989.1.16.2.4.1.5.1
        asdmaxOfdmUcdBurstProfileExtTable OBJECT-TYPE
            SYNTAX SEQUENCE OF AsdmaxOfdmUcdBurstProfileExtEntry
            MAX-ACCESS not-accessible
            STATUS current
            DESCRIPTION
                "This table extends the definition of the uplink burst profiles
                specified in the table wmanIfCmnOfdmUcdBurstProfileTable.
                It provides the thresholds used to manage the change of 
                burst profiles similarly to how it is done for downlink."
            ::= { asdmaxOfdmPhy 1 }

        
        -- 1.3.6.1.4.1.989.1.16.2.4.1.5.1.1
        asdmaxOfdmUcdBurstProfileExtEntry OBJECT-TYPE
            SYNTAX AsdmaxOfdmUcdBurstProfileExtEntry
            MAX-ACCESS not-accessible
            STATUS current
            DESCRIPTION
                "Description."
            INDEX { ifIndex, wmanIfCmnOfdmUiucIndex }
            ::= { asdmaxOfdmUcdBurstProfileExtTable 1 }

        
        AsdmaxOfdmUcdBurstProfileExtEntry ::=
            SEQUENCE { 
                asdmaxOfdmUiucMandatoryExitThreshold
                    INTEGER,
                asdmaxOfdmUiucMinEntryThreshold
                    INTEGER,
                asdmaxOfdmUcdBurstProfileRowStatus
                    RowStatus
             }

        -- 1.3.6.1.4.1.989.1.16.2.4.1.5.1.1.1
        asdmaxOfdmUiucMandatoryExitThreshold OBJECT-TYPE
            SYNTAX INTEGER (-255..255)
            UNITS "0.25 dB"
            MAX-ACCESS read-create
            STATUS current
            DESCRIPTION
                "UIUC mandatory exit threshold: -63.75 to +63.75 dB CINR at or
                below where this UIUC can no longer be used and where this
                change to a more robust UIUC is required, in 0.25 dB units.
                "
            ::= { asdmaxOfdmUcdBurstProfileExtEntry 1 }

        
        -- 1.3.6.1.4.1.989.1.16.2.4.1.5.1.1.2
        asdmaxOfdmUiucMinEntryThreshold OBJECT-TYPE
            SYNTAX INTEGER (-255..255)
            UNITS "0.25 dB"
            MAX-ACCESS read-create
            STATUS current
            DESCRIPTION
                "UIUC minimum entry threshold: -63.75 to +63.75 dB dB. The minimum CINR
                required to start using this UIUC when changing from a more
                robust UIUC is required, in 0.25 dB units.
                "
            ::= { asdmaxOfdmUcdBurstProfileExtEntry 2 }

        
        -- 1.3.6.1.4.1.989.1.16.2.4.1.5.1.1.3
        asdmaxOfdmUcdBurstProfileRowStatus OBJECT-TYPE
            SYNTAX RowStatus
            MAX-ACCESS read-create
            STATUS current
            DESCRIPTION
                "Description."
            ::= { asdmaxOfdmUcdBurstProfileExtEntry 3 }

        
        -- 1.3.6.1.4.1.989.1.16.2.4.1.5.2
        asdmaxOfdmConfigTable OBJECT-TYPE
            SYNTAX SEQUENCE OF AsdmaxOfdmConfigEntry
            MAX-ACCESS not-accessible
            STATUS current
            DESCRIPTION
                "This tables contains Ofdm specific Phy configuration objects 
                of the BS 'Sector'.
                The table contains only objects planned to be defined in the next 
                drafts of the standard MIB (table wmanIfBsOfdmConfigurationTable)
                
                The BS is responsible for creating a row in this table for each 
                interface index of type propBWAp2Mp.
                The NMS can modify values in this table."
            ::= { asdmaxOfdmPhy 2 }

        
        -- 1.3.6.1.4.1.989.1.16.2.4.1.5.2.1
        asdmaxOfdmConfigEntry OBJECT-TYPE
            SYNTAX AsdmaxOfdmConfigEntry
            MAX-ACCESS not-accessible
            STATUS current
            DESCRIPTION
                "This tables contains general configuration objects of the BS 'Sector'.
                The table contains all the objects of the following categories:
                -Not presnt in Draft1 of the standard MIB but present or planned 
                 for next drafts
                -Not inteded to be in standard MIB
                "
            INDEX { ifIndex }
            ::= { asdmaxOfdmConfigTable 1 }

        
        AsdmaxOfdmConfigEntry ::=
            SEQUENCE { 
                asdmaxOfdmCfgMinReqRegionFullTxOpp
                    INTEGER,
                asdmaxOfdmCfgMinFocusedCtTxOpp
                    INTEGER,
                asdmaxOfdmCfgMaxRoundTripDelay
                    INTEGER,
                asdmaxOfdmCfgRangeAbortTimingThold
                    INTEGER,
                asdmaxOfdmCfgRangeAbortPowerThold
                    INTEGER,
                asdmaxOfdmCfgRangeAbortFreqThold
                    INTEGER,
                asdmaxOfdmCfgDnlkRateId
                    INTEGER,
                asdmaxOfdmCfgRatioG
                    INTEGER
             }

        -- 1.3.6.1.4.1.989.1.16.2.4.1.5.2.1.1
        asdmaxOfdmCfgMinReqRegionFullTxOpp OBJECT-TYPE
            SYNTAX INTEGER (1..65535)
            UNITS "1/s"
            MAX-ACCESS read-write
            STATUS current
            DESCRIPTION
                "The minimum number of Full bandwidth Req-Region Full
                Transmit opportunities scheduled in the UL per second."
            REFERENCE
                "Section 6.3.7.4.3 in IEEE 802.16-2004"
            ::= { asdmaxOfdmConfigEntry 1 }

        
        -- 1.3.6.1.4.1.989.1.16.2.4.1.5.2.1.2
        asdmaxOfdmCfgMinFocusedCtTxOpp OBJECT-TYPE
            SYNTAX INTEGER (0..65535)
            UNITS "1/s"
            MAX-ACCESS read-write
            STATUS current
            DESCRIPTION
                "The minimum number of focused contention Transmit
                opportunities scheduled in the UL per second. The value may
                be 0 if the focused contention is not implemented."
            REFERENCE
                "Section 6.3.6.4 and 8.3.7.3.3 in IEEE 802.16-2004"
            ::= { asdmaxOfdmConfigEntry 2 }

        
        -- 1.3.6.1.4.1.989.1.16.2.4.1.5.2.1.3
        asdmaxOfdmCfgMaxRoundTripDelay OBJECT-TYPE
            SYNTAX INTEGER (1..65535)
            UNITS "us"
            MAX-ACCESS read-write
            STATUS current
            DESCRIPTION
                "Maximum supported round trip delay.
                It is required to limit the cell size."
            REFERENCE
                "Section 8.3.5.1 in IEEE 802.16-2004"
            ::= { asdmaxOfdmConfigEntry 3 }

        
        -- 1.3.6.1.4.1.989.1.16.2.4.1.5.2.1.4
        asdmaxOfdmCfgRangeAbortTimingThold OBJECT-TYPE
            SYNTAX INTEGER (0..255)
            UNITS "1/Fs"
            MAX-ACCESS read-write
            STATUS current
            DESCRIPTION
                "This object defines Tolerable Timing Offset. BS performs
                Initial Ranging until the SS transmissions are within 
                limits that are deemed tolerable by the BS. If the SS does
                not transmit within these limits after a number of
                correction attempts then the BS aborts Initial Ranging."
            REFERENCE
                "Figure 63 and Table 365 in IEEE 802.16-2004"
            ::= { asdmaxOfdmConfigEntry 4 }

        
        -- 1.3.6.1.4.1.989.1.16.2.4.1.5.2.1.5
        asdmaxOfdmCfgRangeAbortPowerThold OBJECT-TYPE
            SYNTAX INTEGER (0..255)
            UNITS "0.25dB"
            MAX-ACCESS read-write
            STATUS current
            DESCRIPTION
                "This object defines Tolerable Power Offset. BS performs
                Initial Ranging until the SS transmissions are within 
                limits that are deemed tolerable by the BS. If the SS does
                not transmit within these limits after a number of
                correction attempts then the BS aborts Initial Ranging."
            REFERENCE
                "Figure 63 and Table 365 in IEEE 802.16-2004"
            ::= { asdmaxOfdmConfigEntry 5 }

        
        -- 1.3.6.1.4.1.989.1.16.2.4.1.5.2.1.6
        asdmaxOfdmCfgRangeAbortFreqThold OBJECT-TYPE
            SYNTAX INTEGER (0..255)
            UNITS "Hz"
            MAX-ACCESS read-write
            STATUS current
            DESCRIPTION
                "This object defines Tolerable Frequency Offset. BS performs
                Initial Ranging until the SS transmissions are within
                limits that are deemed tolerable by the BS. If the SS does
                not transmit within these limits after a number of
                correction attempts then the BS aborts Initial Ranging."
            REFERENCE
                "Figure 63 and Table 365 in IEEE 802.16-2004"
            ::= { asdmaxOfdmConfigEntry 6 }

        
        -- 1.3.6.1.4.1.989.1.16.2.4.1.5.2.1.7
        asdmaxOfdmCfgDnlkRateId OBJECT-TYPE
            SYNTAX INTEGER
                {
                dnlkRateIdBpsk1-2(0),
                dnlkRateIdQpsk1-2(1),
                dnlkRateIdQpsk3-4(2),
                dnlkRateId16Qam1-2(3),
                dnlkRateId16Qam3-4(4),
                dnlkRateId64Qam2-3(5),
                dnlkRateId64Qam3-4(6)
                }
            MAX-ACCESS read-write
            STATUS current
            DESCRIPTION
                "The Rate ID to be used in the first downlink burst
                immediately following the FCH. The Rate ID encoding is
                static and cannot be changed during system operation. The
                change of the Rate ID should be applied on system
                re-intialisation (e.g. following sector or BS reset)."
            REFERENCE
                "Section 8.3.3.4.3 in IEEE 802.16-2004"
            DEFVAL { dnlkRateIdBpsk1-2 }
            ::= { asdmaxOfdmConfigEntry 7 }

        
        -- 1.3.6.1.4.1.989.1.16.2.4.1.5.2.1.8
        asdmaxOfdmCfgRatioG OBJECT-TYPE
            SYNTAX INTEGER
                {
                ratioG4(0),
                ratioG8(1),
                ratioG16(2),
                ratioG32(3)
                }
            MAX-ACCESS read-write
            STATUS current
            DESCRIPTION
                "The ratio of CP time to 'useful' time.  Values
                are 1/4, 1/8, 1/16 or 1/32."
            DEFVAL { ratioG4 }
            ::= { asdmaxOfdmConfigEntry 8 }

        
        -- 1.3.6.1.4.1.989.1.16.2.4.1.5.3
        asdmaxOfdmSubChannelConfigTable OBJECT-TYPE
            SYNTAX SEQUENCE OF AsdmaxOfdmSubChannelConfigEntry
            MAX-ACCESS not-accessible
            STATUS current
            DESCRIPTION
                "This table provides the thresholds used to manage the
                change in subchannelisation used in the uplink."
            ::= { asdmaxOfdmPhy 3 }

        
        -- 1.3.6.1.4.1.989.1.16.2.4.1.5.3.1
        asdmaxOfdmSubChannelConfigEntry OBJECT-TYPE
            SYNTAX AsdmaxOfdmSubChannelConfigEntry
            MAX-ACCESS not-accessible
            STATUS current
            DESCRIPTION
                "One row for each SubChannelisation width for each interface independently."
            INDEX { ifIndex, asdmaxOfdmSubChannelWidth }
            ::= { asdmaxOfdmSubChannelConfigTable 1 }

        
        AsdmaxOfdmSubChannelConfigEntry ::=
            SEQUENCE { 
                asdmaxOfdmSubChannelWidth
                    INTEGER,
                asdmaxOfdmSubChannelMandatoryExitThreshold
                    INTEGER,
                asdmaxOfdmSubChannelMinEntryThreshold
                    INTEGER,
                asdmaxOfdmSubChannelRowStatus
                    RowStatus
             }

        -- 1.3.6.1.4.1.989.1.16.2.4.1.5.3.1.1
        asdmaxOfdmSubChannelWidth OBJECT-TYPE
            SYNTAX INTEGER
                {
                subChannelWidthSixteenth(1),
                subChannelWidthEighth(2),
                subChannelWidthQuarter(4),
                subChannelWidthHalf(8),
                subChannelWidthFull(16)
                }
            MAX-ACCESS not-accessible
            STATUS current
            DESCRIPTION
                "Indicates the bandwidth that will be granted to the SS
                for uplink data.  Must be 16, 8, 4, 2, 1 or 0, where
                16 = full bandwidth and 1 = sixteenth bandwidth.  0
                indicates that the SS bandwidth will be automatically
                selected by the BS."
            ::= { asdmaxOfdmSubChannelConfigEntry 1 }

        
        -- 1.3.6.1.4.1.989.1.16.2.4.1.5.3.1.2
        asdmaxOfdmSubChannelMandatoryExitThreshold OBJECT-TYPE
            SYNTAX INTEGER (-255..255)
            UNITS "0.25 dB"
            MAX-ACCESS read-create
            STATUS current
            DESCRIPTION
                "Mandatory subchannelisation exit threshold: 0 - 63.75 dB
                CINR below which this subchannelisation can no longer
                be used and where a change to a more robust subchannelisation
                is required, in 0.25 dB units.
                "
            DEFVAL { 255 }
            ::= { asdmaxOfdmSubChannelConfigEntry 2 }

        
        -- 1.3.6.1.4.1.989.1.16.2.4.1.5.3.1.3
        asdmaxOfdmSubChannelMinEntryThreshold OBJECT-TYPE
            SYNTAX INTEGER (-255..255)
            UNITS "0.25 dB"
            MAX-ACCESS read-create
            STATUS current
            DESCRIPTION
                "Minimum subchannelisation entry threshold: 0 - 63.75 dB
                CINR at or above which this subchannelisation can be used
                and where a change from a less robust subchannelisation
                is allowed, in 0.25 dB units.
                "
            DEFVAL { 255 }
            ::= { asdmaxOfdmSubChannelConfigEntry 3 }

        
        -- 1.3.6.1.4.1.989.1.16.2.4.1.5.3.1.4
        asdmaxOfdmSubChannelRowStatus OBJECT-TYPE
            SYNTAX RowStatus
            MAX-ACCESS read-create
            STATUS current
            DESCRIPTION
                "Description."
            ::= { asdmaxOfdmSubChannelConfigEntry 4 }

        
        -- 1.3.6.1.4.1.989.1.16.2.4.1.6
        asdmaxSnmpAgent OBJECT IDENTIFIER ::= { asdmaxMibObjects 6 }

        
        -- 1.3.6.1.4.1.989.1.16.2.4.1.6.1
        asdmaxSnmpAgentConfigTable OBJECT-TYPE
            SYNTAX SEQUENCE OF AsdmaxSnmpAgentConfigEntry
            MAX-ACCESS not-accessible
            STATUS current
            DESCRIPTION
                "This table defines the configuration and action objects 
                for the controller entity of the BS. The controller entity 
                is the one, which implements SNMP agent for this MIB.
                This table has only one row."
            ::= { asdmaxSnmpAgent 1 }

        
        -- 1.3.6.1.4.1.989.1.16.2.4.1.6.1.1
        asdmaxSnmpAgentConfigEntry OBJECT-TYPE
            SYNTAX AsdmaxSnmpAgentConfigEntry
            MAX-ACCESS not-accessible
            STATUS current
            DESCRIPTION
                "Description."
            INDEX { asdmaxSnmpAgentConfigIndex }
            ::= { asdmaxSnmpAgentConfigTable 1 }

        
        AsdmaxSnmpAgentConfigEntry ::=
            SEQUENCE { 
                asdmaxSnmpAgentConfigIndex
                    INTEGER,
                asdmaxSnmpAgentMgmtOnTrafficPort
                    INTEGER,
                asdmaxSnmpAgentMgmtVlanId
                    AsmaxExtendedVlanId,
                asdmaxSnmpAgentIpAddressType
                    InetAddressType,
                asdmaxSnmpAgentIpAddress
                    InetAddress,
                asdmaxQBridgeMode
                    INTEGER,
                asdmaxQBridgeSTagEthertype
                    Integer32,
                asdmaxQBridgeSTagConfigMode
                    INTEGER,
                asdmaxQBridgeSTagPvid
                    AsmaxVlanIdOrNone,
                asdmaxQBridgeSTagUseSTagPriority
                    AsmaxBooleanSwitch,
                asdmaxQBridgeSTagPriority
                    Integer32,
                asdmaxLicenceCertificate
                    OCTET STRING,
                asdmaxLicenceCertCapabilities
                    DisplayString,
                asdmaxLicenceCertInvalid
                    AsmaxBooleanSwitch
             }

        -- 1.3.6.1.4.1.989.1.16.2.4.1.6.1.1.1
        asdmaxSnmpAgentConfigIndex OBJECT-TYPE
            SYNTAX INTEGER (1)
            MAX-ACCESS not-accessible
            STATUS current
            DESCRIPTION
                "Description."
            ::= { asdmaxSnmpAgentConfigEntry 1 }

        
        -- 1.3.6.1.4.1.989.1.16.2.4.1.6.1.1.2
        asdmaxSnmpAgentMgmtOnTrafficPort OBJECT-TYPE
            SYNTAX INTEGER
                {
                mgmtOnTrafficPortDisabled(0),
                mgmtOnTrafficPortEnabled(1)
                }
            MAX-ACCESS read-write
            STATUS current
            DESCRIPTION
                "Controls whether the management traffic is on
                the same network port as regular traffic."
            ::= { asdmaxSnmpAgentConfigEntry 2 }

        
        -- 1.3.6.1.4.1.989.1.16.2.4.1.6.1.1.3
        asdmaxSnmpAgentMgmtVlanId OBJECT-TYPE
            SYNTAX AsmaxExtendedVlanId
            MAX-ACCESS read-write
            STATUS current
            DESCRIPTION
                "Sets the VLAN that management traffic is in, 4096 for none."
            ::= { asdmaxSnmpAgentConfigEntry 3 }

        
        -- 1.3.6.1.4.1.989.1.16.2.4.1.6.1.1.4
        asdmaxSnmpAgentIpAddressType OBJECT-TYPE
            SYNTAX InetAddressType
            MAX-ACCESS read-write
            STATUS current
            DESCRIPTION
                "The type of IP address used in the object
                asdmaxSnmpAgentIpAddress.
                Internal - used by local configuration tool."
            DEFVAL { ipv4 }
            ::= { asdmaxSnmpAgentConfigEntry 4 }

        
        -- 1.3.6.1.4.1.989.1.16.2.4.1.6.1.1.5
        asdmaxSnmpAgentIpAddress OBJECT-TYPE
            SYNTAX InetAddress
            MAX-ACCESS read-write
            STATUS current
            DESCRIPTION
                "IP address of SNMP agent. This address when changed should be applied to 
                management port interface. 
                Internal - used by local configuration tool."
            DEFVAL { "" }
            ::= { asdmaxSnmpAgentConfigEntry 5 }

        
        -- 1.3.6.1.4.1.989.1.16.2.4.1.6.1.1.6
        asdmaxQBridgeMode OBJECT-TYPE
            SYNTAX INTEGER
                {
                bridgeModeVlan(1),
                bridgeModeProvidersVlan(3)
                }
            MAX-ACCESS read-write
            STATUS current
            DESCRIPTION
                "Defines the general mode of BS bridge.
                In VLAN mode bridge implements 802.1q standard.
                In Providers mode bridge extends 802.1q with the S-TAGging based on 802.1ad standard 
                but is limited to single S-TAG VID per port."
            DEFVAL { bridgeModeVlan }
            ::= { asdmaxSnmpAgentConfigEntry 6 }

        
        -- 1.3.6.1.4.1.989.1.16.2.4.1.6.1.1.7
        asdmaxQBridgeSTagEthertype OBJECT-TYPE
            SYNTAX Integer32 (0..65535)
            MAX-ACCESS read-write
            STATUS current
            DESCRIPTION
                "The Ethertype of the frame with outer S-TAG for providers VLAN bridge mode.
                The typical values used are:
                0x88A8 (34984),
                0x9100 (37120),
                0x9200 (37376),
                0x9300 (37632)
                The default value is 0x9100 (37120).
                The object is not defined as an enumeration to allow future extensions.
                NMS should show it as an enumeration on GUI."
            DEFVAL { 37120 }
            ::= { asdmaxSnmpAgentConfigEntry 7 }

        
        -- 1.3.6.1.4.1.989.1.16.2.4.1.6.1.1.8
        asdmaxQBridgeSTagConfigMode OBJECT-TYPE
            SYNTAX INTEGER
                {
                sTagUseSsConfig(1),
                sTagUseBsConfigForAllSsPorts(2)
                }
            MAX-ACCESS read-write
            STATUS current
            DESCRIPTION
                "Instructs to either use SS config (default) for each SS port STagging
                or to use BS config for each SS Port on this BS bridge."
            DEFVAL { sTagUseSsConfig }
            ::= { asdmaxSnmpAgentConfigEntry 8 }

        
        -- 1.3.6.1.4.1.989.1.16.2.4.1.6.1.1.9
        asdmaxQBridgeSTagPvid OBJECT-TYPE
            SYNTAX AsmaxVlanIdOrNone
            MAX-ACCESS read-write
            STATUS current
            DESCRIPTION
                "This object is defined using 802.1q and 802.ad terminology.
                The object overwrites the config for all SS ports on this bridge
                and is used when asdmaxQBridgeSTagConfigMode is set to sTagUseBsConfigForAllSsPorts.
                Object defines VLAN ID applied to outer tag (S-TAG) of the frame when 
                the bridge works in Providers VLAN mode (as defined by asdmaxQBridgeMode). 
                All the packets received from the C-Bridge of this port
                (tagged or untagged with C-TAG i.e. Q-tag) are tagged with this VID."
            DEFVAL { 1 }
            ::= { asdmaxSnmpAgentConfigEntry 9 }

        
        -- 1.3.6.1.4.1.989.1.16.2.4.1.6.1.1.10
        asdmaxQBridgeSTagUseSTagPriority OBJECT-TYPE
            SYNTAX AsmaxBooleanSwitch
            MAX-ACCESS read-write
            STATUS current
            DESCRIPTION
                "The object overwrite the config for all SS ports on this BS bridge.
                When false (default) the user priority for STag is copied from 
                the inner tag (CTag).
                When true the user priority for STag is taken from 
                the object asdmaxQBridgeSTagPriority."
            DEFVAL { booleanFalse }
            ::= { asdmaxSnmpAgentConfigEntry 10 }

        
        -- 1.3.6.1.4.1.989.1.16.2.4.1.6.1.1.11
        asdmaxQBridgeSTagPriority OBJECT-TYPE
            SYNTAX Integer32 (0..7)
            MAX-ACCESS read-write
            STATUS current
            DESCRIPTION
                "This object is defined using 802.1q and 802.ad terminology.
                The object overwrites the config for all SS ports on this bridge
                when STagConfigMode selects value sTagConfigModeUseBsConfigForAllSsPorts.
                It is only used when instructed by asdmaxSnmpAgentSTagUseSTagPriority.
                Object defines VLAN user priority applied to outer tag (S-TAG) of the frame 
                when the bridge works in Providers mode (as defined in asDot1qBridgeMode). 
                All the packets received from the C-Bridge of this port
                (tagged or untagged with C-TAG i.e Q-tag) are tagged with this VLAN user priority."
            DEFVAL { 0 }
            ::= { asdmaxSnmpAgentConfigEntry 11 }

        
        -- 1.3.6.1.4.1.989.1.16.2.4.1.6.1.1.12
        asdmaxLicenceCertificate OBJECT-TYPE
            SYNTAX OCTET STRING (SIZE (0..65535))
            MAX-ACCESS read-write
            STATUS current
            DESCRIPTION
                "Certificate defining the licenced featurs for the BS 
                identified by inventory MacAddress. The principal use of
                the certificate is for licensing the encryption algorithms."
            DEFVAL { ''b }
            ::= { asdmaxSnmpAgentConfigEntry 12 }

        
        -- 1.3.6.1.4.1.989.1.16.2.4.1.6.1.1.13
        asdmaxLicenceCertCapabilities OBJECT-TYPE
            SYNTAX DisplayString
            MAX-ACCESS read-only
            STATUS current
            DESCRIPTION
                "BS capabilities licenced using object asdmaxLicenceCertificate.
                The capabilites are encodded in clear text ready to display on EMS GUI."
            DEFVAL { ''b }
            ::= { asdmaxSnmpAgentConfigEntry 13 }

        
        -- 1.3.6.1.4.1.989.1.16.2.4.1.6.1.1.14
        asdmaxLicenceCertInvalid OBJECT-TYPE
            SYNTAX AsmaxBooleanSwitch
            MAX-ACCESS read-only
            STATUS current
            DESCRIPTION
                "Reports the invalidity of the configured certificate asdmaxLicenceCertificate."
            DEFVAL { booleanFalse }
            ::= { asdmaxSnmpAgentConfigEntry 14 }

        
        -- 1.3.6.1.4.1.989.1.16.2.4.1.6.2
        asdmaxSnmpActionsTable OBJECT-TYPE
            SYNTAX SEQUENCE OF AsdmaxSnmpActionsEntry
            MAX-ACCESS not-accessible
            STATUS current
            DESCRIPTION
                "This table defines the actions specific to custom implementation
                of SNMP agnet in DemoMax.
                "
            ::= { asdmaxSnmpAgent 2 }

        
        -- 1.3.6.1.4.1.989.1.16.2.4.1.6.2.1
        asdmaxSnmpActionsEntry OBJECT-TYPE
            SYNTAX AsdmaxSnmpActionsEntry
            MAX-ACCESS not-accessible
            STATUS current
            DESCRIPTION
                "Description."
            INDEX { asdmaxSnmpAgentConfigIndex }
            ::= { asdmaxSnmpActionsTable 1 }

        
        AsdmaxSnmpActionsEntry ::=
            SEQUENCE { 
                asdmaxSnmpActionsDeleteAllSsConfig
                    AsmaxAction,
                asdmaxSnmpActionsReinitMib
                    AsmaxAction,
                asdmaxSnmpActionsResetBs
                    INTEGER,
                asdmaxSnmpActionsRowStatus
                    RowStatus
             }

        -- 1.3.6.1.4.1.989.1.16.2.4.1.6.2.1.1
        asdmaxSnmpActionsDeleteAllSsConfig OBJECT-TYPE
            SYNTAX AsmaxAction
            MAX-ACCESS read-create
            STATUS current
            DESCRIPTION
                "When set to actionExecute, it instructs BS 
                to delete all MIB objects relevant to given SS,
                provisioned as well as registered on the BS.
                "
            ::= { asdmaxSnmpActionsEntry 1 }

        
        -- 1.3.6.1.4.1.989.1.16.2.4.1.6.2.1.2
        asdmaxSnmpActionsReinitMib OBJECT-TYPE
            SYNTAX AsmaxAction
            MAX-ACCESS read-create
            STATUS current
            DESCRIPTION
                "When set to actionExecute, it instructs BS 
                to erase all MIB objects and reinitialise the entire MIB."
            ::= { asdmaxSnmpActionsEntry 2 }

        
        -- 1.3.6.1.4.1.989.1.16.2.4.1.6.2.1.3
        asdmaxSnmpActionsResetBs OBJECT-TYPE
            SYNTAX INTEGER
                {
                actionsResetBsNoAction(0),
                actionsResetBs(1)
                }
            MAX-ACCESS read-create
            STATUS current
            DESCRIPTION
                "This object should be implemented as follows:
                - When set to actionsResetBs value, instructs BS to reset
                  itself
                - When set to value different than actionsResetBs it
                  should be ignored
                - When read it should return actionsResetBsNoAction"
            DEFVAL { actionsResetBsNoAction }
            ::= { asdmaxSnmpActionsEntry 3 }

        
        -- 1.3.6.1.4.1.989.1.16.2.4.1.6.2.1.4
        asdmaxSnmpActionsRowStatus OBJECT-TYPE
            SYNTAX RowStatus
            MAX-ACCESS read-create
            STATUS current
            DESCRIPTION
                "Description."
            ::= { asdmaxSnmpActionsEntry 4 }

        
        -- 1.3.6.1.4.1.989.1.16.2.4.1.6.3
        asdmaxSwUpgradeTable OBJECT-TYPE
            SYNTAX SEQUENCE OF AsdmaxSwUpgradeEntry
            MAX-ACCESS not-accessible
            STATUS current
            DESCRIPTION
                "Description."
            ::= { asdmaxSnmpAgent 3 }

        
        -- 1.3.6.1.4.1.989.1.16.2.4.1.6.3.1
        asdmaxSwUpgradeEntry OBJECT-TYPE
            SYNTAX AsdmaxSwUpgradeEntry
            MAX-ACCESS not-accessible
            STATUS current
            DESCRIPTION
                "Description."
            INDEX { asdmaxSwType }
            ::= { asdmaxSwUpgradeTable 1 }

        
        AsdmaxSwUpgradeEntry ::=
            SEQUENCE { 
                asdmaxSwType
                    AsmaxBsSoftwareType,
                asdmaxSwCfgCommand
                    INTEGER,
                asdmaxSwCfgFileToInstall
                    DisplayString,
                asdmaxSwCfgFileServerAddrType
                    InetAddressType,
                asdmaxSwCfgFileServerAddr
                    InetAddress,
                asdmaxSwCfgVersionToActivate
                    DisplayString,
                asdmaxSwStatusCode
                    INTEGER,
                asdmaxSwStatusString
                    DisplayString,
                asdmaxSwStatusProgress
                    INTEGER,
                asdmaxSwActiveVersion
                    DisplayString,
                asdmaxSwActiveDetails
                    DisplayString,
                asdmaxSwStandbyVersion
                    DisplayString,
                asdmaxSwStandbyDetails
                    DisplayString,
                asdmaxSwTypeDescription
                    DisplayString,
                asdmaxSwServerType
                    INTEGER,
                asdmaxSwServerUserName
                    DisplayString,
                asdmaxSwServerPassword
                    DisplayString
             }

        -- 1.3.6.1.4.1.989.1.16.2.4.1.6.3.1.1
        asdmaxSwType OBJECT-TYPE
            SYNTAX AsmaxBsSoftwareType
            MAX-ACCESS not-accessible
            STATUS current
            DESCRIPTION
                "Identifies the type of image or image package to install. 
                Different types may require different implementation
                of the upgrade process.
                'swTypeOs' is typically a maintenance operation 
                used in exceptional circumstance and by default doesn't 
                have the standby storage."
            ::= { asdmaxSwUpgradeEntry 1 }

        
        -- 1.3.6.1.4.1.989.1.16.2.4.1.6.3.1.2
        asdmaxSwCfgCommand OBJECT-TYPE
            SYNTAX INTEGER
                {
                swCommandIdle(0),
                swCommandAbort(1),
                swCommandInstallOnly(2),
                swCommandActivateOnly(3)
                }
            MAX-ACCESS read-write
            STATUS current
            DESCRIPTION
                "Object carries request to initiate a part 
                of upgrate process as follows:
                swCommandIdle - no action
                swCommandAbort - aborts any upgrade operation reported 
                    as failed or in progress.
                swCommandInstallOnly - typically initiates the download 
                    of the file from the file server. The file to install
                    is identified by object 'asdmaxSwCfgFileToInstall'
                swCommandActivateOnly - typically initiates the process 
                    resulting in a change of active (running) software
                The time when the downloaded file is commited to non volatile 
                memory is subject to implementation.
                
                This object should be treated as write-only but if read by 
                generic browser it should return always a value of 'swCommandIdle'
                "
            ::= { asdmaxSwUpgradeEntry 2 }

        
        -- 1.3.6.1.4.1.989.1.16.2.4.1.6.3.1.3
        asdmaxSwCfgFileToInstall OBJECT-TYPE
            SYNTAX DisplayString
            MAX-ACCESS read-write
            STATUS current
            DESCRIPTION
                "The fully qualified name of the file to install 
                (typically download from the server)."
            ::= { asdmaxSwUpgradeEntry 3 }

        
        -- 1.3.6.1.4.1.989.1.16.2.4.1.6.3.1.4
        asdmaxSwCfgFileServerAddrType OBJECT-TYPE
            SYNTAX InetAddressType
            MAX-ACCESS read-write
            STATUS current
            DESCRIPTION
                "Defines the type of 'asdmaxSwCfgFileServerAddr'."
            ::= { asdmaxSwUpgradeEntry 4 }

        
        -- 1.3.6.1.4.1.989.1.16.2.4.1.6.3.1.5
        asdmaxSwCfgFileServerAddr OBJECT-TYPE
            SYNTAX InetAddress
            MAX-ACCESS read-write
            STATUS current
            DESCRIPTION
                "Defines the address of the server the file to install 
                is available to download from."
            ::= { asdmaxSwUpgradeEntry 5 }

        
        -- 1.3.6.1.4.1.989.1.16.2.4.1.6.3.1.6
        asdmaxSwCfgVersionToActivate OBJECT-TYPE
            SYNTAX DisplayString
            MAX-ACCESS read-write
            STATUS current
            DESCRIPTION
                "Defines the version of the software to activate. 
                This value must match the version of one of the two files 
                installed: 'asdmaxSwActiveVersion' or 'asdmaxStandbyVersion'.
                If the version is not installed the requested activation 
                terminates with an error."
            ::= { asdmaxSwUpgradeEntry 6 }

        
        -- 1.3.6.1.4.1.989.1.16.2.4.1.6.3.1.7
        asdmaxSwStatusCode OBJECT-TYPE
            SYNTAX INTEGER
                {
                swStatusIdle(1),
                swStatusInstallInProgress(2),
                swStatusActivationInProgress(3),
                swStatusInstallFailure(4),
                swStatusActivationFailure(5)
                }
            MAX-ACCESS read-only
            STATUS current
            DESCRIPTION
                "Reported status of the operation in progress. The values 
                of this object mean:
                swStatusIdle - no operation in progress or last requested 
                    operation completed successfully
                swStatusInstallInProgress - Install operation in progress
                swStatusActivationInProgress - Activation operation in progress
                swStatusInstallFailure - Install operation terminated with error
                swStatusActivationFailure - Activation operation terminated with error
                "
            ::= { asdmaxSwUpgradeEntry 7 }

        
        -- 1.3.6.1.4.1.989.1.16.2.4.1.6.3.1.8
        asdmaxSwStatusString OBJECT-TYPE
            SYNTAX DisplayString
            MAX-ACCESS read-only
            STATUS current
            DESCRIPTION
                "Implementation specific reporting message. If operation is 
                terminated with an error this object will report error details."
            ::= { asdmaxSwUpgradeEntry 8 }

        
        -- 1.3.6.1.4.1.989.1.16.2.4.1.6.3.1.9
        asdmaxSwStatusProgress OBJECT-TYPE
            SYNTAX INTEGER (0..100)
            UNITS "%"
            MAX-ACCESS read-only
            STATUS current
            DESCRIPTION
                "The progress of the operation expressed in %. If exact 
                progress is not available the object should report:
                0% if no operation is in progress
                50% if operation is in progress
                100% when operation is complete
                The progress value can change from non zero value back 
                to zero percent only when the operation has been aborted 
                or when a new operation has been requested by setting 
                the object asdmaxSwCfgCommand.
                "
            ::= { asdmaxSwUpgradeEntry 9 }

        
        -- 1.3.6.1.4.1.989.1.16.2.4.1.6.3.1.10
        asdmaxSwActiveVersion OBJECT-TYPE
            SYNTAX DisplayString
            MAX-ACCESS read-only
            STATUS current
            DESCRIPTION
                "The version string of the active (running) software."
            ::= { asdmaxSwUpgradeEntry 10 }

        
        -- 1.3.6.1.4.1.989.1.16.2.4.1.6.3.1.11
        asdmaxSwActiveDetails OBJECT-TYPE
            SYNTAX DisplayString
            MAX-ACCESS read-only
            STATUS current
            DESCRIPTION
                "Details of the active (running) software. The contents of 
                this object is implementation specific."
            ::= { asdmaxSwUpgradeEntry 11 }

        
        -- 1.3.6.1.4.1.989.1.16.2.4.1.6.3.1.12
        asdmaxSwStandbyVersion OBJECT-TYPE
            SYNTAX DisplayString
            MAX-ACCESS read-only
            STATUS current
            DESCRIPTION
                "The version string of the standby (backup) software.
                This software version is available for activation."
            ::= { asdmaxSwUpgradeEntry 12 }

        
        -- 1.3.6.1.4.1.989.1.16.2.4.1.6.3.1.13
        asdmaxSwStandbyDetails OBJECT-TYPE
            SYNTAX DisplayString
            MAX-ACCESS read-only
            STATUS current
            DESCRIPTION
                "Details of the standby (backup) software. The contents of 
                this object is implementation specific."
            ::= { asdmaxSwUpgradeEntry 13 }

        
        -- 1.3.6.1.4.1.989.1.16.2.4.1.6.3.1.14
        asdmaxSwTypeDescription OBJECT-TYPE
            SYNTAX DisplayString
            MAX-ACCESS read-only
            STATUS current
            DESCRIPTION
                "Describes the role of the software type."
            ::= { asdmaxSwUpgradeEntry 14 }

        
        -- 1.3.6.1.4.1.989.1.16.2.4.1.6.3.1.15
        asdmaxSwServerType OBJECT-TYPE
            SYNTAX INTEGER
                {
                swServerTypeFtp(1),
                swServerTypeTftp(2)
                }
            MAX-ACCESS read-write
            STATUS current
            DESCRIPTION
                "Defines the type of file server used to install(download) file image.
                FTP server requires user name and password defined by objects 
                asMaxBsCmSwServerUserName and asMaxBsCmSwServerPassword."
            DEFVAL { swServerTypeTftp }
            ::= { asdmaxSwUpgradeEntry 15 }

        
        -- 1.3.6.1.4.1.989.1.16.2.4.1.6.3.1.16
        asdmaxSwServerUserName OBJECT-TYPE
            SYNTAX DisplayString
            MAX-ACCESS read-write
            STATUS current
            DESCRIPTION
                "User name is required to open session on file servers with user authentication
                implemented like FTP."
            ::= { asdmaxSwUpgradeEntry 16 }

        
        -- 1.3.6.1.4.1.989.1.16.2.4.1.6.3.1.17
        asdmaxSwServerPassword OBJECT-TYPE
            SYNTAX DisplayString
            MAX-ACCESS read-write
            STATUS current
            DESCRIPTION
                "Password is required to open session on file servers with user authentication
                implemented like FTP. The password is given for the user specified by object
                asMaxBsCmSwServerUserName."
            ::= { asdmaxSwUpgradeEntry 17 }

        
        -- 1.3.6.1.4.1.989.1.16.2.4.1.6.4
        asdmaxSnmpTestTable OBJECT-TYPE
            SYNTAX SEQUENCE OF AsdmaxSnmpTestEntry
            MAX-ACCESS not-accessible
            STATUS current
            DESCRIPTION
                "Table used to apply stimuli for integration tests
                of SNMP agent-manager.
                This table should be only implemented conditionally 
                in the debug code.
                The rows are created by NMS."
            ::= { asdmaxSnmpAgent 4 }

        
        -- 1.3.6.1.4.1.989.1.16.2.4.1.6.4.1
        asdmaxSnmpTestEntry OBJECT-TYPE
            SYNTAX AsdmaxSnmpTestEntry
            MAX-ACCESS not-accessible
            STATUS current
            DESCRIPTION
                "Description."
            INDEX { ifIndex }
            ::= { asdmaxSnmpTestTable 1 }

        
        AsdmaxSnmpTestEntry ::=
            SEQUENCE { 
                asdmaxSnmpTestTriggerTrap
                    INTEGER,
                asdmaxSnmpTestRowStatus
                    RowStatus
             }

        -- 1.3.6.1.4.1.989.1.16.2.4.1.6.4.1.1
        asdmaxSnmpTestTriggerTrap OBJECT-TYPE
            SYNTAX INTEGER
                {
                triggerTrapNoAction(0),
                triggerTrapStatusNotif(1),
                triggerTrapDsxFail(2),
                triggerTrapRssiChange(3),
                triggerTrapPkmFail(4)
                }
            MAX-ACCESS read-create
            STATUS current
            DESCRIPTION
                "Used to instruct BS to trigger example trap refering to
                arbitrary of unknown source (SS).
                When set to triggerTrapNoAction BS should ignore it.
                When set to a differnt value BS should send requested trap
                for the ifIndex this object is set."
            ::= { asdmaxSnmpTestEntry 1 }

        
        -- 1.3.6.1.4.1.989.1.16.2.4.1.6.4.1.2
        asdmaxSnmpTestRowStatus OBJECT-TYPE
            SYNTAX RowStatus
            MAX-ACCESS read-create
            STATUS current
            DESCRIPTION
                "Description."
            ::= { asdmaxSnmpTestEntry 2 }

        
        -- 1.3.6.1.4.1.989.1.16.2.4.1.6.5
        asdmaxSnmpTrapDestTable OBJECT-TYPE
            SYNTAX SEQUENCE OF AsdmaxSnmpTrapDestEntry
            MAX-ACCESS not-accessible
            STATUS current
            DESCRIPTION
                "Description."
            ::= { asdmaxSnmpAgent 5 }

        
        -- 1.3.6.1.4.1.989.1.16.2.4.1.6.5.1
        asdmaxSnmpTrapDestEntry OBJECT-TYPE
            SYNTAX AsdmaxSnmpTrapDestEntry
            MAX-ACCESS not-accessible
            STATUS current
            DESCRIPTION
                "Description."
            INDEX { asdmaxSnmpTrapDestIndex }
            ::= { asdmaxSnmpTrapDestTable 1 }

        
        AsdmaxSnmpTrapDestEntry ::=
            SEQUENCE { 
                asdmaxSnmpTrapDestIndex
                    INTEGER,
                asdmaxSnmpV1V2TrapDestAddrType
                    InetAddressType,
                asdmaxSnmpV1V2TrapDestAddress
                    InetAddress,
                asdmaxSnmpV1V2TrapDestPort
                    INTEGER,
                asdmaxSnmpTrapDestRowStatus
                    RowStatus,
                asdmaxSnmpTrapDestDescription
                    DisplayString
             }

        -- 1.3.6.1.4.1.989.1.16.2.4.1.6.5.1.1
        asdmaxSnmpTrapDestIndex OBJECT-TYPE
            SYNTAX INTEGER (1..8)
            MAX-ACCESS not-accessible
            STATUS current
            DESCRIPTION
                "Description."
            ::= { asdmaxSnmpTrapDestEntry 1 }

        
        -- 1.3.6.1.4.1.989.1.16.2.4.1.6.5.1.2
        asdmaxSnmpV1V2TrapDestAddrType OBJECT-TYPE
            SYNTAX InetAddressType
            MAX-ACCESS read-create
            STATUS current
            DESCRIPTION
                "The type of IP address used in the object
                asdmaxSnmpV1V2TrapDestAddress."
            DEFVAL { ipv4 }
            ::= { asdmaxSnmpTrapDestEntry 2 }

        
        -- 1.3.6.1.4.1.989.1.16.2.4.1.6.5.1.3
        asdmaxSnmpV1V2TrapDestAddress OBJECT-TYPE
            SYNTAX InetAddress
            MAX-ACCESS read-create
            STATUS current
            DESCRIPTION
                "IP address of SNMP manager configured as a trap
                destination for versions V1 and V2 of SNMP. If this object
                is not created or empty the traps are not sent."
            DEFVAL { "" }
            ::= { asdmaxSnmpTrapDestEntry 3 }

        
        -- 1.3.6.1.4.1.989.1.16.2.4.1.6.5.1.4
        asdmaxSnmpV1V2TrapDestPort OBJECT-TYPE
            SYNTAX INTEGER (0..65535)
            MAX-ACCESS read-create
            STATUS current
            DESCRIPTION
                "Port number of SNMP manager configured as a trap
                destination for versions V1 and V2 of SNMP."
            DEFVAL { 0 }
            ::= { asdmaxSnmpTrapDestEntry 4 }

        
        -- 1.3.6.1.4.1.989.1.16.2.4.1.6.5.1.5
        asdmaxSnmpTrapDestRowStatus OBJECT-TYPE
            SYNTAX RowStatus
            MAX-ACCESS read-create
            STATUS current
            DESCRIPTION
                "Description."
            ::= { asdmaxSnmpTrapDestEntry 5 }

        
        -- 1.3.6.1.4.1.989.1.16.2.4.1.6.5.1.6
        asdmaxSnmpTrapDestDescription OBJECT-TYPE
            SYNTAX DisplayString
            MAX-ACCESS read-create
            STATUS current
            DESCRIPTION
                "Text describing the manager configured to receive traps.
                This object is for information purposes only. It can for example
                say 'Netspan @Netview'."
            ::= { asdmaxSnmpTrapDestEntry 6 }

        
        -- 1.3.6.1.4.1.989.1.16.2.4.1.7
        asdmaxDevice OBJECT IDENTIFIER ::= { asdmaxMibObjects 7 }

        
        -- 1.3.6.1.4.1.989.1.16.2.4.1.7.1
        asdmaxScrtStatusTable OBJECT-TYPE
            SYNTAX SEQUENCE OF AsdmaxScrtStatusEntry
            MAX-ACCESS not-accessible
            STATUS current
            DESCRIPTION
                "Defines status objects for each SCRT device."
            ::= { asdmaxDevice 1 }

        
        -- 1.3.6.1.4.1.989.1.16.2.4.1.7.1.1
        asdmaxScrtStatusEntry OBJECT-TYPE
            SYNTAX AsdmaxScrtStatusEntry
            MAX-ACCESS not-accessible
            STATUS current
            DESCRIPTION
                "One row for each SCRT device."
            INDEX { asdmaxScrtDeviceIndex }
            ::= { asdmaxScrtStatusTable 1 }

        
        AsdmaxScrtStatusEntry ::=
            SEQUENCE { 
                asdmaxScrtDeviceIndex
                    INTEGER,
                asdmaxScrtInstance
                    INTEGER,
                asdmaxScrtStatusIfIndex
                    InterfaceIndex,
                asdmaxScrtStatusOperState
                    INTEGER,
                asdmaxScrtStatusRfTransceiverStatus
                    BITS,
                asdmaxScrtStatusForwardPower
                    Integer32,
                asdmaxScrtStatusReversePower
                    Integer32,
                asdmaxScrtStatusCarrierSense
                    INTEGER
             }

        -- 1.3.6.1.4.1.989.1.16.2.4.1.7.1.1.1
        asdmaxScrtDeviceIndex OBJECT-TYPE
            SYNTAX INTEGER (1..16)
            MAX-ACCESS not-accessible
            STATUS current
            DESCRIPTION
                "SNMP index to SRRT device tables. This is 1 based index."
            ::= { asdmaxScrtStatusEntry 1 }

        
        -- 1.3.6.1.4.1.989.1.16.2.4.1.7.1.1.2
        asdmaxScrtInstance OBJECT-TYPE
            SYNTAX INTEGER (0..15)
            MAX-ACCESS read-only
            STATUS current
            DESCRIPTION
                "Identifies an instance of the scrt device.
                The value of index starts with zero = (ScrtDeviceIndex-1).
                This matches internal SCRT numbering in the agent implementation."
            ::= { asdmaxScrtStatusEntry 2 }

        
        -- 1.3.6.1.4.1.989.1.16.2.4.1.7.1.1.3
        asdmaxScrtStatusIfIndex OBJECT-TYPE
            SYNTAX InterfaceIndex
            MAX-ACCESS read-only
            STATUS current
            DESCRIPTION
                "Reports the interface index this SCRT provides RF services for.
                This is important for multisector BS to identify which SCRT corresponds
                to which sector."
            ::= { asdmaxScrtStatusEntry 3 }

        
        -- 1.3.6.1.4.1.989.1.16.2.4.1.7.1.1.4
        asdmaxScrtStatusOperState OBJECT-TYPE
            SYNTAX INTEGER
                {
                scrtOperStateOk(0),
                scrtOperStateFault(1)
                }
            MAX-ACCESS read-only
            STATUS current
            DESCRIPTION
                "General operational state ok/not ok."
            ::= { asdmaxScrtStatusEntry 4 }

        
        -- 1.3.6.1.4.1.989.1.16.2.4.1.7.1.1.5
        asdmaxScrtStatusRfTransceiverStatus OBJECT-TYPE
            SYNTAX BITS
                {
                scrtStatusInitialisationError(0),
                scrtStatusCalibrationFault(1),
                scrtStatusPaOvercurrent(2),
                scrtStatusTxOffMibConfigured(3),
                scrtStatusUnknownFreqVariant(4),
                scrtStatusTxOffTimingLoss(5),
                scrtStatusAntennaMismatch(6)
                }
            MAX-ACCESS read-only
            STATUS current
            DESCRIPTION
                "Detailed status of the RF transceiver as defined in the value list.
                "
            ::= { asdmaxScrtStatusEntry 5 }

        
        -- 1.3.6.1.4.1.989.1.16.2.4.1.7.1.1.6
        asdmaxScrtStatusForwardPower OBJECT-TYPE
            SYNTAX Integer32
            MAX-ACCESS read-only
            STATUS current
            DESCRIPTION
                "Forward power measurement (raw ADC value)."
            ::= { asdmaxScrtStatusEntry 6 }

        
        -- 1.3.6.1.4.1.989.1.16.2.4.1.7.1.1.7
        asdmaxScrtStatusReversePower OBJECT-TYPE
            SYNTAX Integer32
            MAX-ACCESS read-only
            STATUS current
            DESCRIPTION
                "Reverse power measurement (raw ADC value)."
            ::= { asdmaxScrtStatusEntry 7 }

        
        -- 1.3.6.1.4.1.989.1.16.2.4.1.7.1.1.8
        asdmaxScrtStatusCarrierSense OBJECT-TYPE
            SYNTAX INTEGER
                {
                noInterference(0),
                highInterference(1),
                lowInterference(2)
                }
            MAX-ACCESS read-only
            STATUS current
            DESCRIPTION
                "Indicates whether interference is detected based on the the percentage level threshold.
                High frequency interference is detected when the tested value goes above the threshold.
                Low frequency interference is detected when the tested value gous below the threshold 
                and above zero. The threshold is defined in asdmaxCarrierSenseHighThresholdPercentageMuting."
            ::= { asdmaxScrtStatusEntry 8 }

        
        -- 1.3.6.1.4.1.989.1.16.2.4.1.7.2
        asdmaxScrtConfigTable OBJECT-TYPE
            SYNTAX SEQUENCE OF AsdmaxScrtConfigEntry
            MAX-ACCESS not-accessible
            STATUS current
            DESCRIPTION
                "Description."
            ::= { asdmaxDevice 2 }

        
        -- 1.3.6.1.4.1.989.1.16.2.4.1.7.2.1
        asdmaxScrtConfigEntry OBJECT-TYPE
            SYNTAX AsdmaxScrtConfigEntry
            MAX-ACCESS not-accessible
            STATUS current
            DESCRIPTION
                "One row for each SCRT device."
            INDEX { asdmaxScrtDeviceIndex }
            ::= { asdmaxScrtConfigTable 1 }

        
        AsdmaxScrtConfigEntry ::=
            SEQUENCE { 
                asdmaxScrtCfgResetDevice
                    INTEGER,
                asdmaxScrtCfgTxEnabled
                    AsmaxBooleanSwitch
             }

        -- 1.3.6.1.4.1.989.1.16.2.4.1.7.2.1.1
        asdmaxScrtCfgResetDevice OBJECT-TYPE
            SYNTAX INTEGER
                {
                actionsResetScrtNoAction(0),
                actionsResetScrt(1)
                }
            MAX-ACCESS read-write
            STATUS current
            DESCRIPTION
                "This object should be implemented as follows:
                - When set to actionsResetScrt value, instructs BS to reset SCRT
                - When set to value different than actionsResetScrt it should be ignored
                - When read it should return actionsResetScrtNoAction"
            ::= { asdmaxScrtConfigEntry 1 }

        
        -- 1.3.6.1.4.1.989.1.16.2.4.1.7.2.1.2
        asdmaxScrtCfgTxEnabled OBJECT-TYPE
            SYNTAX AsmaxBooleanSwitch
            MAX-ACCESS read-write
            STATUS current
            DESCRIPTION
                "Disables/enables transmitter for each scrt independently."
            ::= { asdmaxScrtConfigEntry 2 }

        
        -- 1.3.6.1.4.1.989.1.16.2.4.2
        asdmaxConformance OBJECT IDENTIFIER ::= { asMaxBSDemoMax 2 }

        
        -- 1.3.6.1.4.1.989.1.16.2.4.2.1
        asdmaxCompliances OBJECT IDENTIFIER ::= { asdmaxConformance 1 }

        
        -- 1.3.6.1.4.1.989.1.16.2.4.2.1.1
        asdmaxRelease0dot1 MODULE-COMPLIANCE
            STATUS current
            DESCRIPTION 
                "Description."
            MODULE -- this module
                MANDATORY-GROUPS { asdmaxObjectGroup, asdmaxTrapsGroup }
            ::= { asdmaxCompliances 1 }

        
        -- 1.3.6.1.4.1.989.1.16.2.4.2.2
        asdmaxGroups OBJECT IDENTIFIER ::= { asdmaxConformance 2 }

        
        -- 1.3.6.1.4.1.989.1.16.2.4.2.2.1
        asdmaxObjectGroup OBJECT-GROUP
            OBJECTS { asdmaxOfdmUiucMandatoryExitThreshold, asdmaxOfdmUiucMinEntryThreshold, asdmaxCustomRngBackoffStart, asdmaxCustomRngBackoffEnd, asdmaxCustomReqBackoffStart, 
                asdmaxCustomReqBackoffEnd, asdmaxCustomFastPowerCtrl, asdmaxCustomMinFreqOffset, asdmaxCustomMaxFreqOffset, asdmaxCustomMinTimingOffset, 
                asdmaxCustomMaxTimingOffset, asdmaxCustomSnrChangeForUlBurstProfile, asdmaxCustomLicenced, asdmaxCustomLinkUpdatePeriod, asdmaxCustomLinkUpdateNumSs, 
                asdmaxCustomTddDownlinkPercentage, asdmaxCustomDuplex, asdmaxProvSsMcastPollGroupId, asdmaxOfdmCfgRatioG, asdmaxProvVlanBcastServiceClassIndex, 
                asdmaxCustomAllowInsecureSs, asdmaxSwStandbyDetails, asdmaxSwStandbyVersion, asdmaxSwActiveDetails, asdmaxSwActiveVersion, 
                asdmaxSwStatusProgress, asdmaxSwStatusString, asdmaxSwStatusCode, asdmaxSwCfgVersionToActivate, asdmaxSwCfgFileServerAddr, 
                asdmaxSwCfgFileServerAddrType, asdmaxSwCfgFileToInstall, asdmaxSwCfgCommand, asdmaxCustomDownlinkRadioEfficiency, asdmaxCustomUplinkRadioEfficiency, 
                asdmaxCustomDownlinkOverbookingRatio, asdmaxCustomUplinkOverbookingRatio, asdmaxCustomChannelBandwidth, asdmaxCustomMinSubchReqRegionFullTxOpp, asdmaxCustomMinRangingTosPerSec, 
                asdmaxSnmpAgentMgmtVlanId, asdmaxSnmpAgentMgmtOnTrafficPort, asdmaxProvSsFixedDownlinkBurstProfile, asdmaxProvSsFixedUplinkBurstProfile, asdmaxBsCfgUncheckedBcastServiceClassIndex, 
                asdmaxBsCfgUncheckedBcastSfid, asdmaxCustomDlMapPeriod, asdmaxCustomFastPeriodicRangingExchange, asdmaxCustomUplinkRxInitialRangingSpread, asdmaxCustomUplinkRxSetPointSpread, 
                asdmaxCustomUplinkRxSetPoint, asdmaxCustomTargetTxPower, asdmaxCustomRxDiversity, asdmaxCustomUseDlPreambles, asdmaxCustomUlAdjacentAllocGap, 
                asdmaxCustomUlMaxAllocSize, asdmaxSwTypeDescription, asdmaxOfdmSubChannelMandatoryExitThreshold, asdmaxOfdmSubChannelMinEntryThreshold, asdmaxOfdmSubChannelRowStatus, 
                asdmaxCustomAchievedTxPower, asdmaxCustomAchievedRxGain, asdmaxCustomContentionPeriodTtg, asdmaxProvSsSubChannelWidth, asdmaxSnmpTrapDestDescription, 
                asdmaxServiceClassExtRowStatus, asdmaxServiceClassExtPollPeriod, asdmaxPkmConfigAuthGraceTime, asdmaxOfdmUcdBurstProfileRowStatus, asdmaxProvSfExtCsType, 
                asdmaxProvSfExtRowStatus, asdmaxProvVlanFlags, asdmaxProvVlanUntaggedBcastSfid, asdmaxProvVlanTaggedBcastSfid, asdmaxProvVlanRowStatus, 
                asdmaxProvSsToVlanMapRowStatus, asdmaxProvClassifierRuleExtPhsSize, asdmaxProvClassifierRuleExtPhsMask, asdmaxProvClassifierRuleExtPhsVerify, asdmaxProvClassifierRuleExtRowStatus, 
                asdmaxProvSsDsxAllowed, asdmaxProvSsRowStatus, asdmaxSsActionsResetSs, asdmaxSsActionsDeReRegSs, asdmaxSsActionsDeReRegSsCode, 
                asdmaxSsActionsDeleteSsConfig, asdmaxSsActionsRowStatus, asdmaxPkmConfigTEKGraceTime, asdmaxPkmConfigAuthWaitTimeout, asdmaxPkmConfigReauthWaitTimeout, 
                asdmaxPkmConfigOpWaitTimeout, asdmaxCustomDlMaxAllocSize, asdmaxCustomInitialBurstTtg, asdmaxCustomTimingSource, asdmaxProvSsMeasPollPeriodMs, 
                asdmaxProvSsMeasPollingRequired, asdmaxProvVlanDhcpRelayAgentActive, asdmaxProvVlanMacForceForwardIpAddress, asdmaxServiceClassExtFlags, asdmaxCustomTransmitFrameGap, 
                asdmaxCustomStcMode, asdmaxCustomUlMidambles, asdmaxCustomStrictConformance, asdmaxServiceClassExtUplinkDSField, asdmaxServiceClassExtUplinkVlan, 
                asdmax1ppsClockDetected, asdmaxCustomCarrierSenseThreshold, asdmaxCustomCarrierSenseBackoffFrames, asdmaxSsStatusProductCode, asdmaxBsCfgBasicMgmtUlQoSProfileIndex, 
                asdmaxBsCfgBasicMgmtDlQoSProfileIndex, asdmaxBsCfgPrimMgmtUlQoSProfileIndex, asdmaxBsCfgPrimMgmtDlQoSProfileIndex, asdmaxCustomPacketCounterUpdatePeriod, asdmaxCustomCidAllocationNumSss, 
                asdmaxCustomBridgeEntriesPerSs, asdmaxCustomBridgeEntriesPerBs, asdmaxProvVlanMacForceForwardIpAddressType, asdmaxCustomGlobalEncryptionMode, asdmaxCustomAdvertisedIeeeVersion, 
                asdmaxCustomStcMinimumShift, asdmaxCustomStcFramesBetweenShifts, asdmaxCustomSasNumBeams, asdmaxBsStdDeviationRssiReport, asdmaxBsStdDeviationCinrReport, 
                asdmaxBsMeanRssiReport, asdmaxBsMeanCinrReport, asdmaxBsBasicReport, asdmaxBsDuration, asdmaxBsStartFrame, 
                asdmaxBsChannelNumber, asdmaxBsHistogramIndex, asdmaxCustomUlSnrUpwardAlpha, asdmaxCustomUlSnrDownwardAlpha, asdmaxCustomPadDownlinkFrame, 
                asdmaxCustomMinimumRegToStcGap, asdmaxCustomEarliestStcStartTime, asdmaxPkmConfigAuthRejectWaitTimeout, asdmaxBsSsDownlinkOctetCount, asdmaxBsSsUplinkOctetCount, 
                asdmaxBsSsDlSecondaryOctetCount, asdmaxBsSsUlSecondaryOctetCount, asdmaxBsSsDlPrimaryOctetCount, asdmaxBsSsUlPrimaryOctetCount, asdmaxBsSsDlBasicOctetCount, 
                asdmaxBsSsUlBasicOctetCount, asdmaxBsSsDownlinkSduCount, asdmaxBsSsUplinkSduCount, asdmaxBsSsDlSecondarySduCount, asdmaxBsSsUlSecondarySduCount, 
                asdmaxBsSsDlPrimarySduCount, asdmaxBsSsUlPrimarySduCount, asdmaxBsSsDlBasicSduCount, asdmaxBsSsUlBasicSduCount, asdmaxBsSsModSubChanStatsUlScwFull, 
                asdmaxBsSsModSubChanStatsUlScwHalf, asdmaxBsSsModSubChanStatsUlScwQuarter, asdmaxBsSsModSubChanStatsUlScwEighth, asdmaxBsSsModSubChanStatsUlScwSixteenth, asdmaxBsSsModSubChanStatsUlMod64Qam34, 
                asdmaxBsSsModSubChanStatsUlMod64Qam23, asdmaxBsSsModSubChanStatsUlMod16Qam34, asdmaxBsSsModSubChanStatsUlMod16Qam12, asdmaxBsSsModSubChanStatsUlModQpsk34, asdmaxBsSsModSubChanStatsUlModQpsk12, 
                asdmaxBsSsModSubChanStatsUlModBpsk, asdmaxBsSsModSubChanStatsDlMod64Qam34, asdmaxBsSsModSubChanStatsDlMod64Qam23, asdmaxBsSsModSubChanStatsDlMod16Qam34, asdmaxBsSsModSubChanStatsDlMod16Qam12, 
                asdmaxBsSsModSubChanStatsDlModQpsk34, asdmaxBsSsModSubChanStatsDlModQpsk12, asdmaxBsSsModSubChanStatsDlModBpsk, asdmaxBsIfDlFrameDataMod64Qam34, asdmaxBsIfDlFrameAvailable, 
                asdmaxBsIfDlFrameContention, asdmaxBsIfUlFrameOverhead, asdmaxBsIfUlFrameDataModBpsk, asdmaxBsIfUlFrameDataModQpsk12, asdmaxBsIfUlFrameDataModQpsk34, 
                asdmaxBsIfUlFrameDataMod16Qam12, asdmaxBsIfUlFrameDataMod16Qam34, asdmaxBsIfUlFrameDataMod64Qam23, asdmaxBsIfUlFrameDataMod64Qam34, asdmaxBsIfUlFrameAvailable, 
                asdmaxBsIfUlFrameContention, asdmaxBsIfUlFrameSize, asdmaxBsIfBroadcastSduCount, asdmaxBsIfBroadcastOctetCount, asdmaxBsIfDlFrameDataMod64Qam23, 
                asdmaxBsIfDlFrameDataMod16Qam34, asdmaxBsIfDlFrameDataMod16Qam12, asdmaxBsIfDlFrameDataModQpsk34, asdmaxBsIfDlFrameDataModQpsk12, asdmaxBsIfDlFrameDataModBpsk, 
                asdmaxBsIfDlFrameOverhead, asdmaxCmnCpsTargetSaid, asdmaxCmnCpsReqTxPolicy, asdmaxCmnCpsMinRsvdTolerableRate, asdmaxCmnCpsArqBlockSize, 
                asdmaxCmnCpsArqRxPurgeTimeout, asdmaxCmnCpsArqDeliverInOrder, asdmaxCmnCpsArqSyncLossTimeout, asdmaxCmnCpsArqBlockLifetime, asdmaxCmnCpsArqWindowSize, 
                asdmaxCmnCpsArqEnable, asdmaxCmnCpsSfSchedulingType, asdmaxCmnCpsSduSize, asdmaxCmnCpsFixedVsVariableSduInd, asdmaxCmnCpsMaxLatency, 
                asdmaxCmnCpsToleratedJitter, asdmaxCmnCpsMinReservedRate, asdmaxCmnCpsMaxTrafficBurst, asdmaxCmnCpsMaxSustainedRate, asdmaxCmnCpsTrafficPriority, 
                asdmaxCmnCpsSfState, asdmaxCmnCpsSfDirection, asdmaxCmnCpsSfCid, asdmaxCmnCpsSfId, asdmaxCmnSfCsSpecification, 
                asdmaxProvSsSnrHysteresisMargin, asdmaxProvSsSnrProtectionMargin, asdmaxProvSsSnrAlphaHigh, asdmaxProvSsSnrAlphaLow, asdmaxProvSsSnrConfigEnabled, 
                asdmaxCustomTxGain, asdmaxCustomGainRf, asdmaxCustomGainPc8520, asdmaxCustomAllocStartTime, asdmaxCustomInitialBurstTailGap, 
                asdmaxCustomTargetRxGain, asdmaxCustomCommissioningMode, asdmaxCustomCommissioningFrameNumber, asdmaxCustomRxGainB, asdmaxCustomTxGainB, 
                asdmaxCustomDlMaxBurstSize, asdmaxCustomScrtPowerUpDelay, asdmaxCustomCidQuarantinePeriod, asdmaxCustomBridgeTimeout, asdmaxCustomBridgeFloodingEnabled, 
                asdmaxProvMcastPollGroupToSize, asdmaxProvMcastPollGroupFrameOffset, asdmaxProvMcastPollGroupFrameDivisor, asdmaxProvMcastPollGroupFocused, asdmaxProvMcastPollGroupRowStatus, 
                asdmaxMcastPollGroupStatusCid, asdmaxServiceClassStatusConfigured, asdmaxSfStatusProvisioned, asdmaxCarrierSenseTrapEnabled, asdmaxCarrierSenseFreqChangeTrapEnabled, 
                asdmax1ppsFrameLockTrapEnabled, asdmaxObsaiLinkTrapEnabled, asdmaxRfTransceiverFaultTrapEnabled, asdmaxCarrierSenseStatus, asdmaxCarrierSenseCountStatus, 
                asdmaxCarrierSenseTrapInfo, asdmaxCarrierSenseFreqChangeTrapInfo, asdmax1ppsFrameLockStatus, asdmaxObsaiLinkStatus, asdmaxObsaiLinkStatusInfo, 
                asdmaxRfTransceiverFaultStatus, asdmaxRfTransceiverFaultStatusInfo, asdmaxOfdmCfgMinReqRegionFullTxOpp, asdmaxOfdmCfgMinFocusedCtTxOpp, asdmaxOfdmCfgMaxRoundTripDelay, 
                asdmaxOfdmCfgRangeAbortTimingThold, asdmaxOfdmCfgRangeAbortPowerThold, asdmaxOfdmCfgRangeAbortFreqThold, asdmaxOfdmCfgDnlkRateId, asdmaxSnmpAgentIpAddressType, 
                asdmaxSnmpAgentIpAddress, asdmaxSnmpActionsDeleteAllSsConfig, asdmaxSnmpActionsReinitMib, asdmaxSnmpActionsResetBs, asdmaxSnmpActionsRowStatus, 
                asdmaxSnmpTestTriggerTrap, asdmaxSnmpTestRowStatus, asdmaxSnmpV1V2TrapDestAddrType, asdmaxSnmpV1V2TrapDestAddress, asdmaxSnmpV1V2TrapDestPort, 
                asdmaxSnmpTrapDestRowStatus, asdmaxScrtInstance, asdmaxScrtStatusIfIndex, asdmaxScrtStatusOperState, asdmaxScrtStatusRfTransceiverStatus, 
                asdmaxScrtCfgResetDevice, asdmaxScrtCfgTxEnabled, asdmaxCustomRxGain, asdmaxCustomTransmitterEnabled, asdmaxBsCfgAllowSsAddressedTraffic, 
                asdmaxBsCfgResetSector, asdmaxBsCfgAutoSfidRangeMax, asdmaxBsCfgAutoSfidRangeMin, asdmaxBsCfgAutoSfidEnabled, asdmaxBsCfg2ndMgmtUlQoSProfileIndex, 
                asdmaxBsCfg2ndMgmtDlQoSProfileIndex, asdmaxSsStatusIpAddr, asdmaxSsStatusIpAddrType, asdmaxSsStatusNextMcastPollCid, asdmaxSsStatusMcastPollCid, 
                asdmaxSsStatusSsId, asdmaxProvSsFakeRegistration, asdmaxProvClassifierRuleExtAction, asdmaxProvClassifierRuleExtQTagEnabled, asdmaxProvClassifierRuleExtQTagVlanID, 
                asdmaxProvClassifierRuleExtQTagPriority, asdmaxSsStatusHwRevision, asdmaxSsStatusSwVersion, asdmaxSsStatusWiFiApIpAddrType, asdmaxSsStatusWiFiApIpAddress, 
                asdmaxSsStatusWiFiApMacAddress, asdmaxSsStatusEasyVoiceIpAddrType, asdmaxSsStatusEasyVoiceIpAddress, asdmaxSsStatusEasyVoiceMacAddress, asdmaxProvSsLanTableMaxSize, 
                asdmaxProvSsAllowedBSID, asdmaxProvSsAllowedBSIDMask, asdmaxSsTrapStatusSsMacAddress, asdmaxSsTrapStatusSsEvent, asdmaxPkmConfigRekeyWaitTimeout, 
                asdmaxBsCfgArqTransmitterDelay, asdmaxBsCfgArqReceiverDelay, asdmaxBsCfgArqMinimumRemoteDelay, asdmaxProvSsPortMode, asdmaxCustomTrafficPortMode, 
                asdmaxBsQDefaultPriority, asdmaxProvSsQDefaultPriority, asdmaxProvSsBsidConfigEnabled, asdmaxProvSsToVlanMapTagging, asdmaxProvSsQSTagPvid, 
                asdmaxProvSsQSTagUseSTagPriority, asdmaxProvSsQSTagPriority, asdmaxQBridgeMode, asdmaxQBridgeSTagEthertype, asdmaxQBridgeSTagConfigMode, 
                asdmaxQBridgeSTagPvid, asdmaxQBridgeSTagUseSTagPriority, asdmaxQBridgeSTagPriority, asdmaxCustomImplementsHomeBasestation, asdmaxProvSsQPortMode, 
                asdmaxProvSsQPvid, asdmaxProvSsQIngressFilterEnabled, asdmaxProvSsQFrameTypes, asdmaxBsQPortMode, asdmaxBsQPvid, 
                asdmaxBsQIngressFilterEnabled, asdmaxProvSfExtSaid, asdmaxLicenceCertInvalid, asdmaxLicenceCertCapabilities, asdmaxLicenceCertificate, 
                asdmaxCustomActiveEncryptionMode, asdmaxScrtStatusReversePower, asdmaxScrtStatusForwardPower, asdmaxCustomGpsloopShift, asdmaxCarrierSenseHighThreshold, 
                asdmaxCarrierSenseMonitorPeriod, asdmaxCarrierSenseStatusV2, asdmaxCarrierSenseV2TrapEnabled, asdmaxScrtStatusCarrierSense, asdmaxRfPathStatus, 
                asdmaxRfPathStatusBits, asdmaxRfPathStatusInfo, asdmaxRfPathStatusChangeTrapEnabled, asdmaxCustomScrtRedundancyEnabled, asdmaxSwServerType, 
                asdmaxSwServerUserName, asdmaxSwServerPassword, asdmaxBsQFrameTypes, asdmaxCustomReuseGroup, asdmaxCustomActiveRxDiversity, 
                asdmaxCustomActiveStcMode }
            STATUS current
            DESCRIPTION 
                "This group contains all objects being the core part 
                of the private MIB and expectend not to be included 
                in the standard MIB.
                "
            ::= { asdmaxGroups 1 }

        
        -- 1.3.6.1.4.1.989.1.16.2.4.2.2.2
        asdmaxObsoleteGroup OBJECT-GROUP
            OBJECTS { asdmaxProvVlanMacForceForwardIpAddressOld, asdmaxSsStatusDlSecondarySduCount, asdmaxSsStatusUlSecondarySduCount, asdmaxSsStatusDlPrimarySduCount, asdmaxSsStatusUlPrimarySduCount, 
                asdmaxSsStatusDlBasicSduCount, asdmaxSsStatusUlBasicSduCount, asdmaxCustomMaxBroadcastSize, asdmaxCustomMinPowerToRaise, asdmaxCustomMaxPowerToLower, 
                asdmaxBsCfgAutoScEnabled, asdmaxBsCfgAutoScIndexRangeMin, asdmaxBsCfgAutoScIndexRangeMax }
            STATUS obsolete
            DESCRIPTION 
                "Description."
            ::= { asdmaxGroups 2 }

        
        -- 1.3.6.1.4.1.989.1.16.2.4.2.2.3
        asdmaxTrapsGroup NOTIFICATION-GROUP
            NOTIFICATIONS { asdmaxCarrierSenseTrap, asdmaxCarrierSenseFreqChangeTrap, asdmax1ppsFrameLockTrap, asdmaxObsaiLinkTrap, asdmaxRfTransceiverFaultTrap, 
                asdmaxSsStatusChangedTrap, asdmaxSsEventTrap, asdmaxLicenceCertInvalidTrap, asdmaxCarrierSenseV2Trap, asdmaxRfPathStatusChangeTrap
                 }
            STATUS current
            DESCRIPTION 
                "Description."
            ::= { asdmaxGroups 3 }

        
        -- 1.3.6.1.4.1.989.1.16.2.4.2.2.4
        asdmaxDeprecatedGroup OBJECT-GROUP
            OBJECTS { asdmaxCarrierSenseSamplingPeriod, asdmaxCarrierSenseDetectionCountLimit }
            STATUS deprecated
            DESCRIPTION 
                "Description."
            ::= { asdmaxGroups 4 }

        
    
    END

--
-- AIRSPAN-DEMOMAX-MIB.mib
--
