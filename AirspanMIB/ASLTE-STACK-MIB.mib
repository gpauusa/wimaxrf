--
-- ASLTE-STACK-MIB.mib
-- MIB generated by MG-SOFT Visual MIB Builder 2010 Version 8.0  Build 400
-- Wednesday, October 12, 2011 at 12:20:34
--

    ASLTE-STACK-MIB DEFINITIONS ::= BEGIN
 
        IMPORTS
            asLte            
                FROM AIRSPAN-PRODUCTS-MIB            
            AsCmnTcBooleanSwitch, AsCmnTcResetCmd, AsCmnTcOperationalStatus, AsCmnTcRunningStatus            
                FROM ASCMN-TC-MIB            
            ifIndex            
                FROM IF-MIB            
            InetAddressType, InetAddress            
                FROM INET-ADDRESS-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            DisplayString, TEXTUAL-CONVENTION            
                FROM SNMPv2-TC;
    
    
        -- 1.3.6.1.4.1.989.1.20.1
        asLteStk MODULE-IDENTITY 
            LAST-UPDATED "201110110941Z"		-- October 11, 2011 at 09:41 GMT
            ORGANIZATION 
                "Airspan Communications Ltd"
            CONTACT-INFO 
                "mbozier@airspan.com"
            DESCRIPTION 
                "Propriatory MIB for Airspan LTE Air Interface on an Airspan BS."
            REVISION "201110110941Z"		-- October 11, 2011 at 09:41 GMT
            DESCRIPTION 
                "Pre-Draft 6:
                Add new objects for RF configuration:
                asLteStkCellCfgRxGain, asLteStkCellCfgTxPower, asLteStkCellCfgUplinkFreq,
                asLteStkCellCfgDownlinkFreq, asLteStkCellCfgChannelBandwidth.
                Add new objects for GPR4 of CCPU LTE eNodeB app:
                asLteStkCellCfgInactivityTimerInterval, asLteStkCellCfgInactivityTimerMaxExpires, 
                asLteStkCellCfgSctpServiceType, asLteStkCellDedCfgPhyN2TxAntennaTm3, 
                asLteStkCellDedCfgPhyN4TxAntennaTm3,
                asLteStkCellDedCfgPhyCodebookRestrictionPresent, asLteStkMacCfgSrsSubframeConfigPrdType"
            REVISION "201108300941Z"		-- August 30, 2011 at 09:41 GMT
            DESCRIPTION 
                "Pre-Draft 5:
                - Changed / added default values for the following mib objects:
                asLteStkCellCfgMibDlBandwidth, asLteStkCellSib2CfgPcchDefaultPagingCycle,
                asLteStkCellSib2CfgPcchnB, asLteStkCellSib2CfgTimeAlignmentTimer, asLteStkCellSib5CfgAllowedMeasBandwidth,
                asLteStkCellSib5CfgQOffsetFreq, asLteStkCellDedCfgSrbTStatusProhibit, asLteStkCellDedCfgMacPeriodicPHRTimer,
                asLteStkCellDedCfgDrbPollByte, asLteStkCellDedCfgDrbLogicalChannelGroup, asLteStkCellCfgUeCategory,
                asLteStkMacCfgPeriodicCqiReportingMode"
            REVISION "201108180941Z"		-- August 18, 2011 at 09:41 GMT
            DESCRIPTION 
                "Pre-Draft 4:
                - replaced asLteStkStackCfgUeCategory with asLteStkCellCfgUeCategory to align
                with IIB implementation."
            REVISION "201107200941Z"		-- July 20, 2011 at 09:41 GMT
            DESCRIPTION 
                "Pre-Draft 3:
                - added entirety of CCPU stack configuration to the MIB."
            REVISION "201103210941Z"		-- March 21, 2011 at 09:41 GMT
            DESCRIPTION 
                "Pre-Draft 2:
                - added first draft of properties for tables asLteStkStackCfgTable, asLteStkStackStatusTable 
                and asLteStkCellCfgTable."
            REVISION "201103150941Z"		-- March 15, 2011 at 09:41 GMT
            DESCRIPTION 
                "Pre-Draft 1:
                - initial version "
            ::= { asLte 1 }

        
    
--
-- Textual conventions
--
    
        AsLteStkSchedulerType ::= TEXTUAL-CONVENTION
            STATUS current
            DESCRIPTION 
                "The type of scheduler used by the LTE stack. This has one of the following values:
                - defaultCC - the default proprietary scheduler provided by CCPU, 
                - roundRobin - UEs are serviced in a round robin fashion
                - pfs - Proportional Fair Scheduling which optimises bandwidth resources whilst being fair to logical
                        channel groups
                - maxCI - optimizes bandwidth resources based on wideband CQI"
            SYNTAX INTEGER
                {
                schedulerDefaultCC(0),
                schedulerRoundRobin(1),
                schedulerPfs(2),
                schedulerMaxCI(3)
                }

        AsLteStkDuplexMode ::= TEXTUAL-CONVENTION
            STATUS current
            DESCRIPTION 
                "Mode of operation TDD or FDD. May in the future offer support for Hybrid FDD"
            SYNTAX INTEGER
                {
                fdd(1),
                tdd(2)
                }

        AsLteStkModulation ::= TEXTUAL-CONVENTION
            STATUS current
            DESCRIPTION 
                "Supported Modulation type.  Non-sequential values are for alignment with CCPU stack"
            SYNTAX INTEGER
                {
                bpsk(1),
                qpsk(2),
                qam16(4),
                qam64(64)
                }

        AsLteStkMibDlBandwidthType ::= TEXTUAL-CONVENTION
            STATUS current
            DESCRIPTION 
                "Transmission bandwidth configuration in resource blocks, NRB in downlink, see TS 36.101
                IE dl-Bandwidth (TS36.331). This IE is signalled in the LTE MIB (Master Information Block)"
            SYNTAX INTEGER
                {
                n6(0),
                n15(1),
                n25(2),
                n50(3),
                n75(4),
                n100(5)
                }

        AsLteStkMibPhichDurationType ::= TEXTUAL-CONVENTION
            STATUS current
            DESCRIPTION 
                "Denotes whether the PHICH (Physical HARQ Indicator channel) duration is normal or extended.
                This IE is signalled in the LTE MIB (Master Information Block)"
            SYNTAX INTEGER
                {
                normal(0),
                extended(1)
                }

        AsLteStkMibPhichResourceType ::= TEXTUAL-CONVENTION
            STATUS current
            DESCRIPTION 
                "Ng parameter defined in TS36.211 which is a parameter used to determine the number of PHICH groups.
                This IE is signalled in the LTE MIB (Master Information Block)"
            SYNTAX INTEGER
                {
                oneSixth(0),
                half(1),
                one(2),
                two(3)
                }

        AsLteStkCellCfgChannelBandwidthType ::= TEXTUAL-CONVENTION
            STATUS current
            DESCRIPTION 
                "The bandwidth of the channel in MHz"
            SYNTAX INTEGER
                {
                bw1dot4Mhz(0),
                bw3Mhz(1),
                bw5Mhz(2),
                bw10Mhz(3),
                bw15Mhz(4),
                bw20Mhz(5)
                }

        AsLteStkCellCfgSctpServiceType ::= TEXTUAL-CONVENTION
            STATUS current
            DESCRIPTION 
                "Denotes whether SCTP runs over raw or UDP sockets."
            SYNTAX INTEGER
                {
                raw(0),
                udp(1)
                }

        AsLteStkCellReservedForOperatorUseType ::= TEXTUAL-CONVENTION
            STATUS current
            DESCRIPTION 
                "Denotes whether the cell is reserved for operator use. IE cellReservedForOperatorUse(TS36.331)"
            SYNTAX INTEGER
                {
                reserved(0),
                notReserved(1)
                }

        AsLteStkCellBarredType ::= TEXTUAL-CONVENTION
            STATUS current
            DESCRIPTION 
                "Defines if the cell is barred for use or not. IE cellBarred(TS36.331)"
            SYNTAX INTEGER
                {
                barred(0),
                notBarred(1)
                }

        AsLteStkCellIntraFreqReselectionAllowedType ::= TEXTUAL-CONVENTION
            STATUS current
            DESCRIPTION 
                "Cell Intra Frequency Selection Allowed or not. IE intraFreqReselection (TS36.311)"
            SYNTAX INTEGER
                {
                allowed(0),
                notAllowed(1)
                }

        AsLteStkSibPeriodicityType ::= TEXTUAL-CONVENTION
            STATUS current
            DESCRIPTION 
                "Allowed values for SI (System Information) periodicities. Measured in frames."
            SYNTAX INTEGER
                {
                f8(0),
                f16(1),
                f32(2),
                f64(3),
                f128(4),
                f256(5),
                f512(6)
                }

        AsLteStkSystemInfoWindowLengthType ::= TEXTUAL-CONVENTION
            STATUS current
            DESCRIPTION 
                "Allowed SI (System Information) Window length values.  Values are in msecs"
            SYNTAX INTEGER
                {
                ms1(0),
                ms2(1),
                ms5(2),
                ms10(3),
                ms15(4),
                ms20(5),
                ms40(6)
                }

        AsLteStkCellSib1TddSubframeAssignmnentType ::= TEXTUAL-CONVENTION
            STATUS current
            DESCRIPTION 
                "UL/DL config types in TDD."
            SYNTAX INTEGER
                {
                configType0(0),
                configType1(1),
                configType2(2),
                configType3(3),
                configType4(4),
                configType5(5),
                configType6(6)
                }

        AsLteStkCellSib2CfgBcchModificationPeriodCoeffType ::= TEXTUAL-CONVENTION
            STATUS current
            DESCRIPTION 
                "Allowed values for asLteStkCellSib2CfgBcchModificationPeriodCoeff.  Measured in frames"
            SYNTAX INTEGER
                {
                n2(0),
                n4(1),
                n8(2),
                n16(3)
                }

        AsLteStkCellSib2CfgPcchDefaultPagingCycleType ::= TEXTUAL-CONVENTION
            STATUS current
            DESCRIPTION 
                "Allowed values for asLteStkCellSib2CfgPcchDefaultPagingCycle.  Expressed in radio frames"
            SYNTAX INTEGER
                {
                rf32(0),
                rf64(1),
                rf128(2),
                rf256(3)
                }

        AsLteStkCellSib2CfgPcchnBType ::= TEXTUAL-CONVENTION
            STATUS current
            DESCRIPTION 
                "Allowed values for AsLteStkCellSib2CfgPcchnB.  Value is a multiple of defaultPagingCycle ('T')"
            SYNTAX INTEGER
                {
                fourT(0),
                twoT(1),
                oneT(2),
                halfT(3),
                quarterT(4),
                oneEighthT(5),
                oneSixteenthT(6),
                oneThirtySecondT(7)
                }

        AsLteStkCellSib2CfgPuschHoppingModeType ::= TEXTUAL-CONVENTION
            STATUS current
            DESCRIPTION 
                "Describes the hopping mode."
            SYNTAX INTEGER
                {
                interSubFrame(0),
                intraAndInterSubframe(1)
                }

        AsLteStkCellSib2CfgPucchDeltaShiftType ::= TEXTUAL-CONVENTION
            STATUS current
            DESCRIPTION 
                "Describes the PUCCH Delta Shift"
            SYNTAX INTEGER
                {
                ds1(0),
                ds2(1),
                ds3(2)
                }

        AsLteStkCellSib2CfgSrsUlBandwidthConfigType ::= TEXTUAL-CONVENTION
            STATUS current
            DESCRIPTION 
                "Bandwidth configuration for SRS (Sounding Reference Signal) in Uplink. Measured in sub-bands."
            SYNTAX INTEGER
                {
                bw0(0),
                bw1(1),
                bw2(2),
                bw3(3),
                bw4(4),
                bw5(5),
                bw6(6),
                bw7(7)
                }

        AsLteStkCellSib2CfgSrsUlSubframeConfigType ::= TEXTUAL-CONVENTION
            STATUS current
            DESCRIPTION 
                "Subframe configuration for SRS.  Arbitrary index into configuration table in the standard"
            SYNTAX INTEGER
                {
                sc0(0),
                sc1(1),
                sc2(2),
                sc3(3),
                sc4(4),
                sc5(5),
                sc6(6),
                sc7(7),
                sc8(8),
                sc9(9),
                sc10(10),
                sc11(11),
                sc12(12),
                sc13(13),
                sc14(14),
                sc15(15)
                }

        AsLteStkCellSib2CfgUlPowerControlAlphaType ::= TEXTUAL-CONVENTION
            STATUS current
            DESCRIPTION 
                "Uplink Power Control Alpha"
            SYNTAX INTEGER
                {
                al0(0),
                al04(1),
                al05(2),
                al06(3),
                al07(4),
                al08(5),
                al09(6),
                al1(7)
                }

        AsLteStkCellSib2CfgUlDeltaFPUCCHFormat1Type ::= TEXTUAL-CONVENTION
            STATUS current
            DESCRIPTION 
                "Delta PUCCH for DCI (Downlink Control Informaation) Format1. Measured in dBm."
            SYNTAX INTEGER
                {
                deltaFminus2(0),
                deltaF0(1),
                deltaF2(2)
                }

        AsLteStkCellSib2CfgUlDeltaFPUCCHFormat1bType ::= TEXTUAL-CONVENTION
            STATUS current
            DESCRIPTION 
                "Delta PUCCH for DCI (Downlink Control Informaation) Format1b. Measured in dBm."
            SYNTAX INTEGER
                {
                deltaF1(0),
                deltaF3(1),
                deltaF5(2)
                }

        AsLteStkCellSib2CfgUlDeltaFPUCCHFormat2Type ::= TEXTUAL-CONVENTION
            STATUS current
            DESCRIPTION 
                "Delta PUCCH for DCI (Downlink Control Informaation) Format2. Measured in dBm."
            SYNTAX INTEGER
                {
                deltaFminus2(0),
                deltaF0(1),
                deltaF1(2),
                deltaF2(3)
                }

        AsLteStkCellSib2CfgUlDeltaFPUCCHFormat2aType ::= TEXTUAL-CONVENTION
            STATUS current
            DESCRIPTION 
                "Delta PUCCH for DCI (Downlink Control Informaation) Format2a. Measured in dBm."
            SYNTAX INTEGER
                {
                deltaFminus2(0),
                deltaF0(1),
                deltaF2(2)
                }

        AsLteStkCellSib2CfgUlDeltaFPUCCHFormat2bType ::= TEXTUAL-CONVENTION
            STATUS current
            DESCRIPTION 
                "Delta PUCCH for DCI (Downlink Control Informaation) Format2b. Measured in dBm."
            SYNTAX INTEGER
                {
                deltaFminus2(0),
                deltaF0(1),
                deltaF2(2)
                }

        AsLteStkCellCfgUlCyclicPrefixLengthType ::= TEXTUAL-CONVENTION
            STATUS current
            DESCRIPTION 
                "Cyclic Prefix in uplink"
            SYNTAX INTEGER
                {
                normal(0),
                extended(1)
                }

        AsLteStkCellSib2CfgUeTimerT3xxType ::= TEXTUAL-CONVENTION
            STATUS current
            DESCRIPTION 
                "Timer Value for T300 , T301 and T310.  Measured in msecs"
            SYNTAX INTEGER
                {
                ms100(0),
                ms200(1),
                ms300(2),
                ms400(3),
                ms600(4),
                ms1000(5),
                ms1500(6),
                ms2000(7)
                }

        AsLteStkCellSib2CfgUeConstantN310Type ::= TEXTUAL-CONVENTION
            STATUS current
            DESCRIPTION 
                "Value for  the variable N310"
            SYNTAX INTEGER
                {
                n1(0),
                n2(1),
                n3(2),
                n4(3),
                n6(4),
                n8(5),
                n10(6),
                n20(7)
                }

        AsLteStkCellSib2CfgUeConstantN311Type ::= TEXTUAL-CONVENTION
            STATUS current
            DESCRIPTION 
                "Value for  the variable N311"
            SYNTAX INTEGER
                {
                n1(0),
                n2(1),
                n3(2),
                n4(3),
                n6(4),
                n8(5),
                n10(6)
                }

        AsLteStkCellSib2CfgUlBandwidthType ::= TEXTUAL-CONVENTION
            STATUS current
            DESCRIPTION 
                "Valid Bandwidth values available in Uplink. Expressed in Resource Blocks (RBs)."
            SYNTAX INTEGER
                {
                n6(0),
                n15(1),
                n25(2),
                n50(3),
                n75(4),
                n100(5)
                }

        AsLteStkCellCfgTimeAlignmentTimerType ::= TEXTUAL-CONVENTION
            STATUS current
            DESCRIPTION 
                "Time for which UE is considered time-aligned. Expressed in sub-frames"
            SYNTAX INTEGER
                {
                sf500(0),
                sf750(1),
                sf1280(2),
                sf1920(3),
                sf2560(4),
                sf5120(5),
                sf10240(6),
                infinity(7)
                }

        AsLteStkCellCfgAllowedMeasBandwidthType ::= TEXTUAL-CONVENTION
            STATUS current
            DESCRIPTION 
                "Allowed bandwidth configurations for measurement bandwidth.  Expressed in resource blocks"
            SYNTAX INTEGER
                {
                mbw6(0),
                mbw15(1),
                mbw25(2),
                mbw50(3),
                mbw75(4),
                mbw100(5)
                }

        AsLteStkCellCfgQOffsetFreq ::= TEXTUAL-CONVENTION
            STATUS current
            DESCRIPTION 
                "Values  for frequency specific offsets for equal priority E-UTRAN frequencies.
                Expressed in dBm"
            SYNTAX INTEGER
                {
                dbminus24(0),
                dbminus22(1),
                dbminus20(2),
                dbminus18(3),
                dbminus16(4),
                dbminus14(5),
                dbminus12(6),
                dbminus10(7),
                dbminus8(8),
                dbminus6(9),
                dbminus5(10),
                dbminus4(11),
                dbminus3(12),
                dbminus2(13),
                dbminus1(14),
                db0(15),
                db1(16),
                db2(17),
                db3(18),
                db4(19),
                db5(20),
                db6(21),
                db8(22),
                db10(23),
                db12(24),
                db14(25),
                db16(26),
                db18(27),
                db20(28),
                db22(29),
                db24(30)
                }

        AsLteStkCellPhyCellIdRangeType ::= TEXTUAL-CONVENTION
            STATUS current
            DESCRIPTION 
                "Values supported for physical cell ID ranges."
            SYNTAX INTEGER
                {
                n4(0),
                n8(1),
                n12(2),
                n16(3),
                n24(4),
                n32(5),
                n48(6),
                n64(7),
                n84(8),
                n96(9),
                n128(10),
                n168(11),
                n252(12),
                n504(13),
                spare2(14),
                spare1(15)
                }

        AsLteStkCellRachCfgNumberOfRAPreamblesType ::= TEXTUAL-CONVENTION
            STATUS current
            DESCRIPTION 
                "Number of random access preambles"
            SYNTAX INTEGER
                {
                n4(0),
                n8(1),
                n12(2),
                n16(3),
                n20(4),
                n24(5),
                n28(6),
                n32(7),
                n36(8),
                n40(9),
                n44(10),
                n48(11),
                n52(12),
                n56(13),
                n60(14),
                n64(15)
                }

        AsLteStkCellRachCfgMessagePowerOffsetGroupBType ::= TEXTUAL-CONVENTION
            STATUS current
            DESCRIPTION 
                "Allowed values for the asLteStkCellRachCfgMessagePowerOffsetGroupB.  Value is in dB."
            SYNTAX INTEGER
                {
                minusInfinity(0),
                dB0(1),
                dB5(2),
                dB8(3),
                dB10(4),
                dB1(5),
                dB15(6),
                dB18(7)
                }

        AsLteStkCellRachCfgPowerRampingStepType ::= TEXTUAL-CONVENTION
            STATUS current
            DESCRIPTION 
                "Allowed values for the asLteStkCellRachCfgPowerRampingStep.  Value is in dB."
            SYNTAX INTEGER
                {
                dB0(0),
                dB2(1),
                dB4(2),
                dB6(3)
                }

        AsLteStkCellRachCfgPreambleInitialRcvdTargetPowerType ::= TEXTUAL-CONVENTION
            STATUS current
            DESCRIPTION 
                "Allowed values for the asLteStkCellRachCfgPreambleInitialRcvdTargetPowerType.  Value is in dB."
            SYNTAX INTEGER
                {
                dBminus120(0),
                dBminus118(1),
                dBminus116(2),
                dBminus114(3),
                dBminus112(4),
                dBminus110(5),
                dBminus108(6),
                dBminus106(7),
                dBminus104(8),
                dBminus102(9),
                dBminus100(10),
                dBminus98(11),
                dBminus96(12),
                dBminus94(13),
                dBminus92(14),
                dBminus90(15)
                }

        AsLteStkCellRachCfgPreambleTransMaxType ::= TEXTUAL-CONVENTION
            STATUS current
            DESCRIPTION 
                "Allowed values for asLteStkCellRachCfgPreambleTransMaxType"
            SYNTAX INTEGER
                {
                n3(0),
                n4(1),
                n5(2),
                n6(3),
                n7(4),
                n8(5),
                n10(6),
                n20(7),
                n50(8),
                n100(9),
                n200(10)
                }

        AsLteStkCellRachCfgRAResponseWindowSizeType ::= TEXTUAL-CONVENTION
            STATUS current
            DESCRIPTION 
                "Allowed values for asLteStkCellRachCfgRAResponseWindowSize.  Measured in subframes"
            SYNTAX INTEGER
                {
                sf2(0),
                sf3(1),
                sf4(2),
                sf5(3),
                sf6(4),
                sf7(5),
                sf8(6),
                sf10(7)
                }

        AsLteStkCellRachCfgMacContentionResolutionTimerType ::= TEXTUAL-CONVENTION
            STATUS current
            DESCRIPTION 
                "Allowed values for asLteStkCellRachCfgMacContentionResolutionTimerType.  Measured in subframes"
            SYNTAX INTEGER
                {
                sf8(0),
                sf16(1),
                sf24(2),
                sf32(3),
                sf40(4),
                sf48(5),
                sf56(6),
                sf64(7)
                }

        AsLteStkCellDedCfgTPollRetransmitType ::= TEXTUAL-CONVENTION
            STATUS current
            DESCRIPTION 
                "Values  for Poll Re-transmit timer at RLC."
            SYNTAX INTEGER
                {
                ms5(0),
                ms10(1),
                ms15(2),
                ms20(3),
                ms25(4),
                ms30(5),
                ms35(6),
                ms40(7),
                ms45(8),
                ms50(9),
                ms55(10),
                ms60(11),
                ms65(12),
                ms70(13),
                ms75(14),
                ms80(15),
                ms85(16),
                ms90(17),
                ms95(18),
                ms100(19),
                ms105(20),
                ms110(21),
                ms115(22),
                ms120(23),
                ms125(24),
                ms130(25),
                ms135(26),
                ms140(27),
                ms145(28),
                ms150(29),
                ms155(30),
                ms160(31),
                ms165(32),
                ms170(33),
                ms175(34),
                ms180(35),
                ms185(36),
                ms190(37),
                ms195(38),
                ms200(39),
                ms205(40),
                ms210(41),
                ms215(42),
                ms220(43),
                ms225(44),
                ms230(45),
                ms235(46),
                ms240(47),
                ms245(48),
                ms250(49),
                ms300(50),
                ms350(51),
                ms400(52),
                ms450(53),
                ms500(54)
                }

        AsLteStkCellDedCfgPollPduType ::= TEXTUAL-CONVENTION
            STATUS current
            DESCRIPTION 
                "Values for RLC Poll-PDU  for AM (Acknowledged Mode) radio bearers."
            SYNTAX INTEGER
                {
                p4(0),
                p8(1),
                p16(2),
                p32(3),
                p64(4),
                p128(5),
                p256(6),
                pInfinity(7)
                }

        AsLteStkCellDedCfgPollByteType ::= TEXTUAL-CONVENTION
            STATUS current
            DESCRIPTION 
                "Values for RLC Poll byte for AM (Acknowledged Mode) radio bearers.  Measured in kBytes"
            SYNTAX INTEGER
                {
                kb25(0),
                kb50(1),
                kb75(2),
                kb100(3),
                kb125(4),
                kb250(5),
                kb375(6),
                kb500(7),
                kb750(8),
                kb1000(9),
                kb1250(10),
                kb1500(11),
                kb2000(12),
                kb3000(13),
                kbInfinity(14)
                }

        AsLteStkCellDedCfgMaxRetxThresholdType ::= TEXTUAL-CONVENTION
            STATUS current
            DESCRIPTION 
                "Values for RLC maximum re-transmission threshold for AM (Acknowledged Mode) radio bearers."
            SYNTAX INTEGER
                {
                t1(0),
                t2(1),
                t3(2),
                t4(3),
                t6(4),
                t8(5),
                t16(6),
                t32(7)
                }

        AsLteStkCellDedCfgTReorderingType ::= TEXTUAL-CONVENTION
            STATUS current
            DESCRIPTION 
                "Values for RLC reordering timer for AM (Acknowledged Mode) radio bearers."
            SYNTAX INTEGER
                {
                ms0(0),
                ms5(1),
                ms10(2),
                ms15(3),
                ms20(4),
                ms25(5),
                ms30(6),
                ms35(7),
                ms40(8),
                ms45(9),
                ms50(10),
                ms55(11),
                ms60(12),
                ms65(13),
                ms70(14),
                ms75(15),
                ms80(16),
                ms85(17),
                ms90(18),
                ms95(19),
                ms100(20),
                ms110(21),
                ms120(22),
                ms130(23),
                ms140(24),
                ms150(25),
                ms160(26),
                ms170(27),
                ms180(28),
                ms190(29),
                ms200(30)
                }

        AsLteStkCellDedCfgTStatusProhibitType ::= TEXTUAL-CONVENTION
            STATUS current
            DESCRIPTION 
                "Values for RLC Poll Status Prohibit timer"
            SYNTAX INTEGER
                {
                ms0(0),
                ms5(1),
                ms10(2),
                ms15(3),
                ms20(4),
                ms25(5),
                ms30(6),
                ms35(7),
                ms40(8),
                ms45(9),
                ms50(10),
                ms55(11),
                ms60(12),
                ms65(13),
                ms70(14),
                ms75(15),
                ms80(16),
                ms85(17),
                ms90(18),
                ms95(19),
                ms100(20),
                ms105(21),
                ms110(22),
                ms115(23),
                ms120(24),
                ms125(25),
                ms130(26),
                ms135(27),
                ms140(28),
                ms145(29),
                ms150(30),
                ms155(31),
                ms160(32),
                ms165(33),
                ms170(34),
                ms175(35),
                ms180(36),
                ms185(37),
                ms190(38),
                ms195(39),
                ms200(40),
                ms205(41),
                ms210(42),
                ms215(43),
                ms220(44),
                ms225(45),
                ms230(46),
                ms235(47),
                ms240(48),
                ms245(49),
                ms250(50),
                ms300(51),
                ms350(52),
                ms400(53),
                ms450(54),
                ms500(55)
                }

        AsLteStkCellDedCfgPriBitRateType ::= TEXTUAL-CONVENTION
            STATUS current
            DESCRIPTION 
                "Values for Prioritised Bit rate of a logical channel at MAC. 
                Measured in kiloBytes per second."
            SYNTAX INTEGER
                {
                kBps0(0),
                kBps8(1),
                kBps16(2),
                kBps32(3),
                kBps64(4),
                kBps128(5),
                kBps256(6),
                infinity(7)
                }

        AsLteStkCellDedCfgBucketSizeDurationType ::= TEXTUAL-CONVENTION
            STATUS current
            DESCRIPTION 
                "Values for Bucket size duration of a logical channel at MAC."
            SYNTAX INTEGER
                {
                ms50(0),
                ms100(1),
                ms150(2),
                ms300(3),
                ms500(4),
                ms1000(5),
                spare1(6),
                spare2(7)
                }

        AsLteStkCellMaxHARQTxType ::= TEXTUAL-CONVENTION
            STATUS current
            DESCRIPTION 
                " Values supported for maximum HARQ transmissions."
            SYNTAX INTEGER
                {
                n1(0),
                n2(1),
                n3(2),
                n4(3),
                n5(4),
                n6(5),
                n7(6),
                n8(7),
                n10(8),
                n12(9),
                n16(10),
                n20(11),
                n24(12),
                n28(13),
                spare1(14),
                spare2(15)
                }

        AsLteStkCellDedCfgMacUlSCHPeriodicBSRTimerType ::= TEXTUAL-CONVENTION
            STATUS current
            DESCRIPTION 
                "Values for periodic BSR Timer.Measured in sub-frames."
            SYNTAX INTEGER
                {
                sf5(0),
                sf10(1),
                sf16(2),
                sf20(3),
                sf32(4),
                sf40(5),
                sf64(6),
                sf80(7),
                sf128(8),
                sf160(9),
                sf320(10),
                sf640(11),
                sf1280(12),
                sf2560(13),
                infinity(14),
                spare1(15)
                }

        AsLteStkCellDedCfgMacUlSCHRetxBSRTimerType ::= TEXTUAL-CONVENTION
            STATUS current
            DESCRIPTION 
                "Values for retransmission BSR Timer.Measured in sub-frames"
            SYNTAX INTEGER
                {
                sf320(0),
                sf640(1),
                sf1280(2),
                sf2560(3),
                sf5120(4),
                sf10240(5),
                spare2(6),
                spare1(7)
                }

        AsLteStkCellDedCfgMacPeriodicPHRTimerType ::= TEXTUAL-CONVENTION
            STATUS current
            DESCRIPTION 
                "Values for periodic PHR Timer.Measured in sub-frames."
            SYNTAX INTEGER
                {
                sf10(0),
                sf20(1),
                sf50(2),
                sf100(3),
                sf200(4),
                sf500(5),
                sf1000(6),
                infinity(7)
                }

        AsLteStkCellDedCfgMacProhibitPHRTimerType ::= TEXTUAL-CONVENTION
            STATUS current
            DESCRIPTION 
                "Values for prohibit PHR Timer.Measured in sub-frames."
            SYNTAX INTEGER
                {
                sf0(0),
                sf10(1),
                sf20(2),
                sf50(3),
                sf100(4),
                sf200(5),
                sf500(6),
                sf1000(7)
                }

        AsLteStkCellDedCfgMacDlPathLossChangeType ::= TEXTUAL-CONVENTION
            STATUS current
            DESCRIPTION 
                "DL Pathloss change for PHR reporting.Measured in dB."
            SYNTAX INTEGER
                {
                dB1(0),
                dB3(1),
                dB6(2),
                infinity(3)
                }

        AsLteStkCellDedCfgPhyTddAckNackFeedbackModeType ::= TEXTUAL-CONVENTION
            STATUS current
            DESCRIPTION 
                "ACK/NACK Feeback mode types- Can be bundling or multiplexing."
            SYNTAX INTEGER
                {
                bundling(0),
                multiplexing(1)
                }

        AsLteStkCellDedCfgPhyCqiReportingModeType ::= TEXTUAL-CONVENTION
            STATUS current
            DESCRIPTION 
                "Aperiodic CQI Reporting Mode Types."
            SYNTAX INTEGER
                {
                rm12(0),
                rm20(1),
                rm22(2),
                rm30(3),
                rm31(4),
                spare3(5),
                spare2(6),
                spare1(7)
                }

        AsLteStkCellDedCfgPhyDsrTransMaxType ::= TEXTUAL-CONVENTION
            STATUS current
            DESCRIPTION 
                "SR (Scheduling Request) transmission parameter.  
                The number of transmissions"
            SYNTAX INTEGER
                {
                n4(0),
                n8(1),
                n16(2),
                n32(3),
                n64(4),
                spare3(5),
                spare2(6),
                spare1(7)
                }

        AsLteStkCellDedCfgPhyPdschAckNackRepFactorType ::= TEXTUAL-CONVENTION
            STATUS current
            DESCRIPTION 
                "ACK/NACK repetition factor values."
            SYNTAX INTEGER
                {
                n2(0),
                n4(1),
                n6(2),
                spare1(3)
                }

        AsLteStkCellDedCfgUeTransmissionMode ::= TEXTUAL-CONVENTION
            STATUS current
            DESCRIPTION 
                "UE Transmission Mode"
            SYNTAX INTEGER
                {
                tm1(0),
                tm2(1),
                tm3(2),
                tm4(3),
                tm5(4),
                tm6(5),
                tm7(6),
                spare1(7)
                }

        AsLteStkCellDedCfgDrbPdcpDiscardTimerType ::= TEXTUAL-CONVENTION
            STATUS current
            DESCRIPTION 
                "Values for discard timer at PDCP."
            SYNTAX INTEGER
                {
                ms50(0),
                ms100(1),
                ms150(2),
                ms300(3),
                ms500(4),
                ms750(5),
                ms1500(6),
                infinity(7)
                }

        AsLteStkCellDedCfgPdschDlPowerAllocationType ::= TEXTUAL-CONVENTION
            STATUS current
            DESCRIPTION 
                "The downlink power allocation on the PDSCH (Physical Downlink Shared Channel) channel."
            SYNTAX INTEGER
                {
                dBminus6(0),
                dbminus4dot77(1),
                dbminus3(2),
                dbminus1dot77(3),
                db0(4),
                db1(5),
                db2(6),
                db3(7)
                }

        AsLteStkMacCfgPeriodicCqiReportingModeType ::= TEXTUAL-CONVENTION
            STATUS current
            DESCRIPTION 
                "Periodic CQI Reporting Mode Types."
            SYNTAX INTEGER
                {
                periodicCqiMode10(0),
                periodocCqiMode11(1),
                periodicCqiMode20(2),
                periodicCqiMode21(3)
                }

        AsLteStkMacCfgPeriodicCqiPeriodicityType ::= TEXTUAL-CONVENTION
            STATUS current
            DESCRIPTION 
                "Periodic CQI periodicity."
            SYNTAX INTEGER
                {
                ms2(0),
                ms5(1),
                ms10(2),
                ms20(3),
                ms32(4),
                ms40(5),
                ms64(6),
                ms80(7),
                ms128(8),
                ms160(9),
                ms256(10),
                msOffset(11)
                }

        AsLteStkMacCfgSubcarrierSpacingType ::= TEXTUAL-CONVENTION
            STATUS current
            DESCRIPTION 
                "Permitted Sub carrier spacing frequencies."
            SYNTAX INTEGER
                {
                spacing15khz(0),
                spacing7dot5khz(1)
                }

        AsLteStkMacCfgUeCqiFormatIndicatorType ::= TEXTUAL-CONVENTION
            STATUS current
            DESCRIPTION 
                "Values for CQI reporting format- whether wideBand or subBand."
            SYNTAX INTEGER
                {
                widebandCQI(0),
                subBandCQI(1)
                }

        AsLteStkMacCfgTxAntennaSelectionType ::= TEXTUAL-CONVENTION
            STATUS current
            DESCRIPTION 
                "Determines whether the UE transmit antenna selection is closedLoop or OpenLoop"
            SYNTAX INTEGER
                {
                closedLoop(0),
                openLoop(1)
                }

        AsLteStkMacCfgSrsSubframeConfigPrdType ::= TEXTUAL-CONVENTION
            STATUS current
            DESCRIPTION 
                "Sounding Reference signal periodicity in msecs"
            SYNTAX INTEGER
                {
                msecs1(1),
                msecs2(2),
                msecs5(5),
                msecs10(10),
                infinite(11)
                }

        AsLteStkSibType ::= TEXTUAL-CONVENTION
            STATUS current
            DESCRIPTION 
                "The different types of optional SIB (System Information Blocks) supported in LTE.
                Note that SIBs 1 and 2 are not included here as they are mandatory."
            SYNTAX INTEGER
                {
                sib3(0),
                sib4(1),
                sib5(2),
                sib6(3),
                sib7(4),
                sib8(5),
                sib9(6),
                sib10(7),
                sib11(8)
                }

    
--
-- Node definitions
--
    
        -- 1.3.6.1.4.1.989.1.20.1.1
        asLteStkConformance OBJECT IDENTIFIER ::= { asLteStk 1 }

        
        -- 1.3.6.1.4.1.989.1.20.1.1.1
        asLteStkCompliance MODULE-COMPLIANCE
            STATUS current
            DESCRIPTION 
                "Description."
            MODULE -- this module
                MANDATORY-GROUPS { asLteStkObjectGroup }
            ::= { asLteStkConformance 1 }

        
        -- 1.3.6.1.4.1.989.1.20.1.1.2
        asLteStkObjectGroup OBJECT-GROUP
            OBJECTS { asLteStkStackIndex, asLteStkStackOperationalStatusChangedTrapEnabled, asLteStkStackStatusOperationalStatus, asLteStkStackStatusOperationalStatusInfo, asLteStkStackCfgResetRequest, 
                asLteStkCellStatusDummyObject, asLteStkCellCfgMaxUeSupported, asLteStkCellCfgMibDlBandwidth, asLteStkCellCfgMibPhichDuration, asLteStkCellCfgMibPhichResource, 
                asLteStkCellSib1CfgCellReserved, asLteStkCellSib1CfgCellBarred, asLteStkCellSib1IntraFreqReselectionAllowed, asLteStkCellSib1qRxLevMin, asLteStkCellSib1qRxLevMinOffset, 
                asLteStkCellSib1qMax, asLteStkCellSib1Sib2Periodicity, asLteStkCellSib1Sib3Periodicity, asLteStkCellSib1Sib4Periodicity, asLteStkCellSib1Sib5Periodicity, 
                asLteStkCellSib1SiWindowLength, asLteStkCellSib1SiValueTag, asLteStkCellSib2CfgBcchModificationPeriodCoeff, asLteStkCellSib2CfgPcchDefaultPagingCycle, asLteStkCellSib2CfgPcchnB, 
                asLteStkCellSib2CfgPdschReferenceSignalPower, asLteStkCellSib2CfgPdschPb, asLteStkCellSib2CfgPuschnSB, asLteStkCellSib2CfgPuschHoppingMode, asLteStkCellSib2CfgPuschHoppingOffset, 
                asLteStkCellSib2CfgPuschEnable64QAM, asLteStkCellSib2CfgPuschGroupHoppingEnabled, asLteStkCellSib2CfgPuschGroupAssignment, asLteStkCellSib2CfgPuschSequenceHoppingEnabled, asLteStkCellSib2CfgPuschCyclicShift, 
                asLteStkCellSib2CfgPucchDeltaShift, asLteStkCellSib2CfgPucchnRBCQI, asLteStkCellSib2CfgPucchnCSAN, asLteStkCellSib2CfgPucchn1PucchAn, asLteStkCellSib2CfgSrsUlBandwidthConfig, 
                asLteStkCellSib2CfgSrsSubframeConfig, asLteStkCellSib2CfgSrsAckNackSimultaneousTx, asLteStkCellSib2CfgSrsMaxUpPts, asLteStkCellSib2CfgUlP0NominalPUSCH, asLteStkCellSib2CfgUlP0NominalPUCCH, 
                asLteStkCellSib2CfgUlPowerControlAlpha, asLteStkCellSib2CfgUlDeltaFPUCCHFormat1, asLteStkCellSib2CfgUlDeltaFPUCCHFormat1b, asLteStkCellSib2CfgUlDeltaFPUCCHFormat2, asLteStkCellSib2CfgUlDeltaFPUCCHFormat2a, 
                asLteStkCellSib2CfgUlDeltaFPUCCHFormat2b, asLteStkCellSib2CfgUlDeltaPreambleMsg3, asLteStkCellSib2CfgUlCyclicPrefixLength, asLteStkCellSib2CfgUeTimerT300, asLteStkCellSib2CfgUeTimerT301, 
                asLteStkCellSib2CfgUeTimerT310, asLteStkCellSib2CfgUeConstantN310, asLteStkCellSib2CfgUeTimerT311, asLteStkCellSib2CfgUeConstantN311, asLteStkCellSib2CfgUlCarrierFrequency, 
                asLteStkCellSib2CfgUlBandwidth, asLteStkCellSib2CfgAdditionalSpectrumEmission, asLteStkCellSib2CfgTimeAlignmentTimer, asLteStkCellSib3CfgNCellChangeMedium, asLteStkCellSib3CfgNCellChangeHigh, 
                asLteStkCellSib3CfgNonIntraSearch, asLteStkCellSib3CfgThreshServingLow, asLteStkCellSib3CfgCellReselectionPriority, asLteStkCellSib3CfgQRxLevMin, asLteStkCellSib3CfgPMax, 
                asLteStkCellSib3CfgSIntraSearch, asLteStkCellSib3CfgAllowedMeasBandwidth, asLteStkCellSib3CfgPresenceAntennaPort1, asLteStkCellSib3CfgNeighCellConfig, asLteStkCellSib3CfgTReselectionEUTRA, 
                asLteStkCellSib4CfgCellIntraListSize, asLteStkCellSib4CfgCellIntraPhyCellId, asLteStkCellSib4CfgCellIntraQOffsetCell, asLteStkCellSib4CfgCellBlackListSize, asLteStkCellSib4CfgCellBlackCellStartCellId, 
                asLteStkCellSib4CfgCellBlackCellRange, asLteStkCellSib4CfgCellCSGCellPhyIdStart, asLteStkCellSib4CfgCellCSGCellIdRange, asLteStkCellSib5CfgDlCarrierFrequency, asLteStkCellSib5CfgqRxLevMin, 
                asLteStkCellSib5CfgTReselectionEUTRA, asLteStkCellSib5CfgThreshXHigh, asLteStkCellSib5CfgThreshXLow, asLteStkCellSib5CfgAllowedMeasBandwidth, asLteStkCellSib5CfgPresenceAntennaPort1, 
                asLteStkCellSib5CfgCellReselectionPriority, asLteStkCellSib5CfgNeighCellConfig, asLteStkCellSib5CfgQOffsetFreq, asLteStkCellRachCfgNumberOfRAPreambles, asLteStkCellRachCfgMessageSizeGroupA, 
                asLteStkCellRachCfgNumberOfGroupARAPreambles, asLteStkCellRachCfgPrachRootSequenceIndex, asLteStkCellRachCfgPrachConfigurationIndex, asLteStkCellRachCfgPrachZeroCorrelationZoneConfig, asLteStkCellRachCfgPrachHighSpeedFlag, 
                asLteStkCellRachCfgPrachFrequencyOffset, asLteStkCellRachCfgMessagePowerOffsetGroupB, asLteStkCellRachCfgPowerRampingStep, asLteStkCellRachCfgPreambleInitialRcvdTargetPower, asLteStkCellRachCfgPreambleTransMax, 
                asLteStkCellRachCfgRAResponseWindowSize, asLteStkCellRachCfgMacContentionResolutionTimer, asLteStkCellRachCfgMaxHarqMsg3Tx, asLteStkCellRachCfgPrachResource, asLteStkCellCfgUeCategory, 
                asLteStkCellDedCfgSrbTPollRetransmit, asLteStkCellDedCfgSrbPollPdu, asLteStkCellDedCfgSrbPollByte, asLteStkCellDedCfgSrbMaxRetxThreshold, asLteStkCellDedCfgSrbTReordering, 
                asLteStkCellDedCfgSrbTStatusProhibit, asLteStkCellDedCfgSrb1Priority, asLteStkCellDedCfgSrb2Priority, asLteStkCellDedCfgSrbPriBitRate, asLteStkCellDedCfgSrbBucketSizeDuration, 
                asLteStkCellDedCfgDrbLogicalChannelGroup, asLteStkCellDedCfgMacUlSCHMaxHARQTx, asLteStkCellDedCfgMacUlSCHPeriodicBSRTimer, asLteStkCellDedCfgMacUlSCHRetxBSRTimer, asLteStkCellDedCfgMacUlSCHTtiBundling, 
                asLteStkCellDedCfgMacTimeAlignmentTimer, asLteStkCellDedCfgMacPeriodicPHRTimer, asLteStkCellDedCfgMacProhibitPHRTimer, asLteStkCellDedCfgMacDlPathLossChange, asLteStkCellDedCfgPhyTddAckNackFeedbackMode, 
                asLteStkCellDedCfgPhyUlP0UePusch, asLteStkCellDedCfgPhyUlP0UePucch, asLteStkCellDedCfgPhyUlDeltaMCSEnabled, asLteStkCellDedCfgPhyUlAccumulationEnabled, asLteStkCellDedCfgPhyUlPSRSOffset, 
                asLteStkCellDedCfgPhyUlFilterCoefficient, asLteStkCellDedCfgPhyBetaOffsetACKIndex, asLteStkCellDedCfgPhyBetaOffsetRIIndex, asLteStkCellDedCfgPhyBetaOffsetCQIIndex, asLteStkCellDedCfgPhyCqiReportingMode, 
                asLteStkCellDedCfgPhyNomPdschRsEpreOffset, asLteStkCellDedCfgPhyCqiPucchResourceIndex, asLteStkCellDedCfgPhyCqiPmiConfigIndex, asLteStkCellDedCfgPhyCqiRIConfigIndex, asLteStkCellDedCfgPhySimultaneousAckNackAndCqi, 
                asLteStkCellDedCfgPhySrPucchResourceIndex, asLteStkCellDedCfgPhyDsrTransMax, asLteStkCellDedCfgPhyPdschAckNackRepFactor, asLteStkCellDedCfgPhyN1PucchAckNackRep, asLteStkCellDedCfgUeTransmissionMode, 
                asLteStkCellDedCfgDrbPdcpDiscardTimer, asLteStkCellDedCfgDrbPdcpStatusRptReq, asLteStkCellDedCfgDrbTPollRetransmit, asLteStkCellDedCfgDrbPollPdu, asLteStkCellDedCfgDrbPollByte, 
                asLteStkCellDedCfgDrbMaxRetxThreshold, asLteStkCellDedCfgDrbTReordering, asLteStkCellDedCfgDrbTStatusProhibit, asLteStkCellDedCfgDrbLogicalChannelPriority, asLteStkCellDedCfgDrbPriBitRate, 
                asLteStkCellDedCfgDrbBucketSizeDuration, asLteStkCellDedCfgSrbLogicalChannelGroup, asLteStkMacCfgPeriodicCqiReportingMode, asLteStkMacCfgPeriodicCqiPeriodicity, asLteStkMacCfgPeriodicCqiSubFrameOffset, 
                asLteStkMacCfgPeriodicCqiOffset, asLteStkMacCfgPeriodicCqiCfgK, asLteStkMacCfgPeriodicCqiPMIConfigIndex, asLteStkMacCfgHARQDeltaOffset, asLteStkMacCfgTimingAlignmentTimerPresent, 
                asLteStkMacCfgTimingAlignmentTimerValue, asLteStkMacCfgUlTrgCqi, asLteStkMacCfgNumMacInst, asLteStkMacCfgMaxUEPerUlSubframe, asLteStkMacCfgMaxUEPerDlSubframe, 
                asLteStkMacCfgMaxUlBwPerUe, asLteStkMacCfgMaxDlBwPerUe, asLteStkMacCfgMaxDlRetxBwPerUe, asLteStkMacCfgMaxNewUeDlPerTti, asLteStkMacCfgMaxNewUeUlPerTti, 
                asLteStkMacCfgNumTxAntennas, asLteStkMacCfgDlCyclicPrefixLength, asLteStkMacCfgDlMaxHARQTx, asLteStkMacCfgDlMaxMsg4HARQTx, asLteStkMacCfgStartRnti, 
                asLteStkMacCfgRntiSize, asLteStkMacCfgControlFormatIndicator, asLteStkMacCfgBcchPchRaCodeRate, asLteStkMacCfgPdcchCodeRate, asLteStkMacCfgPuschSubbandStart, 
                asLteStkMacCfgPuschNumOfSubbands, asLteStkMacCfgPuschSizeOfSubbands, asLteStkMacCfgPuschSizeSubbandDmrs, asLteStkMacCfgDlfsEnabled, asLteStkMacCfgDlfsType, 
                asLteStkMacCfgDlfsThresholdCqi, asLteStkMacCfgPhichNg, asLteStkSchedulerSiRetxCnt, asLteStkMacCfgPucchPwrFmt3RntiStart, asLteStkMacCfgPucchPwrFmt3RntiSize, 
                asLteStkMacCfgPucchPwrFmt3aRntiStart, asLteStkMacCfgPucchPwrFmt3aRntiSize, asLteStkMacCfgPuschPwrFmt3RntiStart, asLteStkMacCfgPuschPwrFmt3RntiSize, asLteStkMacCfgPuschPwrFmt3aRntiStart, 
                asLteStkMacCfgPuschPwrFmt3aRntiSize, asLteStkMacCfgDfltUEBitRate, asLteStkMacCfgDfltUEQosGbr, asLteStkMacCfgDfltUEQosMbr, asLteStkMacCfgDfltUEQosQci, 
                asLteStkMacCfgPreambleSetCfgValid, asLteStkMacCfgPreambleSetCfgStart, asLteStkMacCfgPreambleSetCfgSize, asLteStkMacCfgNumPrachResources, asLteStkMacCfgNumCmnLogicalChannels, 
                asLteStkMacCfgSubcarrierSpacing, asLteStkCellCfgBchTBSize, asLteStkCellCfgDlSCHTBSize, asLteStkCellSib1TddSubframeAssignmnent, asLteStkCellSib1TddSubframeCfg, 
                asLteStkCellDedCfgPdschDlPowerAllocation, asLteStkMacCfgUeCqiInitialValue, asLteStkMacCfgUeCqiFormatIndicator, asLteStkMacCfgUeCqiSubBandK, asLteStkMacCfgTxAntennaSelection, 
                asLteStkCellDedCfgPhyN2TxAntennaTm3, asLteStkCellDedCfgPhyN4TxAntennaTm3, asLteStkCellDedCfgPhyCodebookRestrictionPresent, asLteStkCellCfgChannelBandwidth, asLteStkCellCfgInactivityTimerInterval, 
                asLteStkCellCfgInactivityTimerMaxExpires, asLteStkCellCfgSctpServiceType, asLteStkCellCfgRxGain, asLteStkCellCfgTxPower, asLteStkCellCfgUplinkFreq, 
                asLteStkCellCfgDownlinkFreq, asLteStkMacCfgTxSrsSubframeConfigPrd, asLteStkStackCfgOperationalStatus, asLteStkStackRunningStatusChangedTrapEnabled, asLteStkStackCfgEnbIpAddressType, 
                asLteStkStackCfgEnbIpAddress, asLteStkStackCfgMmeIpAddressType, asLteStkStackCfgMmeIpAddress, asLteStkStackCfgUplinkScheduler, asLteStkStackCfgDownlinkScheduler, 
                asLteStkStackStatusRunningStatus, asLteStkStackStatusRunningStatusInfo, asLteStkCellCfgMcc, asLteStkCellCfgMnc, asLteStkCellCfgCellId, 
                asLteStkCellCfgFreqBand, asLteStkCellCfgDuplexMode, asLteStkCellCfgModulation, asLteStkCellCfgTac }
            STATUS current
            DESCRIPTION 
                "Description."
            ::= { asLteStkConformance 2 }

        
        -- 1.3.6.1.4.1.989.1.20.1.1.3
        asLteStkNotificationGroup NOTIFICATION-GROUP
            NOTIFICATIONS { asLteStkStackOperationalStatusChangedTrap, asLteStkStackRunningStatusChangedTrap }
            STATUS current
            DESCRIPTION 
                "Description."
            ::= { asLteStkConformance 3 }

        
        -- 1.3.6.1.4.1.989.1.20.1.2
        asLteStkNotifications OBJECT IDENTIFIER ::= { asLteStk 2 }

        
        -- 1.3.6.1.4.1.989.1.20.1.2.0
        asLteStkTrapPrefix OBJECT IDENTIFIER ::= { asLteStkNotifications 0 }

        
        -- 1.3.6.1.4.1.989.1.20.1.2.0.1
        asLteStkStackRunningStatusChangedTrap NOTIFICATION-TYPE
            OBJECTS { asLteStkStackStatusRunningStatus, asLteStkStackStatusRunningStatusInfo }
            STATUS current
            DESCRIPTION 
                "Signifies that the running state of the LTE stack has changed.  Trap should only be raised on 
                transition into or out of the failed state."
            ::= { asLteStkTrapPrefix 1 }

        
        -- 1.3.6.1.4.1.989.1.20.1.2.0.2
        asLteStkStackOperationalStatusChangedTrap NOTIFICATION-TYPE
            OBJECTS { asLteStkStackStatusOperationalStatus, asLteStkStackStatusOperationalStatusInfo }
            STATUS current
            DESCRIPTION 
                "Signifies that LTE stack operational status has changed."
            ::= { asLteStkTrapPrefix 2 }

        
        -- 1.3.6.1.4.1.989.1.20.1.2.1
        asLteStkTrapControlTable OBJECT-TYPE
            SYNTAX SEQUENCE OF AsLteStkTrapControlEntry
            MAX-ACCESS not-accessible
            STATUS current
            DESCRIPTION
                "Defines enabled/disabled controls for each traps independently. 
                The traps are enabled/disabled simulanously across the all cells/sectors of the stack."
            ::= { asLteStkNotifications 1 }

        
        -- 1.3.6.1.4.1.989.1.20.1.2.1.1
        asLteStkTrapControlEntry OBJECT-TYPE
            SYNTAX AsLteStkTrapControlEntry
            MAX-ACCESS not-accessible
            STATUS current
            DESCRIPTION
                "Single row."
            INDEX { asLteStkTrapControlIndex }
            ::= { asLteStkTrapControlTable 1 }

        
        AsLteStkTrapControlEntry ::=
            SEQUENCE { 
                asLteStkTrapControlIndex
                    INTEGER,
                asLteStkStackRunningStatusChangedTrapEnabled
                    AsCmnTcBooleanSwitch,
                asLteStkStackOperationalStatusChangedTrapEnabled
                    AsCmnTcBooleanSwitch
             }

        -- 1.3.6.1.4.1.989.1.20.1.2.1.1.1
        asLteStkTrapControlIndex OBJECT-TYPE
            SYNTAX INTEGER (1)
            MAX-ACCESS not-accessible
            STATUS current
            DESCRIPTION
                "Arbitrary index - one row only."
            ::= { asLteStkTrapControlEntry 1 }

        
        -- 1.3.6.1.4.1.989.1.20.1.2.1.1.2
        asLteStkStackRunningStatusChangedTrapEnabled OBJECT-TYPE
            SYNTAX AsCmnTcBooleanSwitch
            MAX-ACCESS read-write
            STATUS current
            DESCRIPTION
                "Enables/disables the LTE Stack Running Status change Trap"
            DEFVAL { booleanTrue }
            ::= { asLteStkTrapControlEntry 2 }

        
        -- 1.3.6.1.4.1.989.1.20.1.2.1.1.3
        asLteStkStackOperationalStatusChangedTrapEnabled OBJECT-TYPE
            SYNTAX AsCmnTcBooleanSwitch
            MAX-ACCESS read-write
            STATUS current
            DESCRIPTION
                "Enables/disables the LTE Stack Operational Status change Trap"
            DEFVAL { booleanTrue }
            ::= { asLteStkTrapControlEntry 3 }

        
        -- 1.3.6.1.4.1.989.1.20.1.3
        asLteStkDevice OBJECT IDENTIFIER ::= { asLteStk 3 }

        
        -- 1.3.6.1.4.1.989.1.20.1.3.1
        asLteStkStackCfgTable OBJECT-TYPE
            SYNTAX SEQUENCE OF AsLteStkStackCfgEntry
            MAX-ACCESS not-accessible
            STATUS current
            DESCRIPTION
                "Table grouping per LTE stack configuration properties."
            ::= { asLteStkDevice 1 }

        
        -- 1.3.6.1.4.1.989.1.20.1.3.1.1
        asLteStkStackCfgEntry OBJECT-TYPE
            SYNTAX AsLteStkStackCfgEntry
            MAX-ACCESS not-accessible
            STATUS current
            DESCRIPTION
                "Description."
            INDEX { asLteStkStackIndex }
            ::= { asLteStkStackCfgTable 1 }

        
        AsLteStkStackCfgEntry ::=
            SEQUENCE { 
                asLteStkStackIndex
                    Integer32,
                asLteStkStackCfgResetRequest
                    AsCmnTcResetCmd,
                asLteStkStackCfgOperationalStatus
                    AsCmnTcOperationalStatus,
                asLteStkStackCfgEnbIpAddressType
                    InetAddressType,
                asLteStkStackCfgEnbIpAddress
                    InetAddress,
                asLteStkStackCfgMmeIpAddressType
                    InetAddressType,
                asLteStkStackCfgMmeIpAddress
                    InetAddress,
                asLteStkStackCfgUplinkScheduler
                    AsLteStkSchedulerType,
                asLteStkStackCfgDownlinkScheduler
                    AsLteStkSchedulerType
             }

        -- 1.3.6.1.4.1.989.1.20.1.3.1.1.1
        asLteStkStackIndex OBJECT-TYPE
            SYNTAX Integer32 (1)
            MAX-ACCESS accessible-for-notify
            STATUS current
            DESCRIPTION
                "Arbitrary index - only one instance ever."
            ::= { asLteStkStackCfgEntry 1 }

        
        -- 1.3.6.1.4.1.989.1.20.1.3.1.1.2
        asLteStkStackCfgResetRequest OBJECT-TYPE
            SYNTAX AsCmnTcResetCmd
            MAX-ACCESS read-write
            STATUS current
            DESCRIPTION
                "Request to reset the stack"
            DEFVAL { resetCmdIdle }
            ::= { asLteStkStackCfgEntry 2 }

        
        -- 1.3.6.1.4.1.989.1.20.1.3.1.1.3
        asLteStkStackCfgOperationalStatus OBJECT-TYPE
            SYNTAX AsCmnTcOperationalStatus
            MAX-ACCESS read-write
            STATUS current
            DESCRIPTION
                "The requested operational status for the stack."
            DEFVAL { operationalStatusOutOfService }
            ::= { asLteStkStackCfgEntry 3 }

        
        -- 1.3.6.1.4.1.989.1.20.1.3.1.1.4
        asLteStkStackCfgEnbIpAddressType OBJECT-TYPE
            SYNTAX InetAddressType
            MAX-ACCESS read-write
            STATUS current
            DESCRIPTION
                "The type of IP address (IPv4 or IPv6) used by the eNodeB."
            DEFVAL { ipv4 }
            ::= { asLteStkStackCfgEntry 4 }

        
        -- 1.3.6.1.4.1.989.1.20.1.3.1.1.5
        asLteStkStackCfgEnbIpAddress OBJECT-TYPE
            SYNTAX InetAddress
            MAX-ACCESS read-write
            STATUS current
            DESCRIPTION
                "The IPv4 or IPv6 address of the eNodeB"
            DEFVAL { "0.0.0.0" }
            ::= { asLteStkStackCfgEntry 5 }

        
        -- 1.3.6.1.4.1.989.1.20.1.3.1.1.6
        asLteStkStackCfgMmeIpAddressType OBJECT-TYPE
            SYNTAX InetAddressType
            MAX-ACCESS read-write
            STATUS current
            DESCRIPTION
                "The type of IP address (IPv4 or IPv6) used by the MME (Mobile Management Entity) in the core Network."
            DEFVAL { ipv4 }
            ::= { asLteStkStackCfgEntry 6 }

        
        -- 1.3.6.1.4.1.989.1.20.1.3.1.1.7
        asLteStkStackCfgMmeIpAddress OBJECT-TYPE
            SYNTAX InetAddress
            MAX-ACCESS read-write
            STATUS current
            DESCRIPTION
                "The IPv4 or IPv6 address of the MME (Mobile Management Entity) in the core Network."
            DEFVAL { "0.0.0.0" }
            ::= { asLteStkStackCfgEntry 7 }

        
        -- 1.3.6.1.4.1.989.1.20.1.3.1.1.8
        asLteStkStackCfgUplinkScheduler OBJECT-TYPE
            SYNTAX AsLteStkSchedulerType
            MAX-ACCESS read-write
            STATUS current
            DESCRIPTION
                "The type of MAC scheduler being used by the stack for the uplink."
            DEFVAL { schedulerDefaultCC }
            ::= { asLteStkStackCfgEntry 8 }

        
        -- 1.3.6.1.4.1.989.1.20.1.3.1.1.9
        asLteStkStackCfgDownlinkScheduler OBJECT-TYPE
            SYNTAX AsLteStkSchedulerType
            MAX-ACCESS read-write
            STATUS current
            DESCRIPTION
                "The type of MAC scheduler being used by the stack for the downlink."
            DEFVAL { schedulerDefaultCC }
            ::= { asLteStkStackCfgEntry 9 }

        
        -- 1.3.6.1.4.1.989.1.20.1.3.2
        asLteStkStackStatusTable OBJECT-TYPE
            SYNTAX SEQUENCE OF AsLteStkStackStatusEntry
            MAX-ACCESS not-accessible
            STATUS current
            DESCRIPTION
                "Table grouping per LTE stack status properties."
            ::= { asLteStkDevice 2 }

        
        -- 1.3.6.1.4.1.989.1.20.1.3.2.1
        asLteStkStackStatusEntry OBJECT-TYPE
            SYNTAX AsLteStkStackStatusEntry
            MAX-ACCESS not-accessible
            STATUS current
            DESCRIPTION
                "Description."
            INDEX { asLteStkStackIndex }
            ::= { asLteStkStackStatusTable 1 }

        
        AsLteStkStackStatusEntry ::=
            SEQUENCE { 
                asLteStkStackStatusRunningStatus
                    AsCmnTcRunningStatus,
                asLteStkStackStatusRunningStatusInfo
                    DisplayString,
                asLteStkStackStatusOperationalStatus
                    AsCmnTcOperationalStatus,
                asLteStkStackStatusOperationalStatusInfo
                    DisplayString
             }

        -- 1.3.6.1.4.1.989.1.20.1.3.2.1.1
        asLteStkStackStatusRunningStatus OBJECT-TYPE
            SYNTAX AsCmnTcRunningStatus
            MAX-ACCESS read-only
            STATUS current
            DESCRIPTION
                "The current running status for the LTE stack."
            ::= { asLteStkStackStatusEntry 1 }

        
        -- 1.3.6.1.4.1.989.1.20.1.3.2.1.2
        asLteStkStackStatusRunningStatusInfo OBJECT-TYPE
            SYNTAX DisplayString
            MAX-ACCESS read-only
            STATUS current
            DESCRIPTION
                "Provides further information on the LTE Stack Running Status"
            ::= { asLteStkStackStatusEntry 2 }

        
        -- 1.3.6.1.4.1.989.1.20.1.3.2.1.3
        asLteStkStackStatusOperationalStatus OBJECT-TYPE
            SYNTAX AsCmnTcOperationalStatus
            MAX-ACCESS read-only
            STATUS current
            DESCRIPTION
                "The current operational status for the LTE stack."
            ::= { asLteStkStackStatusEntry 3 }

        
        -- 1.3.6.1.4.1.989.1.20.1.3.2.1.4
        asLteStkStackStatusOperationalStatusInfo OBJECT-TYPE
            SYNTAX DisplayString
            MAX-ACCESS read-only
            STATUS current
            DESCRIPTION
                "Provides further information on the LTE Stack Operational Status"
            ::= { asLteStkStackStatusEntry 4 }

        
        -- 1.3.6.1.4.1.989.1.20.1.4
        asLteStkIf OBJECT IDENTIFIER ::= { asLteStk 4 }

        
        -- 1.3.6.1.4.1.989.1.20.1.4.1
        asLteStkCellCfgTable OBJECT-TYPE
            SYNTAX SEQUENCE OF AsLteStkCellCfgEntry
            MAX-ACCESS not-accessible
            STATUS current
            DESCRIPTION
                "Table grouping per LTE cell configuration properties."
            ::= { asLteStkIf 1 }

        
        -- 1.3.6.1.4.1.989.1.20.1.4.1.1
        asLteStkCellCfgEntry OBJECT-TYPE
            SYNTAX AsLteStkCellCfgEntry
            MAX-ACCESS not-accessible
            STATUS current
            DESCRIPTION
                "Description."
            INDEX { ifIndex }
            ::= { asLteStkCellCfgTable 1 }

        
        AsLteStkCellCfgEntry ::=
            SEQUENCE { 
                asLteStkCellCfgMcc
                    Integer32,
                asLteStkCellCfgMnc
                    Integer32,
                asLteStkCellCfgCellId
                    Integer32,
                asLteStkCellCfgFreqBand
                    Integer32,
                asLteStkCellCfgDuplexMode
                    AsLteStkDuplexMode,
                asLteStkCellCfgModulation
                    AsLteStkModulation,
                asLteStkCellCfgTac
                    Integer32,
                asLteStkCellCfgMaxUeSupported
                    Integer32,
                asLteStkCellCfgMibDlBandwidth
                    AsLteStkMibDlBandwidthType,
                asLteStkCellCfgMibPhichDuration
                    AsLteStkMibPhichDurationType,
                asLteStkCellCfgMibPhichResource
                    AsLteStkMibPhichResourceType,
                asLteStkCellCfgBchTBSize
                    Integer32,
                asLteStkCellCfgDlSCHTBSize
                    Integer32,
                asLteStkCellCfgUeCategory
                    Integer32,
                asLteStkCellCfgRxGain
                    Integer32,
                asLteStkCellCfgTxPower
                    Integer32,
                asLteStkCellCfgUplinkFreq
                    Integer32,
                asLteStkCellCfgDownlinkFreq
                    Integer32,
                asLteStkCellCfgChannelBandwidth
                    AsLteStkCellCfgChannelBandwidthType,
                asLteStkCellCfgInactivityTimerInterval
                    Integer32,
                asLteStkCellCfgInactivityTimerMaxExpires
                    Integer32,
                asLteStkCellCfgSctpServiceType
                    AsLteStkCellCfgSctpServiceType
             }

        -- 1.3.6.1.4.1.989.1.20.1.4.1.1.1
        asLteStkCellCfgMcc OBJECT-TYPE
            SYNTAX Integer32 (200..999)
            MAX-ACCESS read-write
            STATUS current
            DESCRIPTION
                "The Mobile Country Code as defined in ITU-T E.212"
            ::= { asLteStkCellCfgEntry 1 }

        
        -- 1.3.6.1.4.1.989.1.20.1.4.1.1.2
        asLteStkCellCfgMnc OBJECT-TYPE
            SYNTAX Integer32 (0..999)
            MAX-ACCESS read-write
            STATUS current
            DESCRIPTION
                "The Mobile Network Code (unique per MCC)"
            ::= { asLteStkCellCfgEntry 2 }

        
        -- 1.3.6.1.4.1.989.1.20.1.4.1.1.3
        asLteStkCellCfgCellId OBJECT-TYPE
            SYNTAX Integer32 (0..503)
            MAX-ACCESS read-write
            STATUS current
            DESCRIPTION
                "Cell Identifier as defined in 3GPP spec 36.211"
            ::= { asLteStkCellCfgEntry 3 }

        
        -- 1.3.6.1.4.1.989.1.20.1.4.1.1.4
        asLteStkCellCfgFreqBand OBJECT-TYPE
            SYNTAX Integer32 (1..40)
            MAX-ACCESS read-write
            STATUS current
            DESCRIPTION
                "Operating Band ID as defined in Table 5.5-1 of 3GPP TS 36.101.  
                Bands in the range 1 to 17 inclusive are FDD; bands in the range 33 to 40 are TDD."
            ::= { asLteStkCellCfgEntry 4 }

        
        -- 1.3.6.1.4.1.989.1.20.1.4.1.1.5
        asLteStkCellCfgDuplexMode OBJECT-TYPE
            SYNTAX AsLteStkDuplexMode
            MAX-ACCESS read-write
            STATUS current
            DESCRIPTION
                "The duplex mode.  There is a dependency between the duplex Mode and the Frequency Band selected."
            ::= { asLteStkCellCfgEntry 5 }

        
        -- 1.3.6.1.4.1.989.1.20.1.4.1.1.6
        asLteStkCellCfgModulation OBJECT-TYPE
            SYNTAX AsLteStkModulation
            MAX-ACCESS read-write
            STATUS current
            DESCRIPTION
                "Maximum modulation to use on the uplink."
            ::= { asLteStkCellCfgEntry 6 }

        
        -- 1.3.6.1.4.1.989.1.20.1.4.1.1.7
        asLteStkCellCfgTac OBJECT-TYPE
            SYNTAX Integer32 (1..65535)
            MAX-ACCESS read-write
            STATUS current
            DESCRIPTION
                "The tracking area code is used to identify a tracking area within the scope of a PLMN
                (Public Land Mobile Network)."
            ::= { asLteStkCellCfgEntry 7 }

        
        -- 1.3.6.1.4.1.989.1.20.1.4.1.1.8
        asLteStkCellCfgMaxUeSupported OBJECT-TYPE
            SYNTAX Integer32 (1..500)
            MAX-ACCESS read-write
            STATUS current
            DESCRIPTION
                "The maximum number of UEs supported per cell."
            DEFVAL { 32 }
            ::= { asLteStkCellCfgEntry 8 }

        
        -- 1.3.6.1.4.1.989.1.20.1.4.1.1.9
        asLteStkCellCfgMibDlBandwidth OBJECT-TYPE
            SYNTAX AsLteStkMibDlBandwidthType
            MAX-ACCESS read-write
            STATUS current
            DESCRIPTION
                "Maximum modulation to use on the uplink."
            DEFVAL { 3 }
            ::= { asLteStkCellCfgEntry 9 }

        
        -- 1.3.6.1.4.1.989.1.20.1.4.1.1.10
        asLteStkCellCfgMibPhichDuration OBJECT-TYPE
            SYNTAX AsLteStkMibPhichDurationType
            MAX-ACCESS read-write
            STATUS current
            DESCRIPTION
                "Maximum modulation to use on the uplink."
            ::= { asLteStkCellCfgEntry 10 }

        
        -- 1.3.6.1.4.1.989.1.20.1.4.1.1.11
        asLteStkCellCfgMibPhichResource OBJECT-TYPE
            SYNTAX AsLteStkMibPhichResourceType
            MAX-ACCESS read-write
            STATUS current
            DESCRIPTION
                "Maximum modulation to use on the uplink."
            ::= { asLteStkCellCfgEntry 11 }

        
        -- 1.3.6.1.4.1.989.1.20.1.4.1.1.12
        asLteStkCellCfgBchTBSize OBJECT-TYPE
            SYNTAX Integer32
            MAX-ACCESS read-write
            STATUS current
            DESCRIPTION
                "The size of BCCH message mapped on to BCH transport channel.
                This is usually the MIB (Master Information Block)."
            DEFVAL { 3 }
            ::= { asLteStkCellCfgEntry 12 }

        
        -- 1.3.6.1.4.1.989.1.20.1.4.1.1.13
        asLteStkCellCfgDlSCHTBSize OBJECT-TYPE
            SYNTAX Integer32
            MAX-ACCESS read-write
            STATUS current
            DESCRIPTION
                "The size of the BCCH message mapped on to DL-SCH transport channel.
                This can be either SIB1 or SIB2."
            DEFVAL { 32 }
            ::= { asLteStkCellCfgEntry 13 }

        
        -- 1.3.6.1.4.1.989.1.20.1.4.1.1.14
        asLteStkCellCfgUeCategory OBJECT-TYPE
            SYNTAX Integer32 (1..5)
            MAX-ACCESS read-write
            STATUS current
            DESCRIPTION
                "UE category. Can be any of the five types. Capabilities of a UE increase with increasing category.
                IE ue-Category(TS 36.331)"
            DEFVAL { 2 }
            ::= { asLteStkCellCfgEntry 14 }

        
        -- 1.3.6.1.4.1.989.1.20.1.4.1.1.15
        asLteStkCellCfgRxGain OBJECT-TYPE
            SYNTAX Integer32
            UNITS "1/100 dB"
            MAX-ACCESS read-write
            STATUS current
            DESCRIPTION
                "End to end gain from antenna to PHY in 1/100ths dB."
            ::= { asLteStkCellCfgEntry 15 }

        
        -- 1.3.6.1.4.1.989.1.20.1.4.1.1.16
        asLteStkCellCfgTxPower OBJECT-TYPE
            SYNTAX Integer32
            UNITS "1/100 dBm"
            MAX-ACCESS read-write
            STATUS current
            DESCRIPTION
                "Power transmitted from antenna connector in 1/100ths dBm."
            ::= { asLteStkCellCfgEntry 16 }

        
        -- 1.3.6.1.4.1.989.1.20.1.4.1.1.17
        asLteStkCellCfgUplinkFreq OBJECT-TYPE
            SYNTAX Integer32
            UNITS "kHz"
            MAX-ACCESS read-write
            STATUS current
            DESCRIPTION
                "The uplink centre frequency in kHz"
            ::= { asLteStkCellCfgEntry 17 }

        
        -- 1.3.6.1.4.1.989.1.20.1.4.1.1.18
        asLteStkCellCfgDownlinkFreq OBJECT-TYPE
            SYNTAX Integer32
            UNITS "kHz"
            MAX-ACCESS read-write
            STATUS current
            DESCRIPTION
                "The downlink centre frequency in kHz"
            ::= { asLteStkCellCfgEntry 18 }

        
        -- 1.3.6.1.4.1.989.1.20.1.4.1.1.19
        asLteStkCellCfgChannelBandwidth OBJECT-TYPE
            SYNTAX AsLteStkCellCfgChannelBandwidthType
            MAX-ACCESS read-write
            STATUS current
            DESCRIPTION
                "The bandwidth of the channel in MHz.  Note that the values stored in properties 
                asLteStkCellCfgMibDlBandwidth and asLteStkCellSib2CfgSrsUlBandwidthConfig should match the 
                enum setting here, as a dlBandwidth of 50 resource blocks is equivalent to a channel bandwidth of 10MHz."
            ::= { asLteStkCellCfgEntry 19 }

        
        -- 1.3.6.1.4.1.989.1.20.1.4.1.1.20
        asLteStkCellCfgInactivityTimerInterval OBJECT-TYPE
            SYNTAX Integer32
            UNITS "msecs"
            MAX-ACCESS read-write
            STATUS current
            DESCRIPTION
                "The value of the inactivity timer interval. Zero indicates the timer is not to be started."
            ::= { asLteStkCellCfgEntry 20 }

        
        -- 1.3.6.1.4.1.989.1.20.1.4.1.1.21
        asLteStkCellCfgInactivityTimerMaxExpires OBJECT-TYPE
            SYNTAX Integer32
            MAX-ACCESS read-write
            STATUS current
            DESCRIPTION
                "The maximum number of times the inactivity timer can expire."
            ::= { asLteStkCellCfgEntry 21 }

        
        -- 1.3.6.1.4.1.989.1.20.1.4.1.1.22
        asLteStkCellCfgSctpServiceType OBJECT-TYPE
            SYNTAX AsLteStkCellCfgSctpServiceType
            MAX-ACCESS read-write
            STATUS current
            DESCRIPTION
                "Defines whether SCTP runs over raw or udp sockets."
            ::= { asLteStkCellCfgEntry 22 }

        
        -- 1.3.6.1.4.1.989.1.20.1.4.2
        asLteStkCellStatusTable OBJECT-TYPE
            SYNTAX SEQUENCE OF AsLteStkCellStatusEntry
            MAX-ACCESS not-accessible
            STATUS current
            DESCRIPTION
                "Description."
            ::= { asLteStkIf 2 }

        
        -- 1.3.6.1.4.1.989.1.20.1.4.2.1
        asLteStkCellStatusEntry OBJECT-TYPE
            SYNTAX AsLteStkCellStatusEntry
            MAX-ACCESS not-accessible
            STATUS current
            DESCRIPTION
                "Description."
            INDEX { ifIndex }
            ::= { asLteStkCellStatusTable 1 }

        
        AsLteStkCellStatusEntry ::=
            SEQUENCE { 
                asLteStkCellStatusDummyObject
                    Integer32
             }

        -- 1.3.6.1.4.1.989.1.20.1.4.2.1.1
        asLteStkCellStatusDummyObject OBJECT-TYPE
            SYNTAX Integer32
            MAX-ACCESS read-only
            STATUS current
            DESCRIPTION
                "Replace with first real object in this table"
            ::= { asLteStkCellStatusEntry 1 }

        
        -- 1.3.6.1.4.1.989.1.20.1.4.3
        asLteStkCellSib1CfgTable OBJECT-TYPE
            SYNTAX SEQUENCE OF AsLteStkCellSib1CfgEntry
            MAX-ACCESS not-accessible
            STATUS current
            DESCRIPTION
                "Configuration IEs held in SIB1 (System Information Block 1)
                SIB1 contains information relevant when evaluating if a UE is allowed to access a cell 
                and defines the scheduling of other system information."
            ::= { asLteStkIf 3 }

        
        -- 1.3.6.1.4.1.989.1.20.1.4.3.1
        asLteStkCellSib1CfgEntry OBJECT-TYPE
            SYNTAX AsLteStkCellSib1CfgEntry
            MAX-ACCESS not-accessible
            STATUS current
            DESCRIPTION
                "Description."
            INDEX { ifIndex }
            ::= { asLteStkCellSib1CfgTable 1 }

        
        AsLteStkCellSib1CfgEntry ::=
            SEQUENCE { 
                asLteStkCellSib1CfgCellReserved
                    AsLteStkCellReservedForOperatorUseType,
                asLteStkCellSib1CfgCellBarred
                    AsLteStkCellBarredType,
                asLteStkCellSib1IntraFreqReselectionAllowed
                    AsLteStkCellIntraFreqReselectionAllowedType,
                asLteStkCellSib1qRxLevMin
                    Integer32,
                asLteStkCellSib1qRxLevMinOffset
                    Integer32,
                asLteStkCellSib1qMax
                    Integer32,
                asLteStkCellSib1Sib2Periodicity
                    AsLteStkSibPeriodicityType,
                asLteStkCellSib1Sib3Periodicity
                    AsLteStkSibPeriodicityType,
                asLteStkCellSib1Sib4Periodicity
                    AsLteStkSibPeriodicityType,
                asLteStkCellSib1Sib5Periodicity
                    AsLteStkSibPeriodicityType,
                asLteStkCellSib1SiWindowLength
                    AsLteStkSystemInfoWindowLengthType,
                asLteStkCellSib1SiValueTag
                    Integer32,
                asLteStkCellSib1TddSubframeAssignmnent
                    AsLteStkCellSib1TddSubframeAssignmnentType,
                asLteStkCellSib1TddSubframeCfg
                    Integer32
             }

        -- 1.3.6.1.4.1.989.1.20.1.4.3.1.1
        asLteStkCellSib1CfgCellReserved OBJECT-TYPE
            SYNTAX AsLteStkCellReservedForOperatorUseType
            MAX-ACCESS read-write
            STATUS current
            DESCRIPTION
                "Defines if the cell is meant for Operator use or not. 
                IE cellReservedForOperatorUse(TS36.331)"
            DEFVAL { 1 }
            ::= { asLteStkCellSib1CfgEntry 1 }

        
        -- 1.3.6.1.4.1.989.1.20.1.4.3.1.2
        asLteStkCellSib1CfgCellBarred OBJECT-TYPE
            SYNTAX AsLteStkCellBarredType
            MAX-ACCESS read-write
            STATUS current
            DESCRIPTION
                "Defines if the cell is barred for use or not. 
                IE cellBarred(TS36.331)"
            DEFVAL { 1 }
            ::= { asLteStkCellSib1CfgEntry 2 }

        
        -- 1.3.6.1.4.1.989.1.20.1.4.3.1.3
        asLteStkCellSib1IntraFreqReselectionAllowed OBJECT-TYPE
            SYNTAX AsLteStkCellIntraFreqReselectionAllowedType
            MAX-ACCESS read-write
            STATUS current
            DESCRIPTION
                "Defines if Cell Intra Frequency Selection is allowed or not. 
                IE intraFreqReselection (TS36.311)"
            DEFVAL { 1 }
            ::= { asLteStkCellSib1CfgEntry 3 }

        
        -- 1.3.6.1.4.1.989.1.20.1.4.3.1.4
        asLteStkCellSib1qRxLevMin OBJECT-TYPE
            SYNTAX Integer32 (-70..-22)
            UNITS "dBm"
            MAX-ACCESS read-write
            STATUS current
            DESCRIPTION
                "Defines the value to indicate the minimum received RSRP (Reference Signal Received Power)
                level for cell-reselection. 
                IE q-RxLevMin(TS36.331)"
            DEFVAL { -50 }
            ::= { asLteStkCellSib1CfgEntry 4 }

        
        -- 1.3.6.1.4.1.989.1.20.1.4.3.1.5
        asLteStkCellSib1qRxLevMinOffset OBJECT-TYPE
            SYNTAX Integer32 (1..8)
            UNITS "dBm"
            MAX-ACCESS read-write
            STATUS current
            DESCRIPTION
                "Defines the offset to the signalled qRxLevMin which can be considered for evaluation of 
                Cell Reselection Rx Level value. (Spec 36.304).
                IE q-RxLevMinOffset(TS36.331)."
            DEFVAL { 1 }
            ::= { asLteStkCellSib1CfgEntry 5 }

        
        -- 1.3.6.1.4.1.989.1.20.1.4.3.1.6
        asLteStkCellSib1qMax OBJECT-TYPE
            SYNTAX Integer32 (-30..33)
            UNITS "dBm"
            MAX-ACCESS read-write
            STATUS current
            DESCRIPTION
                "Defines the limit on the UE's uplink transmission power. 
                Corresponds to PEMAX in Spec 36.101.
                IE p-Max(TS36.331)"
            DEFVAL { 0 }
            ::= { asLteStkCellSib1CfgEntry 6 }

        
        -- 1.3.6.1.4.1.989.1.20.1.4.3.1.7
        asLteStkCellSib1Sib2Periodicity OBJECT-TYPE
            SYNTAX AsLteStkSibPeriodicityType
            UNITS "radioFrames"
            MAX-ACCESS read-write
            STATUS current
            DESCRIPTION
                "Defines the periodicity of System Information Block 2 (SIB2).
                IE schedulingInfoList(TS36.331)"
            DEFVAL { 1 }
            ::= { asLteStkCellSib1CfgEntry 7 }

        
        -- 1.3.6.1.4.1.989.1.20.1.4.3.1.8
        asLteStkCellSib1Sib3Periodicity OBJECT-TYPE
            SYNTAX AsLteStkSibPeriodicityType
            UNITS "radioFrames"
            MAX-ACCESS read-write
            STATUS current
            DESCRIPTION
                "Defines the periodicity of System Information Block 3 (SIB3).
                IE schedulingInfoList(TS36.331)"
            DEFVAL { 2 }
            ::= { asLteStkCellSib1CfgEntry 8 }

        
        -- 1.3.6.1.4.1.989.1.20.1.4.3.1.9
        asLteStkCellSib1Sib4Periodicity OBJECT-TYPE
            SYNTAX AsLteStkSibPeriodicityType
            UNITS "radioFrames"
            MAX-ACCESS read-write
            STATUS current
            DESCRIPTION
                "Defines the periodicity of System Information Block 4 (SIB4).
                IE schedulingInfoList(TS36.331)"
            DEFVAL { 3 }
            ::= { asLteStkCellSib1CfgEntry 9 }

        
        -- 1.3.6.1.4.1.989.1.20.1.4.3.1.10
        asLteStkCellSib1Sib5Periodicity OBJECT-TYPE
            SYNTAX AsLteStkSibPeriodicityType
            UNITS "radioFrames"
            MAX-ACCESS read-write
            STATUS current
            DESCRIPTION
                "Defines the periodicity of System Information Block 5 (SIB5).
                IE schedulingInfoList(TS36.331)"
            DEFVAL { 3 }
            ::= { asLteStkCellSib1CfgEntry 10 }

        
        -- 1.3.6.1.4.1.989.1.20.1.4.3.1.11
        asLteStkCellSib1SiWindowLength OBJECT-TYPE
            SYNTAX AsLteStkSystemInfoWindowLengthType
            UNITS "msecs"
            MAX-ACCESS read-write
            STATUS current
            DESCRIPTION
                "Window Length for all the System Information Block messages. 
                The SI message can be transmitted within the siWindowLength any number of times.
                IE si-WindowLength(TS36.331)"
            DEFVAL { 5 }
            ::= { asLteStkCellSib1CfgEntry 11 }

        
        -- 1.3.6.1.4.1.989.1.20.1.4.3.1.12
        asLteStkCellSib1SiValueTag OBJECT-TYPE
            SYNTAX Integer32 (0..31)
            MAX-ACCESS read-write
            STATUS current
            DESCRIPTION
                "System Information Value Tag indicates any change in the SI messages.
                IE systemInfoValueTag(TS36.331)"
            DEFVAL { 0 }
            ::= { asLteStkCellSib1CfgEntry 12 }

        
        -- 1.3.6.1.4.1.989.1.20.1.4.3.1.13
        asLteStkCellSib1TddSubframeAssignmnent OBJECT-TYPE
            SYNTAX AsLteStkCellSib1TddSubframeAssignmnentType
            MAX-ACCESS read-write
            STATUS current
            DESCRIPTION
                "DL/UL subframe config type in TDD.
                IE subframeAssignment.(TS36.331)"
            DEFVAL { 2 }
            ::= { asLteStkCellSib1CfgEntry 13 }

        
        -- 1.3.6.1.4.1.989.1.20.1.4.3.1.14
        asLteStkCellSib1TddSubframeCfg OBJECT-TYPE
            SYNTAX Integer32
            MAX-ACCESS read-write
            STATUS current
            DESCRIPTION
                "Special subframe configuration for TDD.
                IE specialSubframePatterns.(TS36.331)"
            DEFVAL { 8 }
            ::= { asLteStkCellSib1CfgEntry 14 }

        
        -- 1.3.6.1.4.1.989.1.20.1.4.4
        asLteStkCellSib2CfgTable OBJECT-TYPE
            SYNTAX SEQUENCE OF AsLteStkCellSib2CfgEntry
            MAX-ACCESS not-accessible
            STATUS current
            DESCRIPTION
                "Configuration IEs held in SIB2 (System Information Block 2)
                SIB2 contains radio resource configuration information that is common for all UEs"
            ::= { asLteStkIf 4 }

        
        -- 1.3.6.1.4.1.989.1.20.1.4.4.1
        asLteStkCellSib2CfgEntry OBJECT-TYPE
            SYNTAX AsLteStkCellSib2CfgEntry
            MAX-ACCESS not-accessible
            STATUS current
            DESCRIPTION
                "Description."
            INDEX { ifIndex }
            ::= { asLteStkCellSib2CfgTable 1 }

        
        AsLteStkCellSib2CfgEntry ::=
            SEQUENCE { 
                asLteStkCellSib2CfgBcchModificationPeriodCoeff
                    AsLteStkCellSib2CfgBcchModificationPeriodCoeffType,
                asLteStkCellSib2CfgPcchDefaultPagingCycle
                    AsLteStkCellSib2CfgPcchDefaultPagingCycleType,
                asLteStkCellSib2CfgPcchnB
                    AsLteStkCellSib2CfgPcchnBType,
                asLteStkCellSib2CfgPdschReferenceSignalPower
                    Integer32,
                asLteStkCellSib2CfgPdschPb
                    Integer32,
                asLteStkCellSib2CfgPuschnSB
                    Integer32,
                asLteStkCellSib2CfgPuschHoppingMode
                    AsLteStkCellSib2CfgPuschHoppingModeType,
                asLteStkCellSib2CfgPuschHoppingOffset
                    Integer32,
                asLteStkCellSib2CfgPuschEnable64QAM
                    AsCmnTcBooleanSwitch,
                asLteStkCellSib2CfgPuschGroupHoppingEnabled
                    AsCmnTcBooleanSwitch,
                asLteStkCellSib2CfgPuschGroupAssignment
                    Integer32,
                asLteStkCellSib2CfgPuschSequenceHoppingEnabled
                    AsCmnTcBooleanSwitch,
                asLteStkCellSib2CfgPuschCyclicShift
                    Integer32,
                asLteStkCellSib2CfgPucchDeltaShift
                    AsLteStkCellSib2CfgPucchDeltaShiftType,
                asLteStkCellSib2CfgPucchnRBCQI
                    Integer32,
                asLteStkCellSib2CfgPucchnCSAN
                    Integer32,
                asLteStkCellSib2CfgPucchn1PucchAn
                    Integer32,
                asLteStkCellSib2CfgSrsUlBandwidthConfig
                    AsLteStkCellSib2CfgSrsUlBandwidthConfigType,
                asLteStkCellSib2CfgSrsSubframeConfig
                    AsLteStkCellSib2CfgSrsUlSubframeConfigType,
                asLteStkCellSib2CfgSrsAckNackSimultaneousTx
                    AsCmnTcBooleanSwitch,
                asLteStkCellSib2CfgSrsMaxUpPts
                    Integer32,
                asLteStkCellSib2CfgUlP0NominalPUSCH
                    Integer32,
                asLteStkCellSib2CfgUlP0NominalPUCCH
                    Integer32,
                asLteStkCellSib2CfgUlPowerControlAlpha
                    AsLteStkCellSib2CfgUlPowerControlAlphaType,
                asLteStkCellSib2CfgUlDeltaFPUCCHFormat1
                    AsLteStkCellSib2CfgUlDeltaFPUCCHFormat1Type,
                asLteStkCellSib2CfgUlDeltaFPUCCHFormat1b
                    AsLteStkCellSib2CfgUlDeltaFPUCCHFormat1bType,
                asLteStkCellSib2CfgUlDeltaFPUCCHFormat2
                    AsLteStkCellSib2CfgUlDeltaFPUCCHFormat2Type,
                asLteStkCellSib2CfgUlDeltaFPUCCHFormat2a
                    AsLteStkCellSib2CfgUlDeltaFPUCCHFormat2aType,
                asLteStkCellSib2CfgUlDeltaFPUCCHFormat2b
                    AsLteStkCellSib2CfgUlDeltaFPUCCHFormat2bType,
                asLteStkCellSib2CfgUlDeltaPreambleMsg3
                    Integer32,
                asLteStkCellSib2CfgUlCyclicPrefixLength
                    AsLteStkCellCfgUlCyclicPrefixLengthType,
                asLteStkCellSib2CfgUeTimerT300
                    AsLteStkCellSib2CfgUeTimerT3xxType,
                asLteStkCellSib2CfgUeTimerT301
                    AsLteStkCellSib2CfgUeTimerT3xxType,
                asLteStkCellSib2CfgUeTimerT310
                    AsLteStkCellSib2CfgUeTimerT3xxType,
                asLteStkCellSib2CfgUeConstantN310
                    AsLteStkCellSib2CfgUeConstantN310Type,
                asLteStkCellSib2CfgUeTimerT311
                    AsLteStkCellSib2CfgUeTimerT3xxType,
                asLteStkCellSib2CfgUeConstantN311
                    AsLteStkCellSib2CfgUeConstantN311Type,
                asLteStkCellSib2CfgUlCarrierFrequency
                    Integer32,
                asLteStkCellSib2CfgUlBandwidth
                    AsLteStkCellSib2CfgUlBandwidthType,
                asLteStkCellSib2CfgAdditionalSpectrumEmission
                    Integer32,
                asLteStkCellSib2CfgTimeAlignmentTimer
                    AsLteStkCellCfgTimeAlignmentTimerType
             }

        -- 1.3.6.1.4.1.989.1.20.1.4.4.1.1
        asLteStkCellSib2CfgBcchModificationPeriodCoeff OBJECT-TYPE
            SYNTAX AsLteStkCellSib2CfgBcchModificationPeriodCoeffType
            UNITS "radioFrames"
            MAX-ACCESS read-write
            STATUS current
            DESCRIPTION
                "Modification period of the BCCH messages.
                IE modificationPeriodCoeff(TS 36.331)"
            DEFVAL { 1 }
            ::= { asLteStkCellSib2CfgEntry 1 }

        
        -- 1.3.6.1.4.1.989.1.20.1.4.4.1.2
        asLteStkCellSib2CfgPcchDefaultPagingCycle OBJECT-TYPE
            SYNTAX AsLteStkCellSib2CfgPcchDefaultPagingCycleType
            UNITS "radioFrames"
            MAX-ACCESS read-write
            STATUS current
            DESCRIPTION
                "Default paging cycle interval. Measured in radio frames. 
                UE should check for paging messages as per the configured cycle.
                IE defaultPagingCycle(TS 36.331)"
            DEFVAL { 2 }
            ::= { asLteStkCellSib2CfgEntry 2 }

        
        -- 1.3.6.1.4.1.989.1.20.1.4.4.1.3
        asLteStkCellSib2CfgPcchnB OBJECT-TYPE
            SYNTAX AsLteStkCellSib2CfgPcchnBType
            MAX-ACCESS read-write
            STATUS current
            DESCRIPTION
                "The parameter used to derive Paging Frame and Paging occasion as in TS36.304. 
                IE nB(TS 36.331)"
            DEFVAL { 2 }
            ::= { asLteStkCellSib2CfgEntry 3 }

        
        -- 1.3.6.1.4.1.989.1.20.1.4.4.1.4
        asLteStkCellSib2CfgPdschReferenceSignalPower OBJECT-TYPE
            SYNTAX Integer32 (-60..50)
            UNITS "dBm"
            MAX-ACCESS read-write
            STATUS current
            DESCRIPTION
                "The reference signal power in downlink. Measured in dBm. 
                IE referenceSignalPower(TS 36.331)"
            DEFVAL { 0 }
            ::= { asLteStkCellSib2CfgEntry 4 }

        
        -- 1.3.6.1.4.1.989.1.20.1.4.4.1.5
        asLteStkCellSib2CfgPdschPb OBJECT-TYPE
            SYNTAX Integer32 (0..3)
            MAX-ACCESS read-write
            STATUS current
            DESCRIPTION
                "Parameter used in Downlink Power Allocation as defined in 36.213 section 5.2.
                IE p-b(TS 36.331)"
            DEFVAL { 0 }
            ::= { asLteStkCellSib2CfgEntry 5 }

        
        -- 1.3.6.1.4.1.989.1.20.1.4.4.1.6
        asLteStkCellSib2CfgPuschnSB OBJECT-TYPE
            SYNTAX Integer32 (1..4)
            MAX-ACCESS read-write
            STATUS current
            DESCRIPTION
                "Parameter defined in 36.211 section 5.2. 
                IE nSB(TS 36.331)"
            DEFVAL { 1 }
            ::= { asLteStkCellSib2CfgEntry 6 }

        
        -- 1.3.6.1.4.1.989.1.20.1.4.4.1.7
        asLteStkCellSib2CfgPuschHoppingMode OBJECT-TYPE
            SYNTAX AsLteStkCellSib2CfgPuschHoppingModeType
            MAX-ACCESS read-write
            STATUS current
            DESCRIPTION
                "Hopping mode indicates whether Inter subframe or Intra and Inter subframe 
                is supported.
                IE hoppingMode(TS 36.331)"
            DEFVAL { 0 }
            ::= { asLteStkCellSib2CfgEntry 7 }

        
        -- 1.3.6.1.4.1.989.1.20.1.4.4.1.8
        asLteStkCellSib2CfgPuschHoppingOffset OBJECT-TYPE
            SYNTAX Integer32 (0..98)
            MAX-ACCESS read-write
            STATUS current
            DESCRIPTION
                "Hopping Offset in PUSCH.
                IE pusch-HoppingOffset(TS 36.331)"
            DEFVAL { 8 }
            ::= { asLteStkCellSib2CfgEntry 8 }

        
        -- 1.3.6.1.4.1.989.1.20.1.4.4.1.9
        asLteStkCellSib2CfgPuschEnable64QAM OBJECT-TYPE
            SYNTAX AsCmnTcBooleanSwitch
            MAX-ACCESS read-write
            STATUS current
            DESCRIPTION
                "Denotes whether 64 QAM modulation for PUSCH is enabled. 
                IE enable64QAM(TS 36.331)"
            DEFVAL { 0 }
            ::= { asLteStkCellSib2CfgEntry 9 }

        
        -- 1.3.6.1.4.1.989.1.20.1.4.4.1.10
        asLteStkCellSib2CfgPuschGroupHoppingEnabled OBJECT-TYPE
            SYNTAX AsCmnTcBooleanSwitch
            MAX-ACCESS read-write
            STATUS current
            DESCRIPTION
                "Denotes whether Group Hopping in PUSCH is enabled
                IE groupHoppingEnabled(TS 36.331)"
            DEFVAL { 0 }
            ::= { asLteStkCellSib2CfgEntry 10 }

        
        -- 1.3.6.1.4.1.989.1.20.1.4.4.1.11
        asLteStkCellSib2CfgPuschGroupAssignment OBJECT-TYPE
            SYNTAX Integer32 (0..29)
            MAX-ACCESS read-write
            STATUS current
            DESCRIPTION
                "Group Assignment in PUSCH. 
                IE groupAssignmentPUSCH(TS 36.331)"
            DEFVAL { 0 }
            ::= { asLteStkCellSib2CfgEntry 11 }

        
        -- 1.3.6.1.4.1.989.1.20.1.4.4.1.12
        asLteStkCellSib2CfgPuschSequenceHoppingEnabled OBJECT-TYPE
            SYNTAX AsCmnTcBooleanSwitch
            MAX-ACCESS read-write
            STATUS current
            DESCRIPTION
                "Enabling/Disabling Sequence Group Hopping in PUSCH.  
                IE sequenceGroupHopping(TS 36.331)"
            DEFVAL { 0 }
            ::= { asLteStkCellSib2CfgEntry 12 }

        
        -- 1.3.6.1.4.1.989.1.20.1.4.4.1.13
        asLteStkCellSib2CfgPuschCyclicShift OBJECT-TYPE
            SYNTAX Integer32 (0..7)
            MAX-ACCESS read-write
            STATUS current
            DESCRIPTION
                "Cyclic Shift in PUSCH. 
                IE cyclicShift(TS 36.331)"
            DEFVAL { 0 }
            ::= { asLteStkCellSib2CfgEntry 13 }

        
        -- 1.3.6.1.4.1.989.1.20.1.4.4.1.14
        asLteStkCellSib2CfgPucchDeltaShift OBJECT-TYPE
            SYNTAX AsLteStkCellSib2CfgPucchDeltaShiftType
            MAX-ACCESS read-write
            STATUS current
            DESCRIPTION
                "Delta PUCCH Shift. 
                IE deltaPUCCH-Shift(TS 36.331)"
            DEFVAL { 0 }
            ::= { asLteStkCellSib2CfgEntry 14 }

        
        -- 1.3.6.1.4.1.989.1.20.1.4.4.1.15
        asLteStkCellSib2CfgPucchnRBCQI OBJECT-TYPE
            SYNTAX Integer32 (0..98)
            UNITS "resourceBlocks"
            MAX-ACCESS read-write
            STATUS current
            DESCRIPTION
                "Number of Resource Blocks available for use by PUCCH formats 2/2a/2b transmission.
                IE nRB-CQI(TS 36.331)"
            DEFVAL { 1 }
            ::= { asLteStkCellSib2CfgEntry 15 }

        
        -- 1.3.6.1.4.1.989.1.20.1.4.4.1.16
        asLteStkCellSib2CfgPucchnCSAN OBJECT-TYPE
            SYNTAX Integer32 (0..7)
            MAX-ACCESS read-write
            STATUS current
            DESCRIPTION
                "Number of cyclic shift used for PUCCH formats 1/1a/1b.
                IE nCS-AN(TS 36.331)"
            DEFVAL { 0 }
            ::= { asLteStkCellSib2CfgEntry 16 }

        
        -- 1.3.6.1.4.1.989.1.20.1.4.4.1.17
        asLteStkCellSib2CfgPucchn1PucchAn OBJECT-TYPE
            SYNTAX Integer32 (0..2047)
            MAX-ACCESS read-write
            STATUS current
            DESCRIPTION
                "N1-PUCCH. Refer 36.213 Section 10.1.  
                IE n1PUCCH-AN(TS 36.331)"
            DEFVAL { 1 }
            ::= { asLteStkCellSib2CfgEntry 17 }

        
        -- 1.3.6.1.4.1.989.1.20.1.4.4.1.18
        asLteStkCellSib2CfgSrsUlBandwidthConfig OBJECT-TYPE
            SYNTAX AsLteStkCellSib2CfgSrsUlBandwidthConfigType
            MAX-ACCESS read-write
            STATUS current
            DESCRIPTION
                "Parameter used in bandwidth Configuration for SRS (Sounding Reference Signal) in Uplink. 
                IE srs-BandwidthConfig(TS 36.331)"
            DEFVAL { 2 }
            ::= { asLteStkCellSib2CfgEntry 18 }

        
        -- 1.3.6.1.4.1.989.1.20.1.4.4.1.19
        asLteStkCellSib2CfgSrsSubframeConfig OBJECT-TYPE
            SYNTAX AsLteStkCellSib2CfgSrsUlSubframeConfigType
            MAX-ACCESS read-write
            STATUS current
            DESCRIPTION
                "Parameters used in subframe configuration for SRS (Sounding Reference Signal) Uplink. 
                IE srs-SubframeConfig(TS 36.331)"
            DEFVAL { 2 }
            ::= { asLteStkCellSib2CfgEntry 19 }

        
        -- 1.3.6.1.4.1.989.1.20.1.4.4.1.20
        asLteStkCellSib2CfgSrsAckNackSimultaneousTx OBJECT-TYPE
            SYNTAX AsCmnTcBooleanSwitch
            MAX-ACCESS read-write
            STATUS current
            DESCRIPTION
                "This variable determines if the transmission of ACK/NACK on PUCCH and SRS
                in one subframe is supported.
                IE ackNackSRS-SimultaneousTransmission(TS 36.331)"
            DEFVAL { 0 }
            ::= { asLteStkCellSib2CfgEntry 20 }

        
        -- 1.3.6.1.4.1.989.1.20.1.4.4.1.21
        asLteStkCellSib2CfgSrsMaxUpPts OBJECT-TYPE
            SYNTAX Integer32 (0)
            MAX-ACCESS read-write
            STATUS current
            DESCRIPTION
                "The presence of this indicates whether reconfiguration of mMaxSRS is valid or not.
                This property is currently forced to value 0.
                IE srs-MaxUpPts(TS 36.331)"
            DEFVAL { 0 }
            ::= { asLteStkCellSib2CfgEntry 21 }

        
        -- 1.3.6.1.4.1.989.1.20.1.4.4.1.22
        asLteStkCellSib2CfgUlP0NominalPUSCH OBJECT-TYPE
            SYNTAX Integer32 (-126..24)
            UNITS "dBm"
            MAX-ACCESS read-write
            STATUS current
            DESCRIPTION
                "Nominal Transmit power in PUSCH. Measured in dBm.
                IE p0-NominalPUSCH(TS 36.331)"
            DEFVAL { -100 }
            ::= { asLteStkCellSib2CfgEntry 22 }

        
        -- 1.3.6.1.4.1.989.1.20.1.4.4.1.23
        asLteStkCellSib2CfgUlP0NominalPUCCH OBJECT-TYPE
            SYNTAX Integer32 (-126..-96)
            UNITS "dBm"
            MAX-ACCESS read-write
            STATUS current
            DESCRIPTION
                "Nominal Transmit power in PUCCH. Measured in dBm.
                IE p0-NominalPUCCH(TS 36.331)"
            DEFVAL { -100 }
            ::= { asLteStkCellSib2CfgEntry 23 }

        
        -- 1.3.6.1.4.1.989.1.20.1.4.4.1.24
        asLteStkCellSib2CfgUlPowerControlAlpha OBJECT-TYPE
            SYNTAX AsLteStkCellSib2CfgUlPowerControlAlphaType
            MAX-ACCESS read-write
            STATUS current
            DESCRIPTION
                "Power control field alpha.  Used in determining the UE Transmit power on
                the PUSCH.
                IE alpha(TS 36.331)"
            DEFVAL { 7 }
            ::= { asLteStkCellSib2CfgEntry 24 }

        
        -- 1.3.6.1.4.1.989.1.20.1.4.4.1.25
        asLteStkCellSib2CfgUlDeltaFPUCCHFormat1 OBJECT-TYPE
            SYNTAX AsLteStkCellSib2CfgUlDeltaFPUCCHFormat1Type
            UNITS "dBm"
            MAX-ACCESS read-write
            STATUS current
            DESCRIPTION
                "Variable used for setting of UE transmit power for PUCCH format 1.(36.213 Sec 5.1.2.1).
                IE deltaF-PUCCH-Format1(TS 36.331)"
            DEFVAL { 1 }
            ::= { asLteStkCellSib2CfgEntry 25 }

        
        -- 1.3.6.1.4.1.989.1.20.1.4.4.1.26
        asLteStkCellSib2CfgUlDeltaFPUCCHFormat1b OBJECT-TYPE
            SYNTAX AsLteStkCellSib2CfgUlDeltaFPUCCHFormat1bType
            UNITS "dBm"
            MAX-ACCESS read-write
            STATUS current
            DESCRIPTION
                "Variable used for setting of UE transmit power for PUCCH format 1b.(36.213 Sec 5.1.2.1).
                IE deltaF-PUCCH-Format1b(TS 36.331)"
            DEFVAL { 1 }
            ::= { asLteStkCellSib2CfgEntry 26 }

        
        -- 1.3.6.1.4.1.989.1.20.1.4.4.1.27
        asLteStkCellSib2CfgUlDeltaFPUCCHFormat2 OBJECT-TYPE
            SYNTAX AsLteStkCellSib2CfgUlDeltaFPUCCHFormat2Type
            UNITS "dBm"
            MAX-ACCESS read-write
            STATUS current
            DESCRIPTION
                "Variable used for setting of UE transmit power for PUCCH format 2.(36.213 Sec 5.1.2.1).
                IE deltaF-PUCCH-Format2(TS 36.331)"
            DEFVAL { 1 }
            ::= { asLteStkCellSib2CfgEntry 27 }

        
        -- 1.3.6.1.4.1.989.1.20.1.4.4.1.28
        asLteStkCellSib2CfgUlDeltaFPUCCHFormat2a OBJECT-TYPE
            SYNTAX AsLteStkCellSib2CfgUlDeltaFPUCCHFormat2aType
            UNITS "dBm"
            MAX-ACCESS read-write
            STATUS current
            DESCRIPTION
                "Variable used for setting of UE transmit power for PUCCH format 2a.(36.213 Sec 5.1.2.1).
                IE deltaF-PUCCH-Format2(TS 36.331)"
            DEFVAL { 1 }
            ::= { asLteStkCellSib2CfgEntry 28 }

        
        -- 1.3.6.1.4.1.989.1.20.1.4.4.1.29
        asLteStkCellSib2CfgUlDeltaFPUCCHFormat2b OBJECT-TYPE
            SYNTAX AsLteStkCellSib2CfgUlDeltaFPUCCHFormat2bType
            UNITS "dBm"
            MAX-ACCESS read-write
            STATUS current
            DESCRIPTION
                "Variable used for setting of UE transmit power for PUCCH format 2b.(36.213 Sec 5.1.2.1).
                IE deltaF-PUCCH-Format2(TS 36.331)"
            DEFVAL { 1 }
            ::= { asLteStkCellSib2CfgEntry 29 }

        
        -- 1.3.6.1.4.1.989.1.20.1.4.4.1.30
        asLteStkCellSib2CfgUlDeltaPreambleMsg3 OBJECT-TYPE
            SYNTAX Integer32 (-1..6)
            UNITS "dBm"
            MAX-ACCESS read-write
            STATUS current
            DESCRIPTION
                "Nominal Transmit power in PUCCH. Measured in dB. 
                IE deltaPreambleMsg3(TS 36.331)"
            DEFVAL { 1 }
            ::= { asLteStkCellSib2CfgEntry 30 }

        
        -- 1.3.6.1.4.1.989.1.20.1.4.4.1.31
        asLteStkCellSib2CfgUlCyclicPrefixLength OBJECT-TYPE
            SYNTAX AsLteStkCellCfgUlCyclicPrefixLengthType
            MAX-ACCESS read-write
            STATUS current
            DESCRIPTION
                "Denotes whether Cyclic Prefix in Uplink is normal or extended.
                IE ul-CyclicPrefixLength(TS 36.331)"
            DEFVAL { 0 }
            ::= { asLteStkCellSib2CfgEntry 31 }

        
        -- 1.3.6.1.4.1.989.1.20.1.4.4.1.32
        asLteStkCellSib2CfgUeTimerT300 OBJECT-TYPE
            SYNTAX AsLteStkCellSib2CfgUeTimerT3xxType
            UNITS "mSecs"
            MAX-ACCESS read-write
            STATUS current
            DESCRIPTION
                "T300 timer value. 
                IE t300 (TS 36.331)"
            DEFVAL { 0 }
            ::= { asLteStkCellSib2CfgEntry 32 }

        
        -- 1.3.6.1.4.1.989.1.20.1.4.4.1.33
        asLteStkCellSib2CfgUeTimerT301 OBJECT-TYPE
            SYNTAX AsLteStkCellSib2CfgUeTimerT3xxType
            UNITS "mSecs"
            MAX-ACCESS read-write
            STATUS current
            DESCRIPTION
                "T301 timer value. 
                IE t301 (TS 36.331)"
            DEFVAL { 0 }
            ::= { asLteStkCellSib2CfgEntry 33 }

        
        -- 1.3.6.1.4.1.989.1.20.1.4.4.1.34
        asLteStkCellSib2CfgUeTimerT310 OBJECT-TYPE
            SYNTAX AsLteStkCellSib2CfgUeTimerT3xxType
            UNITS "mSecs"
            MAX-ACCESS read-write
            STATUS current
            DESCRIPTION
                "T310 timer value. 
                IE t310 (TS 36.331)"
            DEFVAL { 0 }
            ::= { asLteStkCellSib2CfgEntry 34 }

        
        -- 1.3.6.1.4.1.989.1.20.1.4.4.1.35
        asLteStkCellSib2CfgUeConstantN310 OBJECT-TYPE
            SYNTAX AsLteStkCellSib2CfgUeConstantN310Type
            MAX-ACCESS read-write
            STATUS current
            DESCRIPTION
                "N310 constant value. 
                IE n310 (TS 36.331)"
            DEFVAL { 0 }
            ::= { asLteStkCellSib2CfgEntry 35 }

        
        -- 1.3.6.1.4.1.989.1.20.1.4.4.1.36
        asLteStkCellSib2CfgUeTimerT311 OBJECT-TYPE
            SYNTAX AsLteStkCellSib2CfgUeTimerT3xxType
            UNITS "mSecs"
            MAX-ACCESS read-write
            STATUS current
            DESCRIPTION
                "T311 timer value. 
                IE t311 (TS 36.331)"
            DEFVAL { 0 }
            ::= { asLteStkCellSib2CfgEntry 36 }

        
        -- 1.3.6.1.4.1.989.1.20.1.4.4.1.37
        asLteStkCellSib2CfgUeConstantN311 OBJECT-TYPE
            SYNTAX AsLteStkCellSib2CfgUeConstantN311Type
            MAX-ACCESS read-write
            STATUS current
            DESCRIPTION
                "N311 constant value. 
                IE n311 (TS 36.331)"
            DEFVAL { 0 }
            ::= { asLteStkCellSib2CfgEntry 37 }

        
        -- 1.3.6.1.4.1.989.1.20.1.4.4.1.38
        asLteStkCellSib2CfgUlCarrierFrequency OBJECT-TYPE
            SYNTAX Integer32 (0..65535)
            MAX-ACCESS read-write
            STATUS current
            DESCRIPTION
                "UL Carrier Frequency to be used. 
                The value here is the E-UTRA Absolute Radio Frequency Channel Number (EARFCN).
                The carrier frequency in MHz can be calculated using this value and the 
                operating band as described in TS 36.101 Section 5.7.3
                IE ul-CarrierFrequency(TS 36.331)"
            DEFVAL { 0 }
            ::= { asLteStkCellSib2CfgEntry 38 }

        
        -- 1.3.6.1.4.1.989.1.20.1.4.4.1.39
        asLteStkCellSib2CfgUlBandwidth OBJECT-TYPE
            SYNTAX AsLteStkCellSib2CfgUlBandwidthType
            UNITS "resourceBlocks"
            MAX-ACCESS read-write
            STATUS current
            DESCRIPTION
                "UL Bandwidth Available. 
                IE ul-Bandwidth(TS 36.331)"
            DEFVAL { 3 }
            ::= { asLteStkCellSib2CfgEntry 39 }

        
        -- 1.3.6.1.4.1.989.1.20.1.4.4.1.40
        asLteStkCellSib2CfgAdditionalSpectrumEmission OBJECT-TYPE
            SYNTAX Integer32 (1..32)
            MAX-ACCESS read-write
            STATUS current
            DESCRIPTION
                "Additional Spectrum Emission details.(36.101) 
                IE additionalSpectrumEmission(TS 36.331)"
            DEFVAL { 1 }
            ::= { asLteStkCellSib2CfgEntry 40 }

        
        -- 1.3.6.1.4.1.989.1.20.1.4.4.1.41
        asLteStkCellSib2CfgTimeAlignmentTimer OBJECT-TYPE
            SYNTAX AsLteStkCellCfgTimeAlignmentTimerType
            UNITS "subFrames"
            MAX-ACCESS read-write
            STATUS current
            DESCRIPTION
                "Time for which UE is considered time-aligned.(36.321) 
                IE timeAlignmentTimerCommon(TS 36.331)"
            DEFVAL { 7 }
            ::= { asLteStkCellSib2CfgEntry 41 }

        
        -- 1.3.6.1.4.1.989.1.20.1.4.5
        asLteStkCellSib3CfgTable OBJECT-TYPE
            SYNTAX SEQUENCE OF AsLteStkCellSib3CfgEntry
            MAX-ACCESS not-accessible
            STATUS current
            DESCRIPTION
                "Configuration IEs held in SIB3 (System Information Block 3)
                SIB3 contains cell re-selection information common for intra and 
                inter frequency and inter-RAT cell re-selection"
            ::= { asLteStkIf 5 }

        
        -- 1.3.6.1.4.1.989.1.20.1.4.5.1
        asLteStkCellSib3CfgEntry OBJECT-TYPE
            SYNTAX AsLteStkCellSib3CfgEntry
            MAX-ACCESS not-accessible
            STATUS current
            DESCRIPTION
                "Description."
            INDEX { ifIndex }
            ::= { asLteStkCellSib3CfgTable 1 }

        
        AsLteStkCellSib3CfgEntry ::=
            SEQUENCE { 
                asLteStkCellSib3CfgNCellChangeMedium
                    Integer32,
                asLteStkCellSib3CfgNCellChangeHigh
                    Integer32,
                asLteStkCellSib3CfgNonIntraSearch
                    Integer32,
                asLteStkCellSib3CfgThreshServingLow
                    Integer32,
                asLteStkCellSib3CfgCellReselectionPriority
                    Integer32,
                asLteStkCellSib3CfgQRxLevMin
                    Integer32,
                asLteStkCellSib3CfgPMax
                    Integer32,
                asLteStkCellSib3CfgSIntraSearch
                    Integer32,
                asLteStkCellSib3CfgAllowedMeasBandwidth
                    AsLteStkCellCfgAllowedMeasBandwidthType,
                asLteStkCellSib3CfgPresenceAntennaPort1
                    AsCmnTcBooleanSwitch,
                asLteStkCellSib3CfgNeighCellConfig
                    Integer32,
                asLteStkCellSib3CfgTReselectionEUTRA
                    Integer32
             }

        -- 1.3.6.1.4.1.989.1.20.1.4.5.1.1
        asLteStkCellSib3CfgNCellChangeMedium OBJECT-TYPE
            SYNTAX Integer32 (1..16)
            MAX-ACCESS read-write
            STATUS current
            DESCRIPTION
                "Number of cell changes required to enter medium mobility state.(NCR_M in 36.304).
                IE n-CellChangeMedium(TS 36.331)"
            DEFVAL { 1 }
            ::= { asLteStkCellSib3CfgEntry 1 }

        
        -- 1.3.6.1.4.1.989.1.20.1.4.5.1.2
        asLteStkCellSib3CfgNCellChangeHigh OBJECT-TYPE
            SYNTAX Integer32 (1..16)
            MAX-ACCESS read-write
            STATUS current
            DESCRIPTION
                "Number of cell changes required to enter high mobility state.(NCR_M in 36.304).
                IE n-CellChangeMedium(TS 36.331)"
            DEFVAL { 1 }
            ::= { asLteStkCellSib3CfgEntry 2 }

        
        -- 1.3.6.1.4.1.989.1.20.1.4.5.1.3
        asLteStkCellSib3CfgNonIntraSearch OBJECT-TYPE
            SYNTAX Integer32 (0..31)
            UNITS "2 dBm"
            MAX-ACCESS read-write
            STATUS current
            DESCRIPTION
                "The threshold (in dB) for E-UTRAN inter frequency and inter-RAT measurements.
                IE s-NonIntraSearch(TS 36.331)"
            DEFVAL { 0 }
            ::= { asLteStkCellSib3CfgEntry 3 }

        
        -- 1.3.6.1.4.1.989.1.20.1.4.5.1.4
        asLteStkCellSib3CfgThreshServingLow OBJECT-TYPE
            SYNTAX Integer32 (0..31)
            UNITS "2 dBm"
            MAX-ACCESS read-write
            STATUS current
            DESCRIPTION
                "The threshold (in dB) for serving frequency used in reselection 
                evaluation towards lower priority E-UTRAN frequency or RAT. 
                IE threshServingLow(TS 36.331)"
            DEFVAL { 0 }
            ::= { asLteStkCellSib3CfgEntry 4 }

        
        -- 1.3.6.1.4.1.989.1.20.1.4.5.1.5
        asLteStkCellSib3CfgCellReselectionPriority OBJECT-TYPE
            SYNTAX Integer32 (0..7)
            MAX-ACCESS read-write
            STATUS current
            DESCRIPTION
                "The absolute priority of the concerned carrier frequency as used by cell 
                reselection procedure. Value of zero indicates lowest priority.
                IE cellReselectonPriority(TS 36.331)"
            DEFVAL { 4 }
            ::= { asLteStkCellSib3CfgEntry 5 }

        
        -- 1.3.6.1.4.1.989.1.20.1.4.5.1.6
        asLteStkCellSib3CfgQRxLevMin OBJECT-TYPE
            SYNTAX Integer32 (-70..-22)
            UNITS "dBm"
            MAX-ACCESS read-write
            STATUS current
            DESCRIPTION
                "Defines the value to indicate the minimum received RSRP (Reference Signal 
                Received Power) level for intra-frequency cell-reselection. 
                IE q-RxLevMin(TS36.331)"
            DEFVAL { -70 }
            ::= { asLteStkCellSib3CfgEntry 6 }

        
        -- 1.3.6.1.4.1.989.1.20.1.4.5.1.7
        asLteStkCellSib3CfgPMax OBJECT-TYPE
            SYNTAX Integer32 (-30..33)
            UNITS "dBm"
            MAX-ACCESS read-write
            STATUS current
            DESCRIPTION
                "Defines the limit on the UE's uplink transmission power. Corresponds to PEMAX in Spec 36.101.
                Value applicable for intra-frequency neighbouring E-UTRA cells.
                IE p-Max(TS36.331)"
            DEFVAL { 1 }
            ::= { asLteStkCellSib3CfgEntry 7 }

        
        -- 1.3.6.1.4.1.989.1.20.1.4.5.1.8
        asLteStkCellSib3CfgSIntraSearch OBJECT-TYPE
            SYNTAX Integer32 (0..31)
            UNITS "2 dBm"
            MAX-ACCESS read-write
            STATUS current
            DESCRIPTION
                "The threshold (in dB) for intra frequency measurements.
                IE s-IntraSearch(TS 36.331)"
            DEFVAL { 1 }
            ::= { asLteStkCellSib3CfgEntry 8 }

        
        -- 1.3.6.1.4.1.989.1.20.1.4.5.1.9
        asLteStkCellSib3CfgAllowedMeasBandwidth OBJECT-TYPE
            SYNTAX AsLteStkCellCfgAllowedMeasBandwidthType
            UNITS "resourceBlocks"
            MAX-ACCESS read-write
            STATUS current
            DESCRIPTION
                "This indicated the maximum allowed measurement bandwidth on a carrier frequency.
                IE allowedMeasBandwidth(TS 36.331)"
            DEFVAL { 0 }
            ::= { asLteStkCellSib3CfgEntry 9 }

        
        -- 1.3.6.1.4.1.989.1.20.1.4.5.1.10
        asLteStkCellSib3CfgPresenceAntennaPort1 OBJECT-TYPE
            SYNTAX AsCmnTcBooleanSwitch
            MAX-ACCESS read-write
            STATUS current
            DESCRIPTION
                "This field indicates whether all the neighbouring cells use Antenna Port 1.
                IE presenceAntennaPort1(TS 36.331)"
            DEFVAL { 0 }
            ::= { asLteStkCellSib3CfgEntry 10 }

        
        -- 1.3.6.1.4.1.989.1.20.1.4.5.1.11
        asLteStkCellSib3CfgNeighCellConfig OBJECT-TYPE
            SYNTAX Integer32 (0..3)
            MAX-ACCESS read-write
            STATUS current
            DESCRIPTION
                "This field provides information about MBSFN (Multicast and Broadcast Single Freq Network) 
                and TDD UL/DL configs of neighbouring cells.
                0 - Not all neighbouring cells have same MBSFN subframe allocation as serving cell.
                1 - No MBSFN subframes present in neighbouring cells.
                2 - MBSFN subframe allocations of neighbouring cells are identical/subset of that in serving cell.
                3 - Different TDD UL/DL allocation in neighbouring cells.
                IE neighCellConfig(TS 36.331)"
            DEFVAL { 0 }
            ::= { asLteStkCellSib3CfgEntry 11 }

        
        -- 1.3.6.1.4.1.989.1.20.1.4.5.1.12
        asLteStkCellSib3CfgTReselectionEUTRA OBJECT-TYPE
            SYNTAX Integer32 (0..7)
            UNITS "secs"
            MAX-ACCESS read-write
            STATUS current
            DESCRIPTION
                "This field provides the value for cell reselection timer from E-UTRA.
                The value is specified in seconds.
                IE t-ReselectionEUTRA(TS 36.331)"
            DEFVAL { 0 }
            ::= { asLteStkCellSib3CfgEntry 12 }

        
        -- 1.3.6.1.4.1.989.1.20.1.4.6
        asLteStkCellSib4CfgTable OBJECT-TYPE
            SYNTAX SEQUENCE OF AsLteStkCellSib4CfgEntry
            MAX-ACCESS not-accessible
            STATUS current
            DESCRIPTION
                "Configuration IEs held in SIB4 (System Information Block 4)
                SIB4 contains neighbouring cell related information relevant only for intra-frequency 
                cell re-selection."
            ::= { asLteStkIf 6 }

        
        -- 1.3.6.1.4.1.989.1.20.1.4.6.1
        asLteStkCellSib4CfgEntry OBJECT-TYPE
            SYNTAX AsLteStkCellSib4CfgEntry
            MAX-ACCESS not-accessible
            STATUS current
            DESCRIPTION
                "Description."
            INDEX { ifIndex }
            ::= { asLteStkCellSib4CfgTable 1 }

        
        AsLteStkCellSib4CfgEntry ::=
            SEQUENCE { 
                asLteStkCellSib4CfgCellIntraListSize
                    Integer32,
                asLteStkCellSib4CfgCellIntraPhyCellId
                    Integer32,
                asLteStkCellSib4CfgCellIntraQOffsetCell
                    AsLteStkCellCfgQOffsetFreq,
                asLteStkCellSib4CfgCellBlackListSize
                    Integer32,
                asLteStkCellSib4CfgCellBlackCellStartCellId
                    Integer32,
                asLteStkCellSib4CfgCellBlackCellRange
                    AsLteStkCellPhyCellIdRangeType,
                asLteStkCellSib4CfgCellCSGCellPhyIdStart
                    Integer32,
                asLteStkCellSib4CfgCellCSGCellIdRange
                    AsLteStkCellPhyCellIdRangeType
             }

        -- 1.3.6.1.4.1.989.1.20.1.4.6.1.1
        asLteStkCellSib4CfgCellIntraListSize OBJECT-TYPE
            SYNTAX Integer32 (1)
            MAX-ACCESS read-write
            STATUS current
            DESCRIPTION
                "This field provides the number of neighbouring intra-frequency cells listed.
                Currently forced to 1
                IE intraFreqNeighCellList- maxCellIntra(TS 36.331)"
            DEFVAL { 1 }
            ::= { asLteStkCellSib4CfgEntry 1 }

        
        -- 1.3.6.1.4.1.989.1.20.1.4.6.1.2
        asLteStkCellSib4CfgCellIntraPhyCellId OBJECT-TYPE
            SYNTAX Integer32 (0..503)
            MAX-ACCESS read-write
            STATUS current
            DESCRIPTION
                "This field provides the physical cell Id of the neighbouring intra-frequency cell for which
                information is provided.
                IE phyCellId(TS 36.331)"
            DEFVAL { 1 }
            ::= { asLteStkCellSib4CfgEntry 2 }

        
        -- 1.3.6.1.4.1.989.1.20.1.4.6.1.3
        asLteStkCellSib4CfgCellIntraQOffsetCell OBJECT-TYPE
            SYNTAX AsLteStkCellCfgQOffsetFreq
            UNITS "dBm"
            MAX-ACCESS read-write
            STATUS current
            DESCRIPTION
                "This field provides the frequency offset between the serving cell and the cell mentioned
                in asLteStkCellSib4CfgCellIntraPhyCellId. Measured in dB.
                IE q-OffsetCell(TS 36.331)"
            DEFVAL { 1 }
            ::= { asLteStkCellSib4CfgEntry 3 }

        
        -- 1.3.6.1.4.1.989.1.20.1.4.6.1.4
        asLteStkCellSib4CfgCellBlackListSize OBJECT-TYPE
            SYNTAX Integer32 (1)
            MAX-ACCESS read-write
            STATUS current
            DESCRIPTION
                "This field provides the number of black listed cells.
                Currently forced to 1.
                IE intraFreqBlackCellList-maxCellBlack (TS 36.331)"
            DEFVAL { 1 }
            ::= { asLteStkCellSib4CfgEntry 4 }

        
        -- 1.3.6.1.4.1.989.1.20.1.4.6.1.5
        asLteStkCellSib4CfgCellBlackCellStartCellId OBJECT-TYPE
            SYNTAX Integer32 (0..503)
            MAX-ACCESS read-write
            STATUS current
            DESCRIPTION
                "This field provides the start of the physical cell identity range for black listed cells.
                IE start(TS 36.331)"
            DEFVAL { 1 }
            ::= { asLteStkCellSib4CfgEntry 5 }

        
        -- 1.3.6.1.4.1.989.1.20.1.4.6.1.6
        asLteStkCellSib4CfgCellBlackCellRange OBJECT-TYPE
            SYNTAX AsLteStkCellPhyCellIdRangeType
            MAX-ACCESS read-write
            STATUS current
            DESCRIPTION
                "This field indicates the number of physical range cell identities black listed from the 
                start asLteStkCellSib4CfgCellBlackCellStartCellId.
                IE range(TS 36.331)"
            DEFVAL { 0 }
            ::= { asLteStkCellSib4CfgEntry 6 }

        
        -- 1.3.6.1.4.1.989.1.20.1.4.6.1.7
        asLteStkCellSib4CfgCellCSGCellPhyIdStart OBJECT-TYPE
            SYNTAX Integer32 (0..503)
            MAX-ACCESS read-write
            STATUS current
            DESCRIPTION
                "This field provides the start of the physical cell identity range for CSG 
                (Closed Subscriber Group) group.
                IE start(TS 36.331)"
            DEFVAL { 1 }
            ::= { asLteStkCellSib4CfgEntry 7 }

        
        -- 1.3.6.1.4.1.989.1.20.1.4.6.1.8
        asLteStkCellSib4CfgCellCSGCellIdRange OBJECT-TYPE
            SYNTAX AsLteStkCellPhyCellIdRangeType
            MAX-ACCESS read-write
            STATUS current
            DESCRIPTION
                "This field indicates the number of physical range cell identities in CSG (Closed
                Subscriber Group) group from the start asLteStkCellSib4CfgCellCSGCellPhyIdStart.
                IE range(TS 36.331)"
            DEFVAL { 0 }
            ::= { asLteStkCellSib4CfgEntry 8 }

        
        -- 1.3.6.1.4.1.989.1.20.1.4.7
        asLteStkCellSib5CfgTable OBJECT-TYPE
            SYNTAX SEQUENCE OF AsLteStkCellSib5CfgEntry
            MAX-ACCESS not-accessible
            STATUS current
            DESCRIPTION
                "Configuration IEs held in SIB5 (System Information Block 5)
                SIB5 contains information relevant only for inter-frequency cell re-selection i.e.
                information about other E-UTRA frequencies and inter-frequency neighbouring cells 
                relevant for cell re-selection."
            ::= { asLteStkIf 7 }

        
        -- 1.3.6.1.4.1.989.1.20.1.4.7.1
        asLteStkCellSib5CfgEntry OBJECT-TYPE
            SYNTAX AsLteStkCellSib5CfgEntry
            MAX-ACCESS not-accessible
            STATUS current
            DESCRIPTION
                "Description"
            INDEX { ifIndex }
            ::= { asLteStkCellSib5CfgTable 1 }

        
        AsLteStkCellSib5CfgEntry ::=
            SEQUENCE { 
                asLteStkCellSib5CfgDlCarrierFrequency
                    Integer32,
                asLteStkCellSib5CfgqRxLevMin
                    Integer32,
                asLteStkCellSib5CfgTReselectionEUTRA
                    Integer32,
                asLteStkCellSib5CfgThreshXHigh
                    Integer32,
                asLteStkCellSib5CfgThreshXLow
                    Integer32,
                asLteStkCellSib5CfgAllowedMeasBandwidth
                    AsLteStkCellCfgAllowedMeasBandwidthType,
                asLteStkCellSib5CfgPresenceAntennaPort1
                    AsCmnTcBooleanSwitch,
                asLteStkCellSib5CfgCellReselectionPriority
                    Integer32,
                asLteStkCellSib5CfgNeighCellConfig
                    Integer32,
                asLteStkCellSib5CfgQOffsetFreq
                    AsLteStkCellCfgQOffsetFreq
             }

        -- 1.3.6.1.4.1.989.1.20.1.4.7.1.1
        asLteStkCellSib5CfgDlCarrierFrequency OBJECT-TYPE
            SYNTAX Integer32 (0..65535)
            MAX-ACCESS read-write
            STATUS current
            DESCRIPTION
                "DL Carrier Frequency to be used. 
                The value here is the E-UTRA Absolute Radio Frequency Channel Number (EARFCN).
                The carrier frequency in MHz can be calculated using this value and the 
                operating band as described in TS 36.101 Section 5.7.3
                IE dl-CarrierFrequency(TS 36.331)"
            DEFVAL { 15 }
            ::= { asLteStkCellSib5CfgEntry 1 }

        
        -- 1.3.6.1.4.1.989.1.20.1.4.7.1.2
        asLteStkCellSib5CfgqRxLevMin OBJECT-TYPE
            SYNTAX Integer32 (-70..-22)
            UNITS "dBm"
            MAX-ACCESS read-write
            STATUS current
            DESCRIPTION
                "Defines the value to indicate the minimum received RSRP (Reference Signal Received Power)
                level for inter-frequency cell-reselection. 
                IE q-RxLevMin(TS36.331)"
            DEFVAL { -65 }
            ::= { asLteStkCellSib5CfgEntry 2 }

        
        -- 1.3.6.1.4.1.989.1.20.1.4.7.1.3
        asLteStkCellSib5CfgTReselectionEUTRA OBJECT-TYPE
            SYNTAX Integer32 (0..7)
            UNITS "secs"
            MAX-ACCESS read-write
            STATUS current
            DESCRIPTION
                "This field provides the value for inter-frequency cell reselection timer from E-UTRA.
                The value is specified in seconds.
                IE t-ReselectionEUTRA(TS 36.331)"
            DEFVAL { 0 }
            ::= { asLteStkCellSib5CfgEntry 3 }

        
        -- 1.3.6.1.4.1.989.1.20.1.4.7.1.4
        asLteStkCellSib5CfgThreshXHigh OBJECT-TYPE
            SYNTAX Integer32 (0..31)
            UNITS "2 dBm"
            MAX-ACCESS read-write
            STATUS current
            DESCRIPTION
                "This specifies the threshold to be used to reselect towards the 
                higher priority frequency rather than the current frequency.
                IE threshX-High(TS 36.331)"
            DEFVAL { 4 }
            ::= { asLteStkCellSib5CfgEntry 4 }

        
        -- 1.3.6.1.4.1.989.1.20.1.4.7.1.5
        asLteStkCellSib5CfgThreshXLow OBJECT-TYPE
            SYNTAX Integer32 (0..31)
            UNITS "2 dBm"
            MAX-ACCESS read-write
            STATUS current
            DESCRIPTION
                "This specifies the threshold to be used to reselect towards the frequency 
                from a higher priority frequency.
                IE threshX-Low(TS 36.331)"
            DEFVAL { 2 }
            ::= { asLteStkCellSib5CfgEntry 5 }

        
        -- 1.3.6.1.4.1.989.1.20.1.4.7.1.6
        asLteStkCellSib5CfgAllowedMeasBandwidth OBJECT-TYPE
            SYNTAX AsLteStkCellCfgAllowedMeasBandwidthType
            UNITS "resourceBlocks"
            MAX-ACCESS read-write
            STATUS current
            DESCRIPTION
                "This indicated the maximum allowed measurement bandwidth on a carrier frequency.
                IE allowedMeasBandwidth(TS 36.331)"
            DEFVAL { 2 }
            ::= { asLteStkCellSib5CfgEntry 6 }

        
        -- 1.3.6.1.4.1.989.1.20.1.4.7.1.7
        asLteStkCellSib5CfgPresenceAntennaPort1 OBJECT-TYPE
            SYNTAX AsCmnTcBooleanSwitch
            MAX-ACCESS read-write
            STATUS current
            DESCRIPTION
                "This field indicates whether the neighbouring cell uses Antenna Port 1.
                IE presenceAntennaPort1(TS 36.331)"
            DEFVAL { 0 }
            ::= { asLteStkCellSib5CfgEntry 7 }

        
        -- 1.3.6.1.4.1.989.1.20.1.4.7.1.8
        asLteStkCellSib5CfgCellReselectionPriority OBJECT-TYPE
            SYNTAX Integer32 (0..7)
            MAX-ACCESS read-write
            STATUS current
            DESCRIPTION
                "The absolute priority of the concerned carrier frequency as used by cell reselection procedure.
                Value of zero indicates lowest priority.
                IE cellReselectonPriority(TS 36.331)"
            DEFVAL { 4 }
            ::= { asLteStkCellSib5CfgEntry 8 }

        
        -- 1.3.6.1.4.1.989.1.20.1.4.7.1.9
        asLteStkCellSib5CfgNeighCellConfig OBJECT-TYPE
            SYNTAX Integer32 (0..3)
            MAX-ACCESS read-write
            STATUS current
            DESCRIPTION
                "This field provides information about MBSFN (Multicast and Broadcast Single Freq Network) 
                and TDD UL/DL configs of neighbouring cells.
                0 - Not all neighbouring cells have same MBSFN subframe allocation as serving cell.
                1 - No MBSFN subframes present in neighbouring cells.
                2 - MBSFN subframe allocations of neighbouring cells are identical/subset of that in serving cell.
                3 - Different TDD UL/DL allocation in neighbouring cells.
                IE neighCellConfig(TS 36.331)"
            DEFVAL { 0 }
            ::= { asLteStkCellSib5CfgEntry 9 }

        
        -- 1.3.6.1.4.1.989.1.20.1.4.7.1.10
        asLteStkCellSib5CfgQOffsetFreq OBJECT-TYPE
            SYNTAX AsLteStkCellCfgQOffsetFreq
            MAX-ACCESS read-write
            STATUS current
            DESCRIPTION
                "This field provides the frequency specific offset for E-UTRA frequencies.
                IE q-OffsetFreq(TS 36.331)"
            DEFVAL { 0 }
            ::= { asLteStkCellSib5CfgEntry 10 }

        
        -- 1.3.6.1.4.1.989.1.20.1.4.8
        asLteStkCellRachCfgTable OBJECT-TYPE
            SYNTAX SEQUENCE OF AsLteStkCellRachCfgEntry
            MAX-ACCESS not-accessible
            STATUS current
            DESCRIPTION
                "This table contains all the configuration used to configure the RACH process.
                The bulk of the configuration is carried in the SIB2 message."
            ::= { asLteStkIf 8 }

        
        -- 1.3.6.1.4.1.989.1.20.1.4.8.1
        asLteStkCellRachCfgEntry OBJECT-TYPE
            SYNTAX AsLteStkCellRachCfgEntry
            MAX-ACCESS not-accessible
            STATUS current
            DESCRIPTION
                "Description."
            INDEX { ifIndex }
            ::= { asLteStkCellRachCfgTable 1 }

        
        AsLteStkCellRachCfgEntry ::=
            SEQUENCE { 
                asLteStkCellRachCfgNumberOfRAPreambles
                    AsLteStkCellRachCfgNumberOfRAPreamblesType,
                asLteStkCellRachCfgMessageSizeGroupA
                    AsLteStkCellRachCfgNumberOfRAPreamblesType,
                asLteStkCellRachCfgNumberOfGroupARAPreambles
                    AsLteStkCellRachCfgNumberOfRAPreamblesType,
                asLteStkCellRachCfgPrachRootSequenceIndex
                    Integer32,
                asLteStkCellRachCfgPrachConfigurationIndex
                    Integer32,
                asLteStkCellRachCfgPrachZeroCorrelationZoneConfig
                    Integer32,
                asLteStkCellRachCfgPrachHighSpeedFlag
                    AsCmnTcBooleanSwitch,
                asLteStkCellRachCfgPrachFrequencyOffset
                    Integer32,
                asLteStkCellRachCfgMessagePowerOffsetGroupB
                    AsLteStkCellRachCfgMessagePowerOffsetGroupBType,
                asLteStkCellRachCfgPowerRampingStep
                    AsLteStkCellRachCfgPowerRampingStepType,
                asLteStkCellRachCfgPreambleInitialRcvdTargetPower
                    AsLteStkCellRachCfgPreambleInitialRcvdTargetPowerType,
                asLteStkCellRachCfgPreambleTransMax
                    AsLteStkCellRachCfgPreambleTransMaxType,
                asLteStkCellRachCfgRAResponseWindowSize
                    AsLteStkCellRachCfgRAResponseWindowSizeType,
                asLteStkCellRachCfgMacContentionResolutionTimer
                    AsLteStkCellRachCfgMacContentionResolutionTimerType,
                asLteStkCellRachCfgMaxHarqMsg3Tx
                    Integer32,
                asLteStkCellRachCfgPrachResource
                    Integer32
             }

        -- 1.3.6.1.4.1.989.1.20.1.4.8.1.1
        asLteStkCellRachCfgNumberOfRAPreambles OBJECT-TYPE
            SYNTAX AsLteStkCellRachCfgNumberOfRAPreamblesType
            MAX-ACCESS read-write
            STATUS current
            DESCRIPTION
                "The number of non-dedicated random access preambles in TS 36.321 [MAC]. 
                IE numberOfRA-Preambles (TS36.331)"
            DEFVAL { 12 }
            ::= { asLteStkCellRachCfgEntry 1 }

        
        -- 1.3.6.1.4.1.989.1.20.1.4.8.1.2
        asLteStkCellRachCfgMessageSizeGroupA OBJECT-TYPE
            SYNTAX AsLteStkCellRachCfgNumberOfRAPreamblesType
            UNITS "bits"
            MAX-ACCESS read-write
            STATUS current
            DESCRIPTION
                "Threshold for preamble selection in TS 36.321 [MAC].  Value is in bits.
                IE messageSizeGroupA (TS36.331)"
            DEFVAL { 1 }
            ::= { asLteStkCellRachCfgEntry 2 }

        
        -- 1.3.6.1.4.1.989.1.20.1.4.8.1.3
        asLteStkCellRachCfgNumberOfGroupARAPreambles OBJECT-TYPE
            SYNTAX AsLteStkCellRachCfgNumberOfRAPreamblesType
            MAX-ACCESS read-write
            STATUS current
            DESCRIPTION
                "The number of random access preambles in GroupA in TS 36.321 [MAC].
                IE sizeOfRA-PreamblesGroupA (TS36.331)"
            DEFVAL { 12 }
            ::= { asLteStkCellRachCfgEntry 3 }

        
        -- 1.3.6.1.4.1.989.1.20.1.4.8.1.4
        asLteStkCellRachCfgPrachRootSequenceIndex OBJECT-TYPE
            SYNTAX Integer32 (0..837)
            MAX-ACCESS read-write
            STATUS current
            DESCRIPTION
                "An index used in Preamble Sequence generation - see TS 36.221 [PHY].
                IE rootSequenceIndex (TS36.331)"
            DEFVAL { 419 }
            ::= { asLteStkCellRachCfgEntry 4 }

        
        -- 1.3.6.1.4.1.989.1.20.1.4.8.1.5
        asLteStkCellRachCfgPrachConfigurationIndex OBJECT-TYPE
            SYNTAX Integer32 (0..63)
            MAX-ACCESS read-write
            STATUS current
            DESCRIPTION
                "Another index used in Preamble Sequence generation - see TS 36.221 [PHY].
                IE prach-ConfigIndex (TS36.331)"
            DEFVAL { 0 }
            ::= { asLteStkCellRachCfgEntry 5 }

        
        -- 1.3.6.1.4.1.989.1.20.1.4.8.1.6
        asLteStkCellRachCfgPrachZeroCorrelationZoneConfig OBJECT-TYPE
            SYNTAX Integer32 (0..15)
            MAX-ACCESS read-write
            STATUS current
            DESCRIPTION
                "Another parameter used to determine the number of cyclic shifts used in 
                Preamble Sequence generation see TS 36.221 [PHY]. 
                IE zeroCorrelationZoneConfig (TS36.331)"
            DEFVAL { 13 }
            ::= { asLteStkCellRachCfgEntry 6 }

        
        -- 1.3.6.1.4.1.989.1.20.1.4.8.1.7
        asLteStkCellRachCfgPrachHighSpeedFlag OBJECT-TYPE
            SYNTAX AsCmnTcBooleanSwitch
            MAX-ACCESS read-write
            STATUS current
            DESCRIPTION
                "Another index used in Preamble Sequence generation - see TS 36.221 [PHY].  
                If FALSE indicates that the unrestricted set is used, otherwise the restricted set is used. 
                IE highSpeedFlag (TS36.331)"
            DEFVAL { 0 }
            ::= { asLteStkCellRachCfgEntry 7 }

        
        -- 1.3.6.1.4.1.989.1.20.1.4.8.1.8
        asLteStkCellRachCfgPrachFrequencyOffset OBJECT-TYPE
            SYNTAX Integer32 (0..94)
            MAX-ACCESS read-write
            STATUS current
            DESCRIPTION
                "The first phyical resource block available for PRACH - see TS 36.221 5.7.2 [PHY].
                For TDD the value range is dependent on the value of prachConfigurationIndex
                IE prach-FreqOffset(TS36.331)"
            DEFVAL { 4 }
            ::= { asLteStkCellRachCfgEntry 8 }

        
        -- 1.3.6.1.4.1.989.1.20.1.4.8.1.9
        asLteStkCellRachCfgMessagePowerOffsetGroupB OBJECT-TYPE
            SYNTAX AsLteStkCellRachCfgMessagePowerOffsetGroupBType
            UNITS "dBm"
            MAX-ACCESS read-write
            STATUS current
            DESCRIPTION
                "Threshold for preamble selection in TS 36.321 [MAC].  Value is in dB.
                IE messagePowerOffsetGroupB (TS36.331)"
            DEFVAL { 1 }
            ::= { asLteStkCellRachCfgEntry 9 }

        
        -- 1.3.6.1.4.1.989.1.20.1.4.8.1.10
        asLteStkCellRachCfgPowerRampingStep OBJECT-TYPE
            SYNTAX AsLteStkCellRachCfgPowerRampingStepType
            UNITS "dBm"
            MAX-ACCESS read-write
            STATUS current
            DESCRIPTION
                "Power ramping factor in TS 36.321 [MAC].  Value is in dB.
                IE powerRampingStep (TS36.331)"
            DEFVAL { 1 }
            ::= { asLteStkCellRachCfgEntry 10 }

        
        -- 1.3.6.1.4.1.989.1.20.1.4.8.1.11
        asLteStkCellRachCfgPreambleInitialRcvdTargetPower OBJECT-TYPE
            SYNTAX AsLteStkCellRachCfgPreambleInitialRcvdTargetPowerType
            UNITS "dBm"
            MAX-ACCESS read-write
            STATUS current
            DESCRIPTION
                "Initial preamble power in TS 36.321 [MAC].  Value is in dB.
                IE preambleInitialReceivedTargetPower (TS36.331)"
            DEFVAL { 5 }
            ::= { asLteStkCellRachCfgEntry 11 }

        
        -- 1.3.6.1.4.1.989.1.20.1.4.8.1.12
        asLteStkCellRachCfgPreambleTransMax OBJECT-TYPE
            SYNTAX AsLteStkCellRachCfgPreambleTransMaxType
            MAX-ACCESS read-write
            STATUS current
            DESCRIPTION
                "Maximum number of preamble transmissions in TS 36.321 [MAC].
                IE preambleTransMax (TS36.331)"
            DEFVAL { 3 }
            ::= { asLteStkCellRachCfgEntry 12 }

        
        -- 1.3.6.1.4.1.989.1.20.1.4.8.1.13
        asLteStkCellRachCfgRAResponseWindowSize OBJECT-TYPE
            SYNTAX AsLteStkCellRachCfgRAResponseWindowSizeType
            UNITS "subframes"
            MAX-ACCESS read-write
            STATUS current
            DESCRIPTION
                "Duration of the RA response window in TS 36.321 [MAC].  Measured in subframes.
                IE ra-ResponseWindowSize (TS36.331)"
            DEFVAL { 7 }
            ::= { asLteStkCellRachCfgEntry 13 }

        
        -- 1.3.6.1.4.1.989.1.20.1.4.8.1.14
        asLteStkCellRachCfgMacContentionResolutionTimer OBJECT-TYPE
            SYNTAX AsLteStkCellRachCfgMacContentionResolutionTimerType
            UNITS "subframes"
            MAX-ACCESS read-write
            STATUS current
            DESCRIPTION
                "Timer for contention resolution in TS 36.321 [MAC].  Measured in subframes.
                IE mac-ContentionResolutionTimer (TS36.331)"
            DEFVAL { 4 }
            ::= { asLteStkCellRachCfgEntry 14 }

        
        -- 1.3.6.1.4.1.989.1.20.1.4.8.1.15
        asLteStkCellRachCfgMaxHarqMsg3Tx OBJECT-TYPE
            SYNTAX Integer32 (1..8)
            MAX-ACCESS read-write
            STATUS current
            DESCRIPTION
                "The maximum number of Msg3 HARQ transmissions used for contention based 
                random access in TS 36.321 [MAC].
                IE maxHARQ-Msg3Tx (TS36.331)"
            DEFVAL { 4 }
            ::= { asLteStkCellRachCfgEntry 15 }

        
        -- 1.3.6.1.4.1.989.1.20.1.4.8.1.16
        asLteStkCellRachCfgPrachResource OBJECT-TYPE
            SYNTAX Integer32
            MAX-ACCESS read-write
            STATUS current
            DESCRIPTION
                "The first physical resource block occupied by PRACH resource. 
                TS 36.321 [MAC] parameter N^RA_PRB."
            DEFVAL { 1 }
            ::= { asLteStkCellRachCfgEntry 16 }

        
        -- 1.3.6.1.4.1.989.1.20.1.4.9
        asLteStkCellDedCfgTable OBJECT-TYPE
            SYNTAX SEQUENCE OF AsLteStkCellDedCfgEntry
            MAX-ACCESS not-accessible
            STATUS current
            DESCRIPTION
                "This table contains all the configuration for the IE RadioResourceConfigDedicated as defined
                in TS 36.331.  This IE is included in RRC-ConnectionReconfiguration messages and is used to
                setup/modify/release RBs (Radio Bearers), to modify the MAC main configuration, to modify 
                the SPS (Semi-persistent scheduling) configuration and to modify dedicated (i.e. per UE) 
                physical configuration"
            ::= { asLteStkIf 9 }

        
        -- 1.3.6.1.4.1.989.1.20.1.4.9.1
        asLteStkCellDedCfgEntry OBJECT-TYPE
            SYNTAX AsLteStkCellDedCfgEntry
            MAX-ACCESS not-accessible
            STATUS current
            DESCRIPTION
                "Description."
            INDEX { ifIndex }
            ::= { asLteStkCellDedCfgTable 1 }

        
        AsLteStkCellDedCfgEntry ::=
            SEQUENCE { 
                asLteStkCellDedCfgSrbTPollRetransmit
                    AsLteStkCellDedCfgTPollRetransmitType,
                asLteStkCellDedCfgSrbPollPdu
                    AsLteStkCellDedCfgPollPduType,
                asLteStkCellDedCfgSrbPollByte
                    AsLteStkCellDedCfgPollByteType,
                asLteStkCellDedCfgSrbMaxRetxThreshold
                    AsLteStkCellDedCfgMaxRetxThresholdType,
                asLteStkCellDedCfgSrbTReordering
                    AsLteStkCellDedCfgTReorderingType,
                asLteStkCellDedCfgSrbTStatusProhibit
                    AsLteStkCellDedCfgTStatusProhibitType,
                asLteStkCellDedCfgSrb1Priority
                    Integer32,
                asLteStkCellDedCfgSrb2Priority
                    Integer32,
                asLteStkCellDedCfgSrbPriBitRate
                    AsLteStkCellDedCfgPriBitRateType,
                asLteStkCellDedCfgSrbBucketSizeDuration
                    AsLteStkCellDedCfgBucketSizeDurationType,
                asLteStkCellDedCfgSrbLogicalChannelGroup
                    Integer32,
                asLteStkCellDedCfgMacUlSCHMaxHARQTx
                    AsLteStkCellMaxHARQTxType,
                asLteStkCellDedCfgMacUlSCHPeriodicBSRTimer
                    AsLteStkCellDedCfgMacUlSCHPeriodicBSRTimerType,
                asLteStkCellDedCfgMacUlSCHRetxBSRTimer
                    AsLteStkCellDedCfgMacUlSCHRetxBSRTimerType,
                asLteStkCellDedCfgMacUlSCHTtiBundling
                    AsCmnTcBooleanSwitch,
                asLteStkCellDedCfgMacTimeAlignmentTimer
                    AsLteStkCellCfgTimeAlignmentTimerType,
                asLteStkCellDedCfgMacPeriodicPHRTimer
                    AsLteStkCellDedCfgMacPeriodicPHRTimerType,
                asLteStkCellDedCfgMacProhibitPHRTimer
                    AsLteStkCellDedCfgMacProhibitPHRTimerType,
                asLteStkCellDedCfgMacDlPathLossChange
                    AsLteStkCellDedCfgMacDlPathLossChangeType,
                asLteStkCellDedCfgPhyTddAckNackFeedbackMode
                    AsLteStkCellDedCfgPhyTddAckNackFeedbackModeType,
                asLteStkCellDedCfgPhyUlP0UePusch
                    Integer32,
                asLteStkCellDedCfgPhyUlP0UePucch
                    Integer32,
                asLteStkCellDedCfgPhyUlDeltaMCSEnabled
                    AsCmnTcBooleanSwitch,
                asLteStkCellDedCfgPhyUlAccumulationEnabled
                    AsCmnTcBooleanSwitch,
                asLteStkCellDedCfgPhyUlPSRSOffset
                    Integer32,
                asLteStkCellDedCfgPhyUlFilterCoefficient
                    Integer32,
                asLteStkCellDedCfgPhyBetaOffsetACKIndex
                    Integer32,
                asLteStkCellDedCfgPhyBetaOffsetRIIndex
                    Integer32,
                asLteStkCellDedCfgPhyBetaOffsetCQIIndex
                    Integer32,
                asLteStkCellDedCfgPhyCqiReportingMode
                    AsLteStkCellDedCfgPhyCqiReportingModeType,
                asLteStkCellDedCfgPhyNomPdschRsEpreOffset
                    Integer32,
                asLteStkCellDedCfgPhyCqiPucchResourceIndex
                    Integer32,
                asLteStkCellDedCfgPhyCqiPmiConfigIndex
                    Integer32,
                asLteStkCellDedCfgPhyCqiRIConfigIndex
                    Integer32,
                asLteStkCellDedCfgPhySimultaneousAckNackAndCqi
                    AsCmnTcBooleanSwitch,
                asLteStkCellDedCfgPhySrPucchResourceIndex
                    Integer32,
                asLteStkCellDedCfgPhyDsrTransMax
                    AsLteStkCellDedCfgPhyDsrTransMaxType,
                asLteStkCellDedCfgPhyPdschAckNackRepFactor
                    AsLteStkCellDedCfgPhyPdschAckNackRepFactorType,
                asLteStkCellDedCfgPhyN1PucchAckNackRep
                    Integer32,
                asLteStkCellDedCfgUeTransmissionMode
                    AsLteStkCellDedCfgUeTransmissionMode,
                asLteStkCellDedCfgDrbPdcpDiscardTimer
                    AsLteStkCellDedCfgDrbPdcpDiscardTimerType,
                asLteStkCellDedCfgDrbPdcpStatusRptReq
                    AsCmnTcBooleanSwitch,
                asLteStkCellDedCfgDrbTPollRetransmit
                    AsLteStkCellDedCfgTPollRetransmitType,
                asLteStkCellDedCfgDrbPollPdu
                    AsLteStkCellDedCfgPollPduType,
                asLteStkCellDedCfgDrbPollByte
                    AsLteStkCellDedCfgPollByteType,
                asLteStkCellDedCfgDrbMaxRetxThreshold
                    AsLteStkCellDedCfgMaxRetxThresholdType,
                asLteStkCellDedCfgDrbTReordering
                    AsLteStkCellDedCfgTReorderingType,
                asLteStkCellDedCfgDrbTStatusProhibit
                    AsLteStkCellDedCfgTStatusProhibitType,
                asLteStkCellDedCfgDrbLogicalChannelPriority
                    Integer32,
                asLteStkCellDedCfgDrbPriBitRate
                    AsLteStkCellDedCfgPriBitRateType,
                asLteStkCellDedCfgDrbBucketSizeDuration
                    AsLteStkCellDedCfgBucketSizeDurationType,
                asLteStkCellDedCfgDrbLogicalChannelGroup
                    Integer32,
                asLteStkCellDedCfgPdschDlPowerAllocation
                    AsLteStkCellDedCfgPdschDlPowerAllocationType,
                asLteStkCellDedCfgPhyN2TxAntennaTm3
                    Unsigned32,
                asLteStkCellDedCfgPhyN4TxAntennaTm3
                    Unsigned32,
                asLteStkCellDedCfgPhyCodebookRestrictionPresent
                    AsCmnTcBooleanSwitch
             }

        -- 1.3.6.1.4.1.989.1.20.1.4.9.1.1
        asLteStkCellDedCfgSrbTPollRetransmit OBJECT-TYPE
            SYNTAX AsLteStkCellDedCfgTPollRetransmitType
            UNITS "mSecs"
            MAX-ACCESS read-write
            STATUS current
            DESCRIPTION
                "Value for the RLC poll-Retransmit timer for SRBs (Signalling Radio Bearers).
                IE t-PollRetransmit(TS 36.331)"
            DEFVAL { 8 }
            ::= { asLteStkCellDedCfgEntry 1 }

        
        -- 1.3.6.1.4.1.989.1.20.1.4.9.1.2
        asLteStkCellDedCfgSrbPollPdu OBJECT-TYPE
            SYNTAX AsLteStkCellDedCfgPollPduType
            MAX-ACCESS read-write
            STATUS current
            DESCRIPTION
                "Value for the RLC poll-PDU constant for SRBs (Signalling Radio Bearers)
                IE pollPDU(TS 36.331)"
            DEFVAL { 7 }
            ::= { asLteStkCellDedCfgEntry 2 }

        
        -- 1.3.6.1.4.1.989.1.20.1.4.9.1.3
        asLteStkCellDedCfgSrbPollByte OBJECT-TYPE
            SYNTAX AsLteStkCellDedCfgPollByteType
            UNITS "kBytes"
            MAX-ACCESS read-write
            STATUS current
            DESCRIPTION
                "Value for the RLC poll-Byte timer for SRBs (Signalling Radio Bearers)
                IE pollByte(TS 36.331)"
            DEFVAL { 14 }
            ::= { asLteStkCellDedCfgEntry 3 }

        
        -- 1.3.6.1.4.1.989.1.20.1.4.9.1.4
        asLteStkCellDedCfgSrbMaxRetxThreshold OBJECT-TYPE
            SYNTAX AsLteStkCellDedCfgMaxRetxThresholdType
            MAX-ACCESS read-write
            STATUS current
            DESCRIPTION
                "Value for the RLC max-retransmission threshold for SRBs (Signalling Radio Bearers)
                IE maxRetxThreshold(TS 36.331)"
            DEFVAL { 3 }
            ::= { asLteStkCellDedCfgEntry 4 }

        
        -- 1.3.6.1.4.1.989.1.20.1.4.9.1.5
        asLteStkCellDedCfgSrbTReordering OBJECT-TYPE
            SYNTAX AsLteStkCellDedCfgTReorderingType
            UNITS "mSecs"
            MAX-ACCESS read-write
            STATUS current
            DESCRIPTION
                "Value for the RLC Re-ordering timer threshold for SRBs (Signalling Radio Bearers)
                IE t-Reordering(TS 36.331)"
            DEFVAL { 7 }
            ::= { asLteStkCellDedCfgEntry 5 }

        
        -- 1.3.6.1.4.1.989.1.20.1.4.9.1.6
        asLteStkCellDedCfgSrbTStatusProhibit OBJECT-TYPE
            SYNTAX AsLteStkCellDedCfgTStatusProhibitType
            UNITS "mSecs"
            MAX-ACCESS read-write
            STATUS current
            DESCRIPTION
                "Value for the RLC Status Prohibit  timer threshold for SRBs (Signalling Radio Bearers)
                IE t-StatusProhibit(TS 36.331)"
            DEFVAL { 0 }
            ::= { asLteStkCellDedCfgEntry 6 }

        
        -- 1.3.6.1.4.1.989.1.20.1.4.9.1.7
        asLteStkCellDedCfgSrb1Priority OBJECT-TYPE
            SYNTAX Integer32 (1..16)
            MAX-ACCESS read-write
            STATUS current
            DESCRIPTION
                "Priority of logical channel corresponding to SRB1 at MAC. 
                SRB1 is carried over the DCCH (Dedicated Control Channel) logical channel
                Increasing values show decreasing priority.
                SRB1 carries both NAS and RRC messages.
                IE priority(in ul-SpecificParameters)(TS 36.331)"
            DEFVAL { 1 }
            ::= { asLteStkCellDedCfgEntry 7 }

        
        -- 1.3.6.1.4.1.989.1.20.1.4.9.1.8
        asLteStkCellDedCfgSrb2Priority OBJECT-TYPE
            SYNTAX Integer32 (1..16)
            MAX-ACCESS read-write
            STATUS current
            DESCRIPTION
                "Priority of logical channel corresponding to SRB2 at MAC. 
                SRB2 is for NAS messages, using DCCH logical channel. 
                SRB2 has a lower-priority than SRB1.
                Increasing values show decreasing priority.
                IE priority(in ul-SpecificParameters)(TS 36.331)"
            DEFVAL { 3 }
            ::= { asLteStkCellDedCfgEntry 8 }

        
        -- 1.3.6.1.4.1.989.1.20.1.4.9.1.9
        asLteStkCellDedCfgSrbPriBitRate OBJECT-TYPE
            SYNTAX AsLteStkCellDedCfgPriBitRateType
            UNITS "KBytes/sec"
            MAX-ACCESS read-write
            STATUS current
            DESCRIPTION
                "Prioritised bit rate for logical channels corresponding to SRB1 and SRB2 at MAC.
                IE prioritisedBitRate(in ul-SpecificParameters)(TS 36.331)"
            DEFVAL { 7 }
            ::= { asLteStkCellDedCfgEntry 9 }

        
        -- 1.3.6.1.4.1.989.1.20.1.4.9.1.10
        asLteStkCellDedCfgSrbBucketSizeDuration OBJECT-TYPE
            SYNTAX AsLteStkCellDedCfgBucketSizeDurationType
            UNITS "mSecs"
            MAX-ACCESS read-write
            STATUS current
            DESCRIPTION
                "Bucket size Duration for SRB1 and SRB2 used for logical channel prioritization.
                IE bucketSizeDuration(in ul-SpecificParameters)(TS 36.331)"
            DEFVAL { 0 }
            ::= { asLteStkCellDedCfgEntry 10 }

        
        -- 1.3.6.1.4.1.989.1.20.1.4.9.1.11
        asLteStkCellDedCfgSrbLogicalChannelGroup OBJECT-TYPE
            SYNTAX Integer32 (0..3)
            MAX-ACCESS read-write
            STATUS current
            DESCRIPTION
                "Logical channel group to which SRB1 and SRB2 belong.
                IE logicalChannelGroup(in ul-SpecificParameters)(TS 36.331)"
            DEFVAL { 0 }
            ::= { asLteStkCellDedCfgEntry 11 }

        
        -- 1.3.6.1.4.1.989.1.20.1.4.9.1.12
        asLteStkCellDedCfgMacUlSCHMaxHARQTx OBJECT-TYPE
            SYNTAX AsLteStkCellMaxHARQTxType
            MAX-ACCESS read-write
            STATUS current
            DESCRIPTION
                "Maximum HARQ transmissions in UL. Used for both SRBs and DRBs.
                IE maxHARQ-Tx(TS 36.331)"
            DEFVAL { 2 }
            ::= { asLteStkCellDedCfgEntry 12 }

        
        -- 1.3.6.1.4.1.989.1.20.1.4.9.1.13
        asLteStkCellDedCfgMacUlSCHPeriodicBSRTimer OBJECT-TYPE
            SYNTAX AsLteStkCellDedCfgMacUlSCHPeriodicBSRTimerType
            UNITS "subframes"
            MAX-ACCESS read-write
            STATUS current
            DESCRIPTION
                "Timer value for reporting a BSR (Buffer Status Report) periodically.
                IE periodicBSR-Timer(TS 36.331)"
            DEFVAL { 0 }
            ::= { asLteStkCellDedCfgEntry 13 }

        
        -- 1.3.6.1.4.1.989.1.20.1.4.9.1.14
        asLteStkCellDedCfgMacUlSCHRetxBSRTimer OBJECT-TYPE
            SYNTAX AsLteStkCellDedCfgMacUlSCHRetxBSRTimerType
            UNITS "subframes"
            MAX-ACCESS read-write
            STATUS current
            DESCRIPTION
                "Timer value for BSR (Buffer Status Report) reporting
                IE retxBSR-Timer(TS 36.331)"
            DEFVAL { 0 }
            ::= { asLteStkCellDedCfgEntry 14 }

        
        -- 1.3.6.1.4.1.989.1.20.1.4.9.1.15
        asLteStkCellDedCfgMacUlSCHTtiBundling OBJECT-TYPE
            SYNTAX AsCmnTcBooleanSwitch
            MAX-ACCESS read-write
            STATUS current
            DESCRIPTION
                "Denotes whether or not TTI bundling is enabled
                IE ttiBundling(TS 36.331)"
            DEFVAL { 0 }
            ::= { asLteStkCellDedCfgEntry 15 }

        
        -- 1.3.6.1.4.1.989.1.20.1.4.9.1.16
        asLteStkCellDedCfgMacTimeAlignmentTimer OBJECT-TYPE
            SYNTAX AsLteStkCellCfgTimeAlignmentTimerType
            UNITS "subframes"
            MAX-ACCESS read-write
            STATUS current
            DESCRIPTION
                "Time for which UE is considered time-aligned.(36.321)
                IE timeAlignmentTimerDedicated(TS 36.331)"
            DEFVAL { 7 }
            ::= { asLteStkCellDedCfgEntry 16 }

        
        -- 1.3.6.1.4.1.989.1.20.1.4.9.1.17
        asLteStkCellDedCfgMacPeriodicPHRTimer OBJECT-TYPE
            SYNTAX AsLteStkCellDedCfgMacPeriodicPHRTimerType
            UNITS "subframes"
            MAX-ACCESS read-write
            STATUS current
            DESCRIPTION
                "Timer value for periodic PHR (Power Headroom) reporting.(36.321)
                IE periodicPHR-Timer(TS 36.331)"
            DEFVAL { 5 }
            ::= { asLteStkCellDedCfgEntry 17 }

        
        -- 1.3.6.1.4.1.989.1.20.1.4.9.1.18
        asLteStkCellDedCfgMacProhibitPHRTimer OBJECT-TYPE
            SYNTAX AsLteStkCellDedCfgMacProhibitPHRTimerType
            UNITS "subframes"
            MAX-ACCESS read-write
            STATUS current
            DESCRIPTION
                "Timer value for prohibiting PHR (Power Headroom) reporting.(36.321)
                IE prohibitPHR-Timer(TS 36.331)"
            DEFVAL { 5 }
            ::= { asLteStkCellDedCfgEntry 18 }

        
        -- 1.3.6.1.4.1.989.1.20.1.4.9.1.19
        asLteStkCellDedCfgMacDlPathLossChange OBJECT-TYPE
            SYNTAX AsLteStkCellDedCfgMacDlPathLossChangeType
            UNITS "dBm"
            MAX-ACCESS read-write
            STATUS current
            DESCRIPTION
                "Change in measured downlink pathloss to trigger a PHR.(36.321)
                IE dlPathLossChange(TS 36.331)"
            DEFVAL { 1 }
            ::= { asLteStkCellDedCfgEntry 19 }

        
        -- 1.3.6.1.4.1.989.1.20.1.4.9.1.20
        asLteStkCellDedCfgPhyTddAckNackFeedbackMode OBJECT-TYPE
            SYNTAX AsLteStkCellDedCfgPhyTddAckNackFeedbackModeType
            MAX-ACCESS read-write
            STATUS current
            DESCRIPTION
                "Indicates one of the two TDD ACK/NACK bundling modes - Multiplexing/Bundling. 
                IE tdd-AckNackFeedbackMode(TS 36.331)"
            DEFVAL { 0 }
            ::= { asLteStkCellDedCfgEntry 20 }

        
        -- 1.3.6.1.4.1.989.1.20.1.4.9.1.21
        asLteStkCellDedCfgPhyUlP0UePusch OBJECT-TYPE
            SYNTAX Integer32 (-8..7)
            UNITS "dBm"
            MAX-ACCESS read-write
            STATUS current
            DESCRIPTION
                "UE specific Transmit power in PUSCH. Measured in dB.
                IE p0-UE-PUSCH(TS 36.331)"
            DEFVAL { 0 }
            ::= { asLteStkCellDedCfgEntry 21 }

        
        -- 1.3.6.1.4.1.989.1.20.1.4.9.1.22
        asLteStkCellDedCfgPhyUlP0UePucch OBJECT-TYPE
            SYNTAX Integer32 (-8..7)
            UNITS "dBm"
            MAX-ACCESS read-write
            STATUS current
            DESCRIPTION
                "UE specific Transmit power in PUCCH. Measured in dB.
                IE p0-UE-PUCCH(TS 36.331)"
            DEFVAL { 0 }
            ::= { asLteStkCellDedCfgEntry 22 }

        
        -- 1.3.6.1.4.1.989.1.20.1.4.9.1.23
        asLteStkCellDedCfgPhyUlDeltaMCSEnabled OBJECT-TYPE
            SYNTAX AsCmnTcBooleanSwitch
            MAX-ACCESS read-write
            STATUS current
            DESCRIPTION
                "Indicates whether or not delta MCS (modulation Coding Scheme) is enabled or not.
                Used in uplink power control on the PUSCH channel (TS 36.213 5.1.1.1)
                IE deltaMCS-Enabled(TS 36.331)"
            DEFVAL { 0 }
            ::= { asLteStkCellDedCfgEntry 23 }

        
        -- 1.3.6.1.4.1.989.1.20.1.4.9.1.24
        asLteStkCellDedCfgPhyUlAccumulationEnabled OBJECT-TYPE
            SYNTAX AsCmnTcBooleanSwitch
            MAX-ACCESS read-write
            STATUS current
            DESCRIPTION
                "Another parameter used in uplink power control on the PUSCH channel (TS 36.213 5.1.1.1)
                IE accumulationEnabled(TS 36.331)"
            DEFVAL { 0 }
            ::= { asLteStkCellDedCfgEntry 24 }

        
        -- 1.3.6.1.4.1.989.1.20.1.4.9.1.25
        asLteStkCellDedCfgPhyUlPSRSOffset OBJECT-TYPE
            SYNTAX Integer32 (0..15)
            MAX-ACCESS read-write
            STATUS current
            DESCRIPTION
                "Value used in calculation of UE Transmit power for Sounding Reference Signals.
                IE pSRS-Offset(TS 36.331)"
            DEFVAL { 3 }
            ::= { asLteStkCellDedCfgEntry 25 }

        
        -- 1.3.6.1.4.1.989.1.20.1.4.9.1.26
        asLteStkCellDedCfgPhyUlFilterCoefficient OBJECT-TYPE
            SYNTAX Integer32 (0..15)
            MAX-ACCESS read-write
            STATUS current
            DESCRIPTION
                "Specifies the filtering co-efficient for RSRP (Reference Signal Received Power)
                measurements used to calculate path loss.
                IE filterCoefficient(TS 36.331)"
            DEFVAL { 4 }
            ::= { asLteStkCellDedCfgEntry 26 }

        
        -- 1.3.6.1.4.1.989.1.20.1.4.9.1.27
        asLteStkCellDedCfgPhyBetaOffsetACKIndex OBJECT-TYPE
            SYNTAX Integer32 (0..15)
            MAX-ACCESS read-write
            STATUS current
            DESCRIPTION
                "Value used in determination of MCS (Modulation Coding Scheme) offset.
                IE betaOffset-ACK-Index(TS 36.331)"
            DEFVAL { 10 }
            ::= { asLteStkCellDedCfgEntry 27 }

        
        -- 1.3.6.1.4.1.989.1.20.1.4.9.1.28
        asLteStkCellDedCfgPhyBetaOffsetRIIndex OBJECT-TYPE
            SYNTAX Integer32 (0..15)
            MAX-ACCESS read-write
            STATUS current
            DESCRIPTION
                "Value used in determination of MCS (Modulation Coding Scheme) offset.
                IE betaOffset-RI-Index(TS 36.331)"
            DEFVAL { 12 }
            ::= { asLteStkCellDedCfgEntry 28 }

        
        -- 1.3.6.1.4.1.989.1.20.1.4.9.1.29
        asLteStkCellDedCfgPhyBetaOffsetCQIIndex OBJECT-TYPE
            SYNTAX Integer32 (0..15)
            MAX-ACCESS read-write
            STATUS current
            DESCRIPTION
                "Value used in determination of MCS (Modulation Coding Scheme) offset.
                IE betaOffset-CQI-Index(TS 36.331)"
            DEFVAL { 15 }
            ::= { asLteStkCellDedCfgEntry 29 }

        
        -- 1.3.6.1.4.1.989.1.20.1.4.9.1.30
        asLteStkCellDedCfgPhyCqiReportingMode OBJECT-TYPE
            SYNTAX AsLteStkCellDedCfgPhyCqiReportingModeType
            MAX-ACCESS read-write
            STATUS current
            DESCRIPTION
                "CQI (Channel Quality Indicator) reporting mode of a UE for PUSCH.
                IE cqi-ReportModeAperiodic(TS 36.331)"
            DEFVAL { 1 }
            ::= { asLteStkCellDedCfgEntry 30 }

        
        -- 1.3.6.1.4.1.989.1.20.1.4.9.1.31
        asLteStkCellDedCfgPhyNomPdschRsEpreOffset OBJECT-TYPE
            SYNTAX Integer32 (-1..6)
            MAX-ACCESS read-write
            STATUS current
            DESCRIPTION
                "Value used in the calculation of ratio of PDSCH EPRE (Energy Per Resource Element)
                to cell specific RS EPRE. deltaOffset is calculated based on this value.
                IE nomPDSCH-RS-EPRE-Offset(TS 36.331)"
            DEFVAL { 6 }
            ::= { asLteStkCellDedCfgEntry 31 }

        
        -- 1.3.6.1.4.1.989.1.20.1.4.9.1.32
        asLteStkCellDedCfgPhyCqiPucchResourceIndex OBJECT-TYPE
            SYNTAX Integer32 (0..1185)
            MAX-ACCESS read-write
            STATUS current
            DESCRIPTION
                "See section 7.2 in 36.213
                IE cqi-PUCCH-ResourceIndex(TS 36.331)"
            DEFVAL { 0 }
            ::= { asLteStkCellDedCfgEntry 32 }

        
        -- 1.3.6.1.4.1.989.1.20.1.4.9.1.33
        asLteStkCellDedCfgPhyCqiPmiConfigIndex OBJECT-TYPE
            SYNTAX Integer32 (0..1023)
            MAX-ACCESS read-write
            STATUS current
            DESCRIPTION
                "CQI (Channel Quality Indicator)/PMI (Precoding Matrix Information) periodicity 
                and Offset configuration index.
                IE cqi-pmi-ConfigIndex(TS 36.331)"
            DEFVAL { 25 }
            ::= { asLteStkCellDedCfgEntry 33 }

        
        -- 1.3.6.1.4.1.989.1.20.1.4.9.1.34
        asLteStkCellDedCfgPhyCqiRIConfigIndex OBJECT-TYPE
            SYNTAX Integer32 (0..1023)
            MAX-ACCESS read-write
            STATUS current
            DESCRIPTION
                "RI (Rank Indication) Configuration Index. Used in determining the subframes in which an 
                RI report should be sent.
                IE ri-ConfigIndex(TS 36.331)"
            DEFVAL { 483 }
            ::= { asLteStkCellDedCfgEntry 34 }

        
        -- 1.3.6.1.4.1.989.1.20.1.4.9.1.35
        asLteStkCellDedCfgPhySimultaneousAckNackAndCqi OBJECT-TYPE
            SYNTAX AsCmnTcBooleanSwitch
            MAX-ACCESS read-write
            STATUS current
            DESCRIPTION
                "Indicates whether simultaneous ACK/NACK and CQI in one subframe is supported.
                IE simultaneousAckNackAndCQI(TS 36.331)"
            DEFVAL { 0 }
            ::= { asLteStkCellDedCfgEntry 35 }

        
        -- 1.3.6.1.4.1.989.1.20.1.4.9.1.36
        asLteStkCellDedCfgPhySrPucchResourceIndex OBJECT-TYPE
            SYNTAX Integer32 (0..2047)
            MAX-ACCESS read-write
            STATUS current
            DESCRIPTION
                "PUCCH resource index to be used for sending an SR (Scheduling Request).
                IE sr-PUCCH-ConfigIndex(TS 36.331)"
            DEFVAL { 0 }
            ::= { asLteStkCellDedCfgEntry 36 }

        
        -- 1.3.6.1.4.1.989.1.20.1.4.9.1.37
        asLteStkCellDedCfgPhyDsrTransMax OBJECT-TYPE
            SYNTAX AsLteStkCellDedCfgPhyDsrTransMaxType
            MAX-ACCESS read-write
            STATUS current
            DESCRIPTION
                "Parameter for SR (Scheduling Request) transmission.
                IE dsr-TransMax(TS 36.331)"
            DEFVAL { 4 }
            ::= { asLteStkCellDedCfgEntry 37 }

        
        -- 1.3.6.1.4.1.989.1.20.1.4.9.1.38
        asLteStkCellDedCfgPhyPdschAckNackRepFactor OBJECT-TYPE
            SYNTAX AsLteStkCellDedCfgPhyPdschAckNackRepFactorType
            MAX-ACCESS read-write
            STATUS current
            DESCRIPTION
                "Number of time ACK/NACK could be repeated for a PDSCH transmission.
                IE repititionFactor(TS 36.331)"
            DEFVAL { 0 }
            ::= { asLteStkCellDedCfgEntry 38 }

        
        -- 1.3.6.1.4.1.989.1.20.1.4.9.1.39
        asLteStkCellDedCfgPhyN1PucchAckNackRep OBJECT-TYPE
            SYNTAX Integer32 (0..2047)
            MAX-ACCESS read-write
            STATUS current
            DESCRIPTION
                "PUCCH resource for ACK/NACk repetition.
                IE n1PUCCH-AN-Rep(TS 36.331)"
            DEFVAL { 0 }
            ::= { asLteStkCellDedCfgEntry 39 }

        
        -- 1.3.6.1.4.1.989.1.20.1.4.9.1.40
        asLteStkCellDedCfgUeTransmissionMode OBJECT-TYPE
            SYNTAX AsLteStkCellDedCfgUeTransmissionMode
            MAX-ACCESS read-write
            STATUS current
            DESCRIPTION
                "Transmission mode of a UE.
                IE transmissionMode(TS 36.331)"
            DEFVAL { 0 }
            ::= { asLteStkCellDedCfgEntry 40 }

        
        -- 1.3.6.1.4.1.989.1.20.1.4.9.1.41
        asLteStkCellDedCfgDrbPdcpDiscardTimer OBJECT-TYPE
            SYNTAX AsLteStkCellDedCfgDrbPdcpDiscardTimerType
            UNITS "msecs"
            MAX-ACCESS read-write
            STATUS current
            DESCRIPTION
                "PDCP Config for data radio bearers (DRBs) - Discard Timer value.
                IE discardTimer(TS 36.331)"
            DEFVAL { 7 }
            ::= { asLteStkCellDedCfgEntry 41 }

        
        -- 1.3.6.1.4.1.989.1.20.1.4.9.1.42
        asLteStkCellDedCfgDrbPdcpStatusRptReq OBJECT-TYPE
            SYNTAX AsCmnTcBooleanSwitch
            MAX-ACCESS read-write
            STATUS current
            DESCRIPTION
                "PDCP Config for data radio bearers (DRBs).  Indicates whether status report
                is required or not.
                IE statusReportRequired(TS 36.331)"
            DEFVAL { 1 }
            ::= { asLteStkCellDedCfgEntry 42 }

        
        -- 1.3.6.1.4.1.989.1.20.1.4.9.1.43
        asLteStkCellDedCfgDrbTPollRetransmit OBJECT-TYPE
            SYNTAX AsLteStkCellDedCfgTPollRetransmitType
            MAX-ACCESS read-write
            STATUS current
            DESCRIPTION
                "Value for the RLC poll-Retransmit timer for DRBs(AM Radio Bearers).
                IE t-PollRetransmit(TS 36.331)"
            DEFVAL { 15 }
            ::= { asLteStkCellDedCfgEntry 43 }

        
        -- 1.3.6.1.4.1.989.1.20.1.4.9.1.44
        asLteStkCellDedCfgDrbPollPdu OBJECT-TYPE
            SYNTAX AsLteStkCellDedCfgPollPduType
            MAX-ACCESS read-write
            STATUS current
            DESCRIPTION
                "Value for the RLC poll-PDU constant for DRBs (Data Radio Bearers)
                IE pollPDU(TS 36.331)"
            DEFVAL { 2 }
            ::= { asLteStkCellDedCfgEntry 44 }

        
        -- 1.3.6.1.4.1.989.1.20.1.4.9.1.45
        asLteStkCellDedCfgDrbPollByte OBJECT-TYPE
            SYNTAX AsLteStkCellDedCfgPollByteType
            UNITS "kBytes"
            MAX-ACCESS read-write
            STATUS current
            DESCRIPTION
                "Value for the RLC poll-Byte timer for DRBs (Data Radio Bearers)
                IE pollByte(TS 36.331)"
            DEFVAL { 13 }
            ::= { asLteStkCellDedCfgEntry 45 }

        
        -- 1.3.6.1.4.1.989.1.20.1.4.9.1.46
        asLteStkCellDedCfgDrbMaxRetxThreshold OBJECT-TYPE
            SYNTAX AsLteStkCellDedCfgMaxRetxThresholdType
            MAX-ACCESS read-write
            STATUS current
            DESCRIPTION
                "Value for the RLC max-retransmission threshold for DRBs (Data Radio Bearers)
                IE maxRetxThreshold(TS 36.331)"
            DEFVAL { 5 }
            ::= { asLteStkCellDedCfgEntry 46 }

        
        -- 1.3.6.1.4.1.989.1.20.1.4.9.1.47
        asLteStkCellDedCfgDrbTReordering OBJECT-TYPE
            SYNTAX AsLteStkCellDedCfgTReorderingType
            UNITS "mSecs"
            MAX-ACCESS read-write
            STATUS current
            DESCRIPTION
                "Value for the RLC Re-ordering timer threshold for DRBs (Data Radio Bearers)
                IE t-Reordering(TS 36.331)"
            DEFVAL { 16 }
            ::= { asLteStkCellDedCfgEntry 47 }

        
        -- 1.3.6.1.4.1.989.1.20.1.4.9.1.48
        asLteStkCellDedCfgDrbTStatusProhibit OBJECT-TYPE
            SYNTAX AsLteStkCellDedCfgTStatusProhibitType
            UNITS "mSecs"
            MAX-ACCESS read-write
            STATUS current
            DESCRIPTION
                "Value for the RLC Status Prohibit  timer threshold for DRBs (Data Radio Bearers)
                IE t-StatusProhibit(TS 36.331)"
            DEFVAL { 12 }
            ::= { asLteStkCellDedCfgEntry 48 }

        
        -- 1.3.6.1.4.1.989.1.20.1.4.9.1.49
        asLteStkCellDedCfgDrbLogicalChannelPriority OBJECT-TYPE
            SYNTAX Integer32 (1..16)
            UNITS "mSecs"
            MAX-ACCESS read-write
            STATUS current
            DESCRIPTION
                "Priority of logical channel corresponding to DRBs at MAC. Increasing values show decreasing priority.
                IE priority(in ul-SpecificParameters)(TS 36.331)"
            DEFVAL { 6 }
            ::= { asLteStkCellDedCfgEntry 49 }

        
        -- 1.3.6.1.4.1.989.1.20.1.4.9.1.50
        asLteStkCellDedCfgDrbPriBitRate OBJECT-TYPE
            SYNTAX AsLteStkCellDedCfgPriBitRateType
            UNITS "KBytes/sec"
            MAX-ACCESS read-write
            STATUS current
            DESCRIPTION
                "Prioritised bit rate for logical channels corresponding to DRB1 at MAC.
                IE prioritisedBitRate(in ul-SpecificParameters)(TS 36.331)"
            DEFVAL { 0 }
            ::= { asLteStkCellDedCfgEntry 50 }

        
        -- 1.3.6.1.4.1.989.1.20.1.4.9.1.51
        asLteStkCellDedCfgDrbBucketSizeDuration OBJECT-TYPE
            SYNTAX AsLteStkCellDedCfgBucketSizeDurationType
            UNITS "mSecs"
            MAX-ACCESS read-write
            STATUS current
            DESCRIPTION
                "Bucket size Duration for DRB1 for logical channel prioritization.
                IE bucketSizeDuration(in ul-SpecificParameters)(TS 36.331)"
            DEFVAL { 1 }
            ::= { asLteStkCellDedCfgEntry 51 }

        
        -- 1.3.6.1.4.1.989.1.20.1.4.9.1.52
        asLteStkCellDedCfgDrbLogicalChannelGroup OBJECT-TYPE
            SYNTAX Integer32 (0..3)
            MAX-ACCESS read-write
            STATUS current
            DESCRIPTION
                "Logical channel group to which DRB1 belongs.
                IE logicalChannelGroup(in ul-SpecificParameters)(TS 36.331)"
            DEFVAL { 1 }
            ::= { asLteStkCellDedCfgEntry 52 }

        
        -- 1.3.6.1.4.1.989.1.20.1.4.9.1.53
        asLteStkCellDedCfgPdschDlPowerAllocation OBJECT-TYPE
            SYNTAX AsLteStkCellDedCfgPdschDlPowerAllocationType
            UNITS "dBm"
            MAX-ACCESS read-write
            STATUS current
            DESCRIPTION
                "The downlink power allocation on the PDSCH (Physical Downlink Shared Channel) channel.
                IE p-a (TS36.331)"
            DEFVAL { 4 }
            ::= { asLteStkCellDedCfgEntry 53 }

        
        -- 1.3.6.1.4.1.989.1.20.1.4.9.1.54
        asLteStkCellDedCfgPhyN2TxAntennaTm3 OBJECT-TYPE
            SYNTAX Unsigned32
            MAX-ACCESS read-write
            STATUS current
            DESCRIPTION
                "Corresponds to n2TxAntenna in transmission mode 3.
                IE n2TxAntenna-tm3 (TS36.331)"
            DEFVAL { 'C0000000'h }
            ::= { asLteStkCellDedCfgEntry 54 }

        
        -- 1.3.6.1.4.1.989.1.20.1.4.9.1.55
        asLteStkCellDedCfgPhyN4TxAntennaTm3 OBJECT-TYPE
            SYNTAX Unsigned32
            MAX-ACCESS read-write
            STATUS current
            DESCRIPTION
                "Corresponds to n4TxAntenna in transmission mode 3.
                IE n4TxAntenna-tm3 (TS36.331)"
            DEFVAL { 0 }
            ::= { asLteStkCellDedCfgEntry 55 }

        
        -- 1.3.6.1.4.1.989.1.20.1.4.9.1.56
        asLteStkCellDedCfgPhyCodebookRestrictionPresent OBJECT-TYPE
            SYNTAX AsCmnTcBooleanSwitch
            MAX-ACCESS read-write
            STATUS current
            DESCRIPTION
                "Indicates whether codebook subset restriction config is present"
            DEFVAL { 0 }
            ::= { asLteStkCellDedCfgEntry 56 }

        
        -- 1.3.6.1.4.1.989.1.20.1.4.10
        asLteStkMacCfgTable OBJECT-TYPE
            SYNTAX SEQUENCE OF AsLteStkMacCfgEntry
            MAX-ACCESS not-accessible
            STATUS current
            DESCRIPTION
                "Configuration for the LTE MAC, Scheduler and Convergence Layer"
            ::= { asLteStkIf 10 }

        
        -- 1.3.6.1.4.1.989.1.20.1.4.10.1
        asLteStkMacCfgEntry OBJECT-TYPE
            SYNTAX AsLteStkMacCfgEntry
            MAX-ACCESS not-accessible
            STATUS current
            DESCRIPTION
                "Description."
            INDEX { ifIndex }
            ::= { asLteStkMacCfgTable 1 }

        
        AsLteStkMacCfgEntry ::=
            SEQUENCE { 
                asLteStkMacCfgPeriodicCqiReportingMode
                    AsLteStkMacCfgPeriodicCqiReportingModeType,
                asLteStkMacCfgPeriodicCqiPeriodicity
                    AsLteStkMacCfgPeriodicCqiPeriodicityType,
                asLteStkMacCfgPeriodicCqiSubFrameOffset
                    Integer32,
                asLteStkMacCfgPeriodicCqiOffset
                    Integer32,
                asLteStkMacCfgPeriodicCqiCfgK
                    Integer32,
                asLteStkMacCfgPeriodicCqiPMIConfigIndex
                    Integer32,
                asLteStkMacCfgHARQDeltaOffset
                    Integer32,
                asLteStkMacCfgTimingAlignmentTimerPresent
                    AsCmnTcBooleanSwitch,
                asLteStkMacCfgTimingAlignmentTimerValue
                    Integer32,
                asLteStkMacCfgUlTrgCqi
                    Integer32,
                asLteStkMacCfgNumMacInst
                    Integer32,
                asLteStkMacCfgMaxUEPerUlSubframe
                    Integer32,
                asLteStkMacCfgMaxUEPerDlSubframe
                    Integer32,
                asLteStkMacCfgMaxUlBwPerUe
                    Integer32,
                asLteStkMacCfgMaxDlBwPerUe
                    Integer32,
                asLteStkMacCfgMaxDlRetxBwPerUe
                    Integer32,
                asLteStkMacCfgMaxNewUeDlPerTti
                    Integer32,
                asLteStkMacCfgMaxNewUeUlPerTti
                    Integer32,
                asLteStkMacCfgNumTxAntennas
                    Integer32,
                asLteStkMacCfgDlCyclicPrefixLength
                    AsLteStkCellCfgUlCyclicPrefixLengthType,
                asLteStkMacCfgDlMaxHARQTx
                    AsLteStkCellMaxHARQTxType,
                asLteStkMacCfgDlMaxMsg4HARQTx
                    AsLteStkCellMaxHARQTxType,
                asLteStkMacCfgStartRnti
                    Integer32,
                asLteStkMacCfgRntiSize
                    Integer32,
                asLteStkMacCfgControlFormatIndicator
                    Integer32,
                asLteStkMacCfgBcchPchRaCodeRate
                    Integer32,
                asLteStkMacCfgPdcchCodeRate
                    Integer32,
                asLteStkMacCfgPuschSubbandStart
                    Integer32,
                asLteStkMacCfgPuschNumOfSubbands
                    Integer32,
                asLteStkMacCfgPuschSizeOfSubbands
                    Integer32,
                asLteStkMacCfgPuschSizeSubbandDmrs
                    Integer32,
                asLteStkMacCfgDlfsEnabled
                    AsCmnTcBooleanSwitch,
                asLteStkMacCfgDlfsType
                    Integer32,
                asLteStkMacCfgDlfsThresholdCqi
                    Integer32,
                asLteStkMacCfgPhichNg
                    Integer32,
                asLteStkSchedulerSiRetxCnt
                    Integer32,
                asLteStkMacCfgPucchPwrFmt3RntiStart
                    Integer32,
                asLteStkMacCfgPucchPwrFmt3RntiSize
                    Integer32,
                asLteStkMacCfgPucchPwrFmt3aRntiStart
                    Integer32,
                asLteStkMacCfgPucchPwrFmt3aRntiSize
                    Integer32,
                asLteStkMacCfgPuschPwrFmt3RntiStart
                    Integer32,
                asLteStkMacCfgPuschPwrFmt3RntiSize
                    Integer32,
                asLteStkMacCfgPuschPwrFmt3aRntiStart
                    Integer32,
                asLteStkMacCfgPuschPwrFmt3aRntiSize
                    Integer32,
                asLteStkMacCfgDfltUEBitRate
                    Integer32,
                asLteStkMacCfgDfltUEQosGbr
                    Integer32,
                asLteStkMacCfgDfltUEQosMbr
                    Integer32,
                asLteStkMacCfgDfltUEQosQci
                    Integer32,
                asLteStkMacCfgPreambleSetCfgValid
                    AsCmnTcBooleanSwitch,
                asLteStkMacCfgPreambleSetCfgStart
                    Integer32,
                asLteStkMacCfgPreambleSetCfgSize
                    Integer32,
                asLteStkMacCfgNumPrachResources
                    Integer32,
                asLteStkMacCfgNumCmnLogicalChannels
                    Integer32,
                asLteStkMacCfgSubcarrierSpacing
                    AsLteStkMacCfgSubcarrierSpacingType,
                asLteStkMacCfgUeCqiInitialValue
                    Integer32,
                asLteStkMacCfgUeCqiFormatIndicator
                    AsLteStkMacCfgUeCqiFormatIndicatorType,
                asLteStkMacCfgUeCqiSubBandK
                    Integer32,
                asLteStkMacCfgTxAntennaSelection
                    AsLteStkMacCfgTxAntennaSelectionType,
                asLteStkMacCfgTxSrsSubframeConfigPrd
                    AsLteStkMacCfgSrsSubframeConfigPrdType
             }

        -- 1.3.6.1.4.1.989.1.20.1.4.10.1.1
        asLteStkMacCfgPeriodicCqiReportingMode OBJECT-TYPE
            SYNTAX AsLteStkMacCfgPeriodicCqiReportingModeType
            MAX-ACCESS read-write
            STATUS current
            DESCRIPTION
                "Determines the Reporting Mode for Periodic CQI.
                Sent in ueCfg to MAC Scheduler."
            DEFVAL { 1 }
            ::= { asLteStkMacCfgEntry 1 }

        
        -- 1.3.6.1.4.1.989.1.20.1.4.10.1.2
        asLteStkMacCfgPeriodicCqiPeriodicity OBJECT-TYPE
            SYNTAX AsLteStkMacCfgPeriodicCqiPeriodicityType
            MAX-ACCESS read-write
            STATUS current
            DESCRIPTION
                "Determines the periodicity with which Periodic CQI is reported.
                Sent in ueCfg to MAC Scheduler."
            DEFVAL { 2 }
            ::= { asLteStkMacCfgEntry 2 }

        
        -- 1.3.6.1.4.1.989.1.20.1.4.10.1.3
        asLteStkMacCfgPeriodicCqiSubFrameOffset OBJECT-TYPE
            SYNTAX Integer32
            MAX-ACCESS read-write
            STATUS current
            DESCRIPTION
                "Subframe offset for Periodic CQI config.
                Sent in ueCfg to MAC Scheduler."
            DEFVAL { 0 }
            ::= { asLteStkMacCfgEntry 3 }

        
        -- 1.3.6.1.4.1.989.1.20.1.4.10.1.4
        asLteStkMacCfgPeriodicCqiOffset OBJECT-TYPE
            SYNTAX Integer32
            MAX-ACCESS read-write
            STATUS current
            DESCRIPTION
                "Cqi offset for Periodic CQI config.
                Sent in ueCfg to MAC Scheduler."
            DEFVAL { 0 }
            ::= { asLteStkMacCfgEntry 4 }

        
        -- 1.3.6.1.4.1.989.1.20.1.4.10.1.5
        asLteStkMacCfgPeriodicCqiCfgK OBJECT-TYPE
            SYNTAX Integer32 (1..4)
            MAX-ACCESS read-write
            STATUS current
            DESCRIPTION
                "k value for Periodic CQI config.
                Sent in ueCfg to MAC Scheduler."
            DEFVAL { 2 }
            ::= { asLteStkMacCfgEntry 5 }

        
        -- 1.3.6.1.4.1.989.1.20.1.4.10.1.6
        asLteStkMacCfgPeriodicCqiPMIConfigIndex OBJECT-TYPE
            SYNTAX Integer32 (0..1023)
            MAX-ACCESS read-write
            STATUS current
            DESCRIPTION
                "CQI/PMI configuration index.
                Sent in ueCfg to MAC Scheduler."
            DEFVAL { 522 }
            ::= { asLteStkMacCfgEntry 6 }

        
        -- 1.3.6.1.4.1.989.1.20.1.4.10.1.7
        asLteStkMacCfgHARQDeltaOffset OBJECT-TYPE
            SYNTAX Integer32
            MAX-ACCESS read-write
            STATUS current
            DESCRIPTION
                "Delta HARQ Offset.
                Sent in ueCfg to MAC Scheduler."
            DEFVAL { 0 }
            ::= { asLteStkMacCfgEntry 7 }

        
        -- 1.3.6.1.4.1.989.1.20.1.4.10.1.8
        asLteStkMacCfgTimingAlignmentTimerPresent OBJECT-TYPE
            SYNTAX AsCmnTcBooleanSwitch
            MAX-ACCESS read-write
            STATUS current
            DESCRIPTION
                "Timing Alignment Timer present or not.
                Sent in ueCfg to MAC Scheduler"
            DEFVAL { 0 }
            ::= { asLteStkMacCfgEntry 8 }

        
        -- 1.3.6.1.4.1.989.1.20.1.4.10.1.9
        asLteStkMacCfgTimingAlignmentTimerValue OBJECT-TYPE
            SYNTAX Integer32
            MAX-ACCESS read-write
            STATUS current
            DESCRIPTION
                "Timing Alignment Timer value.
                Sent in ueCfg to MAC Scheduler"
            DEFVAL { 0 }
            ::= { asLteStkMacCfgEntry 9 }

        
        -- 1.3.6.1.4.1.989.1.20.1.4.10.1.10
        asLteStkMacCfgUlTrgCqi OBJECT-TYPE
            SYNTAX Integer32 (1..15)
            MAX-ACCESS read-write
            STATUS current
            DESCRIPTION
                "Target UL CQI to be achieved through power control."
            DEFVAL { 9 }
            ::= { asLteStkMacCfgEntry 10 }

        
        -- 1.3.6.1.4.1.989.1.20.1.4.10.1.11
        asLteStkMacCfgNumMacInst OBJECT-TYPE
            SYNTAX Integer32
            MAX-ACCESS read-write
            STATUS current
            DESCRIPTION
                "Number of MAC Instances running in the stack."
            DEFVAL { 0 }
            ::= { asLteStkMacCfgEntry 11 }

        
        -- 1.3.6.1.4.1.989.1.20.1.4.10.1.12
        asLteStkMacCfgMaxUEPerUlSubframe OBJECT-TYPE
            SYNTAX Integer32
            MAX-ACCESS read-write
            STATUS current
            DESCRIPTION
                "Maximum number of UEs that can be scheduled in UL in a subframe."
            DEFVAL { 2 }
            ::= { asLteStkMacCfgEntry 12 }

        
        -- 1.3.6.1.4.1.989.1.20.1.4.10.1.13
        asLteStkMacCfgMaxUEPerDlSubframe OBJECT-TYPE
            SYNTAX Integer32
            MAX-ACCESS read-write
            STATUS current
            DESCRIPTION
                "Maximum number of UEs that can be scheduled in DL in a subframe."
            DEFVAL { 2 }
            ::= { asLteStkMacCfgEntry 13 }

        
        -- 1.3.6.1.4.1.989.1.20.1.4.10.1.14
        asLteStkMacCfgMaxUlBwPerUe OBJECT-TYPE
            SYNTAX Integer32
            MAX-ACCESS read-write
            STATUS current
            DESCRIPTION
                "Maximum bandwidth that can be allocated to a UE in a subframe in UL."
            DEFVAL { 50 }
            ::= { asLteStkMacCfgEntry 14 }

        
        -- 1.3.6.1.4.1.989.1.20.1.4.10.1.15
        asLteStkMacCfgMaxDlBwPerUe OBJECT-TYPE
            SYNTAX Integer32
            MAX-ACCESS read-write
            STATUS current
            DESCRIPTION
                "Maximum bandwidth that can be allocated to a UE in a subframe in UL."
            DEFVAL { 50 }
            ::= { asLteStkMacCfgEntry 15 }

        
        -- 1.3.6.1.4.1.989.1.20.1.4.10.1.16
        asLteStkMacCfgMaxDlRetxBwPerUe OBJECT-TYPE
            SYNTAX Integer32
            MAX-ACCESS read-write
            STATUS current
            DESCRIPTION
                "Maximum bandwidth that can be allocated for a re-transmission to a UE
                in a subframe in DL."
            DEFVAL { 50 }
            ::= { asLteStkMacCfgEntry 16 }

        
        -- 1.3.6.1.4.1.989.1.20.1.4.10.1.17
        asLteStkMacCfgMaxNewUeDlPerTti OBJECT-TYPE
            SYNTAX Integer32
            MAX-ACCESS read-write
            STATUS current
            DESCRIPTION
                "Maximum number of UEs for which new transmissions(not retransmisions)
                can be scheduled in DL."
            DEFVAL { 1 }
            ::= { asLteStkMacCfgEntry 17 }

        
        -- 1.3.6.1.4.1.989.1.20.1.4.10.1.18
        asLteStkMacCfgMaxNewUeUlPerTti OBJECT-TYPE
            SYNTAX Integer32
            MAX-ACCESS read-write
            STATUS current
            DESCRIPTION
                "Maximum number of UEs for which new transmissions(not retransmisions)
                can be scheduled in UL."
            DEFVAL { 1 }
            ::= { asLteStkMacCfgEntry 18 }

        
        -- 1.3.6.1.4.1.989.1.20.1.4.10.1.19
        asLteStkMacCfgNumTxAntennas OBJECT-TYPE
            SYNTAX Integer32
            MAX-ACCESS read-write
            STATUS current
            DESCRIPTION
                "Number of antennas configured at the e-NodeB."
            DEFVAL { 1 }
            ::= { asLteStkMacCfgEntry 19 }

        
        -- 1.3.6.1.4.1.989.1.20.1.4.10.1.20
        asLteStkMacCfgDlCyclicPrefixLength OBJECT-TYPE
            SYNTAX AsLteStkCellCfgUlCyclicPrefixLengthType
            MAX-ACCESS read-write
            STATUS current
            DESCRIPTION
                "This tells if the cyclic prefix is normal or extended in DL."
            DEFVAL { 0 }
            ::= { asLteStkMacCfgEntry 20 }

        
        -- 1.3.6.1.4.1.989.1.20.1.4.10.1.21
        asLteStkMacCfgDlMaxHARQTx OBJECT-TYPE
            SYNTAX AsLteStkCellMaxHARQTxType
            MAX-ACCESS read-write
            STATUS current
            DESCRIPTION
                "Maximum HARQ transmissions in DL. Used for both SRBs and DRBs."
            DEFVAL { 2 }
            ::= { asLteStkMacCfgEntry 21 }

        
        -- 1.3.6.1.4.1.989.1.20.1.4.10.1.22
        asLteStkMacCfgDlMaxMsg4HARQTx OBJECT-TYPE
            SYNTAX AsLteStkCellMaxHARQTxType
            MAX-ACCESS read-write
            STATUS current
            DESCRIPTION
                "Maximum HARQ transmissions in DL for msg4."
            DEFVAL { 1 }
            ::= { asLteStkMacCfgEntry 22 }

        
        -- 1.3.6.1.4.1.989.1.20.1.4.10.1.23
        asLteStkMacCfgStartRnti OBJECT-TYPE
            SYNTAX Integer32
            MAX-ACCESS read-write
            STATUS current
            DESCRIPTION
                "The value from which RNTI (Radio Network Temporary Identifier) assignment
                for a UE starts."
            DEFVAL { 100 }
            ::= { asLteStkMacCfgEntry 23 }

        
        -- 1.3.6.1.4.1.989.1.20.1.4.10.1.24
        asLteStkMacCfgRntiSize OBJECT-TYPE
            SYNTAX Integer32
            MAX-ACCESS read-write
            STATUS current
            DESCRIPTION
                "Indicates the contiguous range of RNTIs (Radio Network Temporary Identifier)
                starting from asLteStkMacCfgStartRnti."
            DEFVAL { 10 }
            ::= { asLteStkMacCfgEntry 24 }

        
        -- 1.3.6.1.4.1.989.1.20.1.4.10.1.25
        asLteStkMacCfgControlFormatIndicator OBJECT-TYPE
            SYNTAX Integer32 (1..3)
            MAX-ACCESS read-write
            STATUS current
            DESCRIPTION
                "Control Format Indicator configuration."
            DEFVAL { 1 }
            ::= { asLteStkMacCfgEntry 25 }

        
        -- 1.3.6.1.4.1.989.1.20.1.4.10.1.26
        asLteStkMacCfgBcchPchRaCodeRate OBJECT-TYPE
            SYNTAX Integer32
            MAX-ACCESS read-write
            STATUS current
            DESCRIPTION
                "BCCH on DLSCH, PCH and RARsp coding rate."
            DEFVAL { 0 }
            ::= { asLteStkMacCfgEntry 26 }

        
        -- 1.3.6.1.4.1.989.1.20.1.4.10.1.27
        asLteStkMacCfgPdcchCodeRate OBJECT-TYPE
            SYNTAX Integer32
            MAX-ACCESS read-write
            STATUS current
            DESCRIPTION
                "PDCCH coding rate for broadcast RNTIs (Radio Network Temporary Identifier). "
            DEFVAL { 0 }
            ::= { asLteStkMacCfgEntry 27 }

        
        -- 1.3.6.1.4.1.989.1.20.1.4.10.1.28
        asLteStkMacCfgPuschSubbandStart OBJECT-TYPE
            SYNTAX Integer32
            MAX-ACCESS read-write
            STATUS current
            DESCRIPTION
                "Start of PUSCH Subbands in RBs. "
            DEFVAL { 1 }
            ::= { asLteStkMacCfgEntry 28 }

        
        -- 1.3.6.1.4.1.989.1.20.1.4.10.1.29
        asLteStkMacCfgPuschNumOfSubbands OBJECT-TYPE
            SYNTAX Integer32
            MAX-ACCESS read-write
            STATUS current
            DESCRIPTION
                "Number of PUSCH Subbands in RBs."
            DEFVAL { 8 }
            ::= { asLteStkMacCfgEntry 29 }

        
        -- 1.3.6.1.4.1.989.1.20.1.4.10.1.30
        asLteStkMacCfgPuschSizeOfSubbands OBJECT-TYPE
            SYNTAX Integer32
            MAX-ACCESS read-write
            STATUS current
            DESCRIPTION
                "Size of each PUSCH Subband in RBs."
            DEFVAL { 6 }
            ::= { asLteStkMacCfgEntry 30 }

        
        -- 1.3.6.1.4.1.989.1.20.1.4.10.1.31
        asLteStkMacCfgPuschSizeSubbandDmrs OBJECT-TYPE
            SYNTAX Integer32
            MAX-ACCESS read-write
            STATUS current
            DESCRIPTION
                "DMRS (demodulation reference signal) information per sub-band."
            DEFVAL { 1 }
            ::= { asLteStkMacCfgEntry 31 }

        
        -- 1.3.6.1.4.1.989.1.20.1.4.10.1.32
        asLteStkMacCfgDlfsEnabled OBJECT-TYPE
            SYNTAX AsCmnTcBooleanSwitch
            MAX-ACCESS read-write
            STATUS current
            DESCRIPTION
                "Parameter indicating if DLFS (downlink frequency selective) scheduler is enabled or not."
            DEFVAL { 0 }
            ::= { asLteStkMacCfgEntry 32 }

        
        -- 1.3.6.1.4.1.989.1.20.1.4.10.1.33
        asLteStkMacCfgDlfsType OBJECT-TYPE
            SYNTAX Integer32
            MAX-ACCESS read-write
            STATUS current
            DESCRIPTION
                "Type of DLFS (downlink frequency selective) scheduler"
            DEFVAL { 0 }
            ::= { asLteStkMacCfgEntry 33 }

        
        -- 1.3.6.1.4.1.989.1.20.1.4.10.1.34
        asLteStkMacCfgDlfsThresholdCqi OBJECT-TYPE
            SYNTAX Integer32
            MAX-ACCESS read-write
            STATUS current
            DESCRIPTION
                "Threshold CQI value below which the sub-band is not considered for allocation 
                for a frequency selective cell."
            DEFVAL { 1 }
            ::= { asLteStkMacCfgEntry 34 }

        
        -- 1.3.6.1.4.1.989.1.20.1.4.10.1.35
        asLteStkMacCfgPhichNg OBJECT-TYPE
            SYNTAX Integer32
            MAX-ACCESS read-write
            STATUS current
            DESCRIPTION
                "Ng value for PHICH. Used to determine the number of PHICH groups."
            DEFVAL { 0 }
            ::= { asLteStkMacCfgEntry 35 }

        
        -- 1.3.6.1.4.1.989.1.20.1.4.10.1.36
        asLteStkSchedulerSiRetxCnt OBJECT-TYPE
            SYNTAX Integer32
            MAX-ACCESS read-write
            STATUS current
            DESCRIPTION
                "System Information Retransmission count."
            DEFVAL { 1 }
            ::= { asLteStkMacCfgEntry 36 }

        
        -- 1.3.6.1.4.1.989.1.20.1.4.10.1.37
        asLteStkMacCfgPucchPwrFmt3RntiStart OBJECT-TYPE
            SYNTAX Integer32
            MAX-ACCESS read-write
            STATUS current
            DESCRIPTION
                "Starting RNTI for PUCCH Format 3 for power control."
            DEFVAL { 1 }
            ::= { asLteStkMacCfgEntry 37 }

        
        -- 1.3.6.1.4.1.989.1.20.1.4.10.1.38
        asLteStkMacCfgPucchPwrFmt3RntiSize OBJECT-TYPE
            SYNTAX Integer32
            MAX-ACCESS read-write
            STATUS current
            DESCRIPTION
                "Size of RNTIs for PUCCH Format 3 for power control."
            DEFVAL { 1 }
            ::= { asLteStkMacCfgEntry 38 }

        
        -- 1.3.6.1.4.1.989.1.20.1.4.10.1.39
        asLteStkMacCfgPucchPwrFmt3aRntiStart OBJECT-TYPE
            SYNTAX Integer32
            MAX-ACCESS read-write
            STATUS current
            DESCRIPTION
                "Starting RNTI for PUCCH Format 3a for power control."
            DEFVAL { 1 }
            ::= { asLteStkMacCfgEntry 39 }

        
        -- 1.3.6.1.4.1.989.1.20.1.4.10.1.40
        asLteStkMacCfgPucchPwrFmt3aRntiSize OBJECT-TYPE
            SYNTAX Integer32
            MAX-ACCESS read-write
            STATUS current
            DESCRIPTION
                "Size of RNTIs for PUCCH Format 3a for power control."
            DEFVAL { 1 }
            ::= { asLteStkMacCfgEntry 40 }

        
        -- 1.3.6.1.4.1.989.1.20.1.4.10.1.41
        asLteStkMacCfgPuschPwrFmt3RntiStart OBJECT-TYPE
            SYNTAX Integer32
            MAX-ACCESS read-write
            STATUS current
            DESCRIPTION
                "Starting RNTI for PUSCH Format 3 for power control."
            DEFVAL { 1 }
            ::= { asLteStkMacCfgEntry 41 }

        
        -- 1.3.6.1.4.1.989.1.20.1.4.10.1.42
        asLteStkMacCfgPuschPwrFmt3RntiSize OBJECT-TYPE
            SYNTAX Integer32
            MAX-ACCESS read-write
            STATUS current
            DESCRIPTION
                "Size of RNTIs for PUSCH Format 3 for power control."
            DEFVAL { 1 }
            ::= { asLteStkMacCfgEntry 42 }

        
        -- 1.3.6.1.4.1.989.1.20.1.4.10.1.43
        asLteStkMacCfgPuschPwrFmt3aRntiStart OBJECT-TYPE
            SYNTAX Integer32
            MAX-ACCESS read-write
            STATUS current
            DESCRIPTION
                "Starting RNTI for PUSCH Format 3a for power control."
            DEFVAL { 1 }
            ::= { asLteStkMacCfgEntry 43 }

        
        -- 1.3.6.1.4.1.989.1.20.1.4.10.1.44
        asLteStkMacCfgPuschPwrFmt3aRntiSize OBJECT-TYPE
            SYNTAX Integer32
            MAX-ACCESS read-write
            STATUS current
            DESCRIPTION
                "Size of RNTIs for PUSCH Format 3a for power control."
            DEFVAL { 1 }
            ::= { asLteStkMacCfgEntry 44 }

        
        -- 1.3.6.1.4.1.989.1.20.1.4.10.1.45
        asLteStkMacCfgDfltUEBitRate OBJECT-TYPE
            SYNTAX Integer32
            MAX-ACCESS read-write
            STATUS current
            DESCRIPTION
                "Default bit rate for a UE."
            DEFVAL { 80000000 }
            ::= { asLteStkMacCfgEntry 45 }

        
        -- 1.3.6.1.4.1.989.1.20.1.4.10.1.46
        asLteStkMacCfgDfltUEQosGbr OBJECT-TYPE
            SYNTAX Integer32
            MAX-ACCESS read-write
            STATUS current
            DESCRIPTION
                "Default QOS guarenteed bit rate for a UE."
            DEFVAL { 80000000 }
            ::= { asLteStkMacCfgEntry 46 }

        
        -- 1.3.6.1.4.1.989.1.20.1.4.10.1.47
        asLteStkMacCfgDfltUEQosMbr OBJECT-TYPE
            SYNTAX Integer32
            MAX-ACCESS read-write
            STATUS current
            DESCRIPTION
                "Default QOS maximum bit rate for a UE."
            DEFVAL { 80000000 }
            ::= { asLteStkMacCfgEntry 47 }

        
        -- 1.3.6.1.4.1.989.1.20.1.4.10.1.48
        asLteStkMacCfgDfltUEQosQci OBJECT-TYPE
            SYNTAX Integer32
            MAX-ACCESS read-write
            STATUS current
            DESCRIPTION
                "Default QCI for a UE."
            DEFVAL { 1 }
            ::= { asLteStkMacCfgEntry 48 }

        
        -- 1.3.6.1.4.1.989.1.20.1.4.10.1.49
        asLteStkMacCfgPreambleSetCfgValid OBJECT-TYPE
            SYNTAX AsCmnTcBooleanSwitch
            MAX-ACCESS read-write
            STATUS current
            DESCRIPTION
                "Indicates if other PreambleSet configuration fields are valid."
            DEFVAL { 0 }
            ::= { asLteStkMacCfgEntry 49 }

        
        -- 1.3.6.1.4.1.989.1.20.1.4.10.1.50
        asLteStkMacCfgPreambleSetCfgStart OBJECT-TYPE
            SYNTAX Integer32
            MAX-ACCESS read-write
            STATUS current
            DESCRIPTION
                "Start Preamble ID for the range managed by MAC."
            DEFVAL { 0 }
            ::= { asLteStkMacCfgEntry 50 }

        
        -- 1.3.6.1.4.1.989.1.20.1.4.10.1.51
        asLteStkMacCfgPreambleSetCfgSize OBJECT-TYPE
            SYNTAX Integer32
            MAX-ACCESS read-write
            STATUS current
            DESCRIPTION
                "Indicates contiguous range of premables managaed by MAC starting 
                from asLteStkMacCfgPreambleSetCfgStart."
            DEFVAL { 0 }
            ::= { asLteStkMacCfgEntry 51 }

        
        -- 1.3.6.1.4.1.989.1.20.1.4.10.1.52
        asLteStkMacCfgNumPrachResources OBJECT-TYPE
            SYNTAX Integer32
            MAX-ACCESS read-write
            STATUS current
            DESCRIPTION
                "Available number of PRACH resources."
            DEFVAL { 0 }
            ::= { asLteStkMacCfgEntry 52 }

        
        -- 1.3.6.1.4.1.989.1.20.1.4.10.1.53
        asLteStkMacCfgNumCmnLogicalChannels OBJECT-TYPE
            SYNTAX Integer32
            MAX-ACCESS read-write
            STATUS current
            DESCRIPTION
                "Total number of logical channels that are configured."
            DEFVAL { 6 }
            ::= { asLteStkMacCfgEntry 53 }

        
        -- 1.3.6.1.4.1.989.1.20.1.4.10.1.54
        asLteStkMacCfgSubcarrierSpacing OBJECT-TYPE
            SYNTAX AsLteStkMacCfgSubcarrierSpacingType
            MAX-ACCESS read-write
            STATUS current
            DESCRIPTION
                "Sub-carrier spacing - can be 15kHz or 7.5 kHz."
            DEFVAL { 0 }
            ::= { asLteStkMacCfgEntry 54 }

        
        -- 1.3.6.1.4.1.989.1.20.1.4.10.1.55
        asLteStkMacCfgUeCqiInitialValue OBJECT-TYPE
            SYNTAX Integer32 (1..15)
            MAX-ACCESS read-write
            STATUS current
            DESCRIPTION
                "The intial value used for CQI reporting in the absence of CQI reports from the UE"
            DEFVAL { 6 }
            ::= { asLteStkMacCfgEntry 55 }

        
        -- 1.3.6.1.4.1.989.1.20.1.4.10.1.56
        asLteStkMacCfgUeCqiFormatIndicator OBJECT-TYPE
            SYNTAX AsLteStkMacCfgUeCqiFormatIndicatorType
            MAX-ACCESS read-write
            STATUS current
            DESCRIPTION
                "Periodic CQI Reporting format"
            DEFVAL { 0 }
            ::= { asLteStkMacCfgEntry 56 }

        
        -- 1.3.6.1.4.1.989.1.20.1.4.10.1.57
        asLteStkMacCfgUeCqiSubBandK OBJECT-TYPE
            SYNTAX Integer32
            MAX-ACCESS read-write
            STATUS current
            DESCRIPTION
                "Another CQI Reporting parameter"
            DEFVAL { 0 }
            ::= { asLteStkMacCfgEntry 57 }

        
        -- 1.3.6.1.4.1.989.1.20.1.4.10.1.58
        asLteStkMacCfgTxAntennaSelection OBJECT-TYPE
            SYNTAX AsLteStkMacCfgTxAntennaSelectionType
            MAX-ACCESS read-write
            STATUS current
            DESCRIPTION
                "Determines whether the UE transmit antenna selection is closedLoop or OpenLoop."
            DEFVAL { 0 }
            ::= { asLteStkMacCfgEntry 58 }

        
        -- 1.3.6.1.4.1.989.1.20.1.4.10.1.59
        asLteStkMacCfgTxSrsSubframeConfigPrd OBJECT-TYPE
            SYNTAX AsLteStkMacCfgSrsSubframeConfigPrdType
            UNITS "msecs"
            MAX-ACCESS read-write
            STATUS current
            DESCRIPTION
                "Sounding Reference signal periodicity in msecs"
            DEFVAL { 0 }
            ::= { asLteStkMacCfgEntry 59 }

        
    
    END

--
-- ASLTE-STACK-MIB.mib
--
