--
-- ASMAX-AD-BRIDGE-MIB.mib
-- MIB generated by MG-SOFT Visual MIB Builder 2010 Version 8.0  Build 400
-- Wednesday, May 04, 2011 at 09:17:53
--

	ASMAX-AD-BRIDGE-MIB DEFINITIONS ::= BEGIN
 
		IMPORTS
			AsmaxBooleanSwitch			
				FROM AIRSPAN-ASMAX-COMMON-MIB			
			asMaxMisc			
				FROM AIRSPAN-PRODUCTS-MIB			
			ifIndex, InterfaceIndex			
				FROM IF-MIB			
			InetAddressType, InetAddress			
				FROM INET-ADDRESS-MIB			
			OBJECT-GROUP, MODULE-COMPLIANCE			
				FROM SNMPv2-CONF			
			Integer32, Unsigned32, OBJECT-TYPE, MODULE-IDENTITY			
				FROM SNMPv2-SMI			
			RowStatus, MacAddress, TEXTUAL-CONVENTION			
				FROM SNMPv2-TC;
	
	
		-- 1.3.6.1.4.1.989.1.16.5.4
		asMaxAdBridge MODULE-IDENTITY 
			LAST-UPDATED "200911091123Z"		-- November 09, 2009 at 11:23 GMT
			ORGANIZATION 
				"Airspan Communications Lt."
			CONTACT-INFO 
				"Krzysztof Dudzinski
				Airspan Communications Ltd.
				email: kdudzins@airspan.com
				http://www.airspan.com"
			DESCRIPTION 
				"The VLAN Bridge MIB module for managing the IEEE 802.1ad functionality
				on Airspan basestations supporting IEEE 802.16e."
			REVISION "201105031620Z"		-- May 03, 2011 at 16:20 GMT
			DESCRIPTION 
				"Added: asDot1adBridgeSTagConfigMode, asDot1adBridgeSTagPortVlan, asDot1adBridgeUseCTagPriority, asDot1adBridgeSTagPriority
				to table asDot1adBridgeTable
				Added: asDot1adSsPortProvClassSTagPriority, asDot1adSsPortProvClassUseCTagPriority, asDot1adSsPortProvClassSTagVlan, asDot1adSsPortProvClassQinqSupported
				to table asDot1adSsPortProvClassTable
				Added: asDot1adSsPortProvsTagPriority, asDot1adSsPortProvUseCTagPriority, asDot1adSsPortProvSTagVlan, asDot1adSsPortProvQinqSupported
				to table asDot1adSsPortProvTable"
			REVISION "200911091123Z"		-- November 09, 2009 at 11:23 GMT
			DESCRIPTION 
				"Draft 7:
				- Added object asDot1adBridgeMgmtVlanIsTagged"
			REVISION "200909211123Z"		-- September 21, 2009 at 11:23 GMT
			DESCRIPTION 
				"Draft 6:
				- Added object asDot1adVlanProvBcastServiceClassIndex"
			REVISION "200803311631Z"		-- March 31, 2008 at 16:31 GMT
			DESCRIPTION 
				"Draft 5:
				added: asDot1adVlanProvArpSourceIpAddress, asDot1adVlanProvLocalIpAddress, asDot1adVlanProvLocalIpNetMask
				new name for: asDot1adVlanProvIpAddressType (was asDot1adVlanProvEdgeRouterIpAddressType)"
			REVISION "200802271540Z"		-- February 27, 2008 at 15:40 GMT
			DESCRIPTION 
				"Draft 4
				- Added new objects asDot1adBridgeMgmtVlanUserPriority, asDot1adBridgeAsnGwVlanId,
				asDot1adBridgeAsnGwVlanUserPriority, asDot1adBridgeSTagEtherType to the asDot1adBridgeTable"
			REVISION "200801291715Z"		-- January 29, 2008 at 17:15 GMT
			DESCRIPTION 
				"Draft 3
				- Updated following review.  Renumber of OIDs to remove holes and 
				use external indexes where possible"
			REVISION "200801281256Z"		-- January 28, 2008 at 12:56 GMT
			DESCRIPTION 
				"Draft 2
				- Added tables for class-based port provisioning.
				- Introduced extra level to separate bridge objects, per-port objects and port class objects.
				- Fixes following review to use AsDot1adVlanIdOrNone for PVIDs and avoid use of Unsigned32
				"
			REVISION "200711261707Z"		-- November 26, 2007 at 17:07 GMT
			DESCRIPTION 
				"Draft 1
				- Changed type of asDot1adVlanProvFwdingDbid from ASmaxBooleanSwitch to Unsigned32"
			REVISION "200711191208Z"		-- November 19, 2007 at 12:08 GMT
			DESCRIPTION 
				"Pre-Draft version"
			::= { asMaxMisc 4 }

		
	
--
-- Textual conventions
--
	
		AsDot1adVlanIdOrNone ::= TEXTUAL-CONVENTION
			DISPLAY-HINT 
				"d"
			STATUS current
			DESCRIPTION 
				"The VLAN-ID that uniquely identifies a specific VLAN,
				or no VLAN.  The special value of zero is used to
				indicate that no VLAN-ID is present or used.  This can
				be used in any situation where an object or a table entry
				must refer either to a specific VLAN, or to no VLAN.
				
				Note that a MIB object that is defined using this
				TEXTUAL-CONVENTION should clarify the meaning of
				'no VLAN' (i.e., the special value 0)."
			SYNTAX Integer32 (0 | 1..4094)

		AsDot1adVlanId ::= TEXTUAL-CONVENTION
			DISPLAY-HINT 
				"d"
			STATUS current
			DESCRIPTION 
				"The VLAN-ID that uniquely identifies a VLAN.  This
				is the 12-bit VLAN-ID used in the VLAN Tag header.
				The range is defined by the REFERENCEd specification."
			REFERENCE 
				"IEEE Std 802.1Q 2003 Edition, Virtual Bridged
				Local Area Networks."
			SYNTAX Integer32 (1..4094)

		AsDot1adVlanBroadcastMode ::= TEXTUAL-CONVENTION
			STATUS current
			DESCRIPTION 
				"Defines the various different modes available for transferring broadcast, multicast
				and flooded unknown destination traffic within the VLAN.
				Value broadcastModeMulticastGroup(0) means that the traffic is sent over a pair of 
				multicast groups over the air interface (one for tagged traffic and one for untagged 
				traffic).
				Value broadcastModeDuplicate(1) means that traffic is duplicated over unicast service
				flows to every SS in the VLAN.
				Value broadcastModeDrop(2) means that all broadcast, multicast and unknown
				destination traffic on the downlink is dropped.
				"
			SYNTAX INTEGER
				{
				broadcastModeMulticastGroup(0),
				broadcastModeDuplicate(1),
				broadcastModeDrop(2)
				}

		AsDot1adPortMode ::= TEXTUAL-CONVENTION
			STATUS current
			DESCRIPTION 
				"When the Bridge is operating in Provider-Bridge mode (802.1ad), this defines the mode 
				the port is operating in.  Allowed values are PNP (Provider Network Port), 
				CNP (Customer Network Port) and CEP (Customer Entry Port) (SS-only).  
				
				"
			SYNTAX INTEGER
				{
				portModePnp(0),
				portModeCnp(1),
				portModeCep(2)
				}

		AsDot1adAllowedFrameTypes ::= TEXTUAL-CONVENTION
			STATUS current
			DESCRIPTION 
				"When this is admitOnlyVlanTagged, the device will discard 
				untagged frames or Priority-Tagged frames received on this port.
				When admitAll(1), untagged frames or Priority-Tagged frames 
				received on the port will be accepted and assigned to 
				a VID based on the PVID of for this port.
				When admitOnlyUntagged(3), is set the device will discard 
				all VLAN tagged frames."
			SYNTAX INTEGER
				{
				admitAll(1),
				admitOnlyVlanTagged(2),
				admitOnlyUntagged(3)
				}

		AsDot1adClassName ::= TEXTUAL-CONVENTION
			STATUS current
			DESCRIPTION 
				"The name of a provisioning class used on the BS for class-based provisioning."
			SYNTAX OCTET STRING (SIZE (2..128))

		AsDot1adVlanIdOrAny ::= TEXTUAL-CONVENTION
			DISPLAY-HINT 
				"d"
			STATUS current
			DESCRIPTION 
				"The VLAN-ID that uniquely identifies a specific VLAN,
				or any VLAN.  The special value of 4095 is used to
				indicate a wildcard, i.e., any VLAN.  This can be used
				in any situation where an object or table entry must
				refer either to a specific VLAN or to any VLAN.
				
				Note that a MIB object that is defined using this
				TEXTUAL-CONVENTION should clarify the meaning of
				'any VLAN' (i.e., the special value 4095)."
			SYNTAX Integer32 (1..4094 | 4095)

		AsDot1adVlanIdOrAnyOrNone ::= TEXTUAL-CONVENTION
			DISPLAY-HINT 
				"d"
			STATUS current
			DESCRIPTION 
				"The VLAN-ID that uniquely identifies a specific VLAN,
				any VLAN, or no VLAN.  The special values 0 and 4095
				have the same meaning as described in the VlanIdOrAny
				and VlanIdOrNone TEXTUAL-CONVENTIONs.
				
				Note that a MIB object that is defined using this
				TEXTUAL-CONVENTION should clarify the meaning of
				'any VLAN' and 'no VLAN' (i.e., the special values
				0 and 4095)."
			SYNTAX Integer32 (0 | 1..4094 | 4095)

	
--
-- Node definitions
--
	
		-- 1.3.6.1.4.1.989.1.16.5.4.1
		asDot1adBridgeObjects OBJECT IDENTIFIER ::= { asMaxAdBridge 1 }

		
		-- 1.3.6.1.4.1.989.1.16.5.4.1.2
		asDot1adVlanProvTable OBJECT-TYPE
			SYNTAX SEQUENCE OF AsDot1adVlanProvEntry
			MAX-ACCESS not-accessible
			STATUS current
			DESCRIPTION
				"A table containing static provisioning information for
				each VLAN configured into the device by (local or
				network) management.  All entries are permanent and will
				be restored after the device is reset.
				"
			::= { asDot1adBridgeObjects 2 }

		
		-- 1.3.6.1.4.1.989.1.16.5.4.1.2.1
		asDot1adVlanProvEntry OBJECT-TYPE
			SYNTAX AsDot1adVlanProvEntry
			MAX-ACCESS not-accessible
			STATUS current
			DESCRIPTION
				"One row per VLAN ID."
			INDEX { asDot1adVlanProvId }
			::= { asDot1adVlanProvTable 1 }

		
		AsDot1adVlanProvEntry ::=
			SEQUENCE { 
				asDot1adVlanProvId
					AsDot1adVlanId,
				asDot1adVlanProvFwdingDbid
					Integer32,
				asDot1adVlanProvSsToSsEnabled
					AsmaxBooleanSwitch,
				asDot1adVlanProvFloodUnknownEnabled
					AsmaxBooleanSwitch,
				asDot1adVlanProvBroadcastMode
					AsDot1adVlanBroadcastMode,
				asDot1adVlanProvUntaggedMcastSfid
					Unsigned32,
				asDot1adVlanProvTaggedMcastSfid
					Unsigned32,
				asDot1adVlanProvDhcpRelayAgentActive
					INTEGER,
				asDot1adVlanProvMacForceForwardingEnabled
					AsmaxBooleanSwitch,
				asDot1adVlanProvIpAddressType
					InetAddressType,
				asDot1adVlanProvEdgeRouterIpAddress
					InetAddress,
				asDot1adVlanProvRowStatus
					RowStatus,
				asDot1adVlanProvArpSourceIpAddress
					InetAddress,
				asDot1adVlanProvLocalIpAddress
					InetAddress,
				asDot1adVlanProvLocalIpNetMask
					InetAddress,
				asDot1adVlanProvBcastServiceClassIndex
					Integer32
			 }

		-- 1.3.6.1.4.1.989.1.16.5.4.1.2.1.1
		asDot1adVlanProvId OBJECT-TYPE
			SYNTAX AsDot1adVlanId
			MAX-ACCESS not-accessible
			STATUS current
			DESCRIPTION
				"VLAN identifier. Only valid VLAN ID can be used i.e. 1 to 4094."
			::= { asDot1adVlanProvEntry 1 }

		
		-- 1.3.6.1.4.1.989.1.16.5.4.1.2.1.2
		asDot1adVlanProvFwdingDbid OBJECT-TYPE
			SYNTAX Integer32 (0..2147483647)
			MAX-ACCESS read-create
			STATUS current
			DESCRIPTION
				"ID of the Forwarding database for this Vlan.  Must not be 0. Is typically set to 1."
			::= { asDot1adVlanProvEntry 2 }

		
		-- 1.3.6.1.4.1.989.1.16.5.4.1.2.1.3
		asDot1adVlanProvSsToSsEnabled OBJECT-TYPE
			SYNTAX AsmaxBooleanSwitch
			MAX-ACCESS read-create
			STATUS current
			DESCRIPTION
				"When this is booleanTrue, traffic is allowed to flow directly between SS ports.
				"
			DEFVAL { booleanTrue }
			::= { asDot1adVlanProvEntry 3 }

		
		-- 1.3.6.1.4.1.989.1.16.5.4.1.2.1.4
		asDot1adVlanProvFloodUnknownEnabled OBJECT-TYPE
			SYNTAX AsmaxBooleanSwitch
			MAX-ACCESS read-create
			STATUS current
			DESCRIPTION
				"Determines whether traffic with an unknown destination in this Vlan can be flooded to every 
				compatible port."
			DEFVAL { booleanTrue }
			::= { asDot1adVlanProvEntry 4 }

		
		-- 1.3.6.1.4.1.989.1.16.5.4.1.2.1.5
		asDot1adVlanProvBroadcastMode OBJECT-TYPE
			SYNTAX AsDot1adVlanBroadcastMode
			MAX-ACCESS read-create
			STATUS current
			DESCRIPTION
				"Controls how broadcast, multicast and flooded traffic with an unknown destination is 
				handled in this VLAN."
			DEFVAL { broadcastModeMulticastGroup }
			::= { asDot1adVlanProvEntry 5 }

		
		-- 1.3.6.1.4.1.989.1.16.5.4.1.2.1.6
		asDot1adVlanProvUntaggedMcastSfid OBJECT-TYPE
			SYNTAX Unsigned32 (1..4294967295)
			MAX-ACCESS read-create
			STATUS current
			DESCRIPTION
				"SFID of the multicast service flow provisioned for untagged broadcast/multicast 
				VLAN traffic. The parameters of this service flow are defined 
				by asDot1adVlanProvBcastServiceClassIndex object."
			::= { asDot1adVlanProvEntry 6 }

		
		-- 1.3.6.1.4.1.989.1.16.5.4.1.2.1.7
		asDot1adVlanProvTaggedMcastSfid OBJECT-TYPE
			SYNTAX Unsigned32 (1..4294967295)
			MAX-ACCESS read-create
			STATUS current
			DESCRIPTION
				"SFID of the multicast service flow provisioned for the tagged broadcast/multicast 
				VLAN traffic. The parameters of this service flow are defined 
				by asDot1adVlanProvBcastServiceClassIndex object."
			::= { asDot1adVlanProvEntry 7 }

		
		-- 1.3.6.1.4.1.989.1.16.5.4.1.2.1.8
		asDot1adVlanProvDhcpRelayAgentActive OBJECT-TYPE
			SYNTAX INTEGER
				{
				dhcpAgentModeOff(0),
				dhcpAgentModeOption82Text(1),
				dhcpAgentModeOption82Binary(2)
				}
			MAX-ACCESS read-create
			STATUS current
			DESCRIPTION
				"Enables the addition of RelayAgentInd sub options in server bound
				DHCP messages, tagging with cctID as SS MAC, remID as BSMac"
			DEFVAL { dhcpAgentOff }
			::= { asDot1adVlanProvEntry 8 }

		
		-- 1.3.6.1.4.1.989.1.16.5.4.1.2.1.9
		asDot1adVlanProvMacForceForwardingEnabled OBJECT-TYPE
			SYNTAX AsmaxBooleanSwitch
			MAX-ACCESS read-create
			STATUS current
			DESCRIPTION
				"When this is booleanTrue, the Mac Force Forwarding option is enabled.
				"
			DEFVAL { booleanFalse }
			::= { asDot1adVlanProvEntry 9 }

		
		-- 1.3.6.1.4.1.989.1.16.5.4.1.2.1.10
		asDot1adVlanProvIpAddressType OBJECT-TYPE
			SYNTAX InetAddressType
			MAX-ACCESS read-create
			STATUS current
			DESCRIPTION
				"This specifies the type of IP address for all addresses configured 
				for this VLAN on a given BS.
				"
			DEFVAL { ipv4 }
			::= { asDot1adVlanProvEntry 10 }

		
		-- 1.3.6.1.4.1.989.1.16.5.4.1.2.1.11
		asDot1adVlanProvEdgeRouterIpAddress OBJECT-TYPE
			SYNTAX InetAddress
			MAX-ACCESS read-create
			STATUS current
			DESCRIPTION
				"This specifies the IP address of the edge router used by the BS.
				When Mac Forced Forwarding is enabled, uplink traffic is forwarded to this router.
				When operating in IP Convergence sublayer mode, this edge router is used as the destination
				for uplink traffic whose destination cannot otherwise be determined.
				The value of this object is configured per BS and per VLAN."
			DEFVAL { "" }
			::= { asDot1adVlanProvEntry 11 }

		
		-- 1.3.6.1.4.1.989.1.16.5.4.1.2.1.12
		asDot1adVlanProvRowStatus OBJECT-TYPE
			SYNTAX RowStatus
			MAX-ACCESS read-create
			STATUS current
			DESCRIPTION
				"This object indicates the status of this entry."
			::= { asDot1adVlanProvEntry 12 }

		
		-- 1.3.6.1.4.1.989.1.16.5.4.1.2.1.13
		asDot1adVlanProvArpSourceIpAddress OBJECT-TYPE
			SYNTAX InetAddress
			MAX-ACCESS read-create
			STATUS current
			DESCRIPTION
				"The IP address assigned to the BS in this traffic VLAN. 
				This address is used as the source address when the BS ARPs 
				or NDPs for addresses in this VLAN.
				The value of this object is configured per BS and per VLAN.
				The type of address is determined by asDot1adVlanProvIpAddressType."
			DEFVAL { "" }
			::= { asDot1adVlanProvEntry 13 }

		
		-- 1.3.6.1.4.1.989.1.16.5.4.1.2.1.14
		asDot1adVlanProvLocalIpAddress OBJECT-TYPE
			SYNTAX InetAddress
			MAX-ACCESS read-create
			STATUS current
			DESCRIPTION
				"The IP address of devices that are directly attached to the BS's network. 
				Used by the ethernet header re-creation facility, 
				addresses that pass this mask are sent directly to their destination, 
				using the ARP or NDP protocol to resolve the ethernet address. 
				All other packets are sent to the router.
				The value of this object is configured per BS and per VLAN.
				The type of address is determined by asDot1adVlanProvIpAddressType."
			DEFVAL { "" }
			::= { asDot1adVlanProvEntry 14 }

		
		-- 1.3.6.1.4.1.989.1.16.5.4.1.2.1.15
		asDot1adVlanProvLocalIpNetMask OBJECT-TYPE
			SYNTAX InetAddress
			MAX-ACCESS read-create
			STATUS current
			DESCRIPTION
				"The IP netmask of devices that are directly attached to the BS's network. 
				Used with the localIpAddress field.
				The value of this object is configured per BS and per VLAN.
				The type of address is determined by asDot1adVlanProvIpAddressType."
			DEFVAL { "" }
			::= { asDot1adVlanProvEntry 15 }

		
		-- 1.3.6.1.4.1.989.1.16.5.4.1.2.1.16
		asDot1adVlanProvBcastServiceClassIndex OBJECT-TYPE
			SYNTAX Integer32 (1..65535)
			MAX-ACCESS read-create
			STATUS current
			DESCRIPTION
				"Defines Service Class to use for Broadcast Service Flows of both tagged and untagged traffic."
			::= { asDot1adVlanProvEntry 16 }

		
		-- 1.3.6.1.4.1.989.1.16.5.4.1.1
		asDot1adBridgeTable OBJECT-TYPE
			SYNTAX SEQUENCE OF AsDot1adBridgeEntry
			MAX-ACCESS not-accessible
			STATUS current
			DESCRIPTION
				"A table containing configuration and status information global to the entire bridge 
				implementation on an 802.16e BS.
				A row in this table should be created by BS with the default values."
			::= { asDot1adBridgeObjects 1 }

		
		-- 1.3.6.1.4.1.989.1.16.5.4.1.1.1
		asDot1adBridgeEntry OBJECT-TYPE
			SYNTAX AsDot1adBridgeEntry
			MAX-ACCESS not-accessible
			STATUS current
			DESCRIPTION
				"Description."
			INDEX { asDot1adBridgeIndex }
			::= { asDot1adBridgeTable 1 }

		
		AsDot1adBridgeEntry ::=
			SEQUENCE { 
				asDot1adBridgeIndex
					Integer32,
				asDot1adBridgeMode
					INTEGER,
				asDot1adBridgeMgmtVlanId
					AsDot1adVlanIdOrNone,
				asDot1adBridgeNumRoutes
					Integer32,
				asDot1adBridgeRouteLife
					Integer32,
				asDot1adBridgeMgmtVlanUserPriority
					Integer32,
				asDot1adBridgeAsnGwVlanId
					AsDot1adVlanIdOrNone,
				asDot1adBridgeAsnGwVlanUserPriority
					Integer32,
				asDot1adBridgeSTagEtherType
					Integer32,
				asDot1adBridgeMgmtVlanIsTagged
					AsmaxBooleanSwitch,
				asDot1adBridgeSTagConfigMode
					INTEGER,
				asDot1adBridgeSTagPortVlan
					Integer32,
				asDot1adBridgeUseCTagPriority
					AsmaxBooleanSwitch,
				asDot1adBridgeSTagPriority
					Integer32
			 }

		-- 1.3.6.1.4.1.989.1.16.5.4.1.1.1.1
		asDot1adBridgeIndex OBJECT-TYPE
			SYNTAX Integer32 (1)
			MAX-ACCESS not-accessible
			STATUS current
			DESCRIPTION
				"Arbitrary index for single row table - must always be set to 1."
			::= { asDot1adBridgeEntry 1 }

		
		-- 1.3.6.1.4.1.989.1.16.5.4.1.1.1.2
		asDot1adBridgeMode OBJECT-TYPE
			SYNTAX INTEGER
				{
				bridgeModeVlan(1),
				bridgeModeProvidersVlan(3)
				}
			MAX-ACCESS read-write
			STATUS current
			DESCRIPTION
				"Defines the general mode of BS bridge.
				In VLAN mode bridge implements the 802.1q standard.
				In Providers mode, the bridge extends the 802.1q with the Service Vlan (S-Vlan) tagging 
				based on the 802.1ad standard. 
				
				"
			DEFVAL { bridgeModeVlan }
			::= { asDot1adBridgeEntry 2 }

		
		-- 1.3.6.1.4.1.989.1.16.5.4.1.1.1.3
		asDot1adBridgeMgmtVlanId OBJECT-TYPE
			SYNTAX AsDot1adVlanIdOrNone
			MAX-ACCESS read-write
			STATUS current
			DESCRIPTION
				"Defines VlanId used to tag the management traffic for the bridge 
				hosting 802.16 BS and management trafic routed to all managed SSs 
				using SMC connection. 
				"
			DEFVAL { 4094 }
			::= { asDot1adBridgeEntry 3 }

		
		-- 1.3.6.1.4.1.989.1.16.5.4.1.1.1.4
		asDot1adBridgeNumRoutes OBJECT-TYPE
			SYNTAX Integer32 (0..2147483647)
			MAX-ACCESS read-write
			STATUS current
			DESCRIPTION
				"Maximum number of routes that the bridge will support. "
			DEFVAL { 32000 }
			::= { asDot1adBridgeEntry 4 }

		
		-- 1.3.6.1.4.1.989.1.16.5.4.1.1.1.5
		asDot1adBridgeRouteLife OBJECT-TYPE
			SYNTAX Integer32 (10000..1000000000)
			UNITS "ms"
			MAX-ACCESS read-write
			STATUS current
			DESCRIPTION
				"Lifetime of a dynamic route in the VLAN bridge in ms. "
			DEFVAL { 300000 }
			::= { asDot1adBridgeEntry 5 }

		
		-- 1.3.6.1.4.1.989.1.16.5.4.1.1.1.6
		asDot1adBridgeMgmtVlanUserPriority OBJECT-TYPE
			SYNTAX Integer32 (0..7)
			MAX-ACCESS read-write
			STATUS current
			DESCRIPTION
				"The priority for the Vlan, as defined in IEEE 802.1q and 802.ad."
			DEFVAL { 7 }
			::= { asDot1adBridgeEntry 6 }

		
		-- 1.3.6.1.4.1.989.1.16.5.4.1.1.1.7
		asDot1adBridgeAsnGwVlanId OBJECT-TYPE
			SYNTAX AsDot1adVlanIdOrNone
			MAX-ACCESS read-write
			STATUS current
			DESCRIPTION
				"The id of the VLAN that the ASN-Gateways are located in."
			DEFVAL { 0 }
			::= { asDot1adBridgeEntry 7 }

		
		-- 1.3.6.1.4.1.989.1.16.5.4.1.1.1.8
		asDot1adBridgeAsnGwVlanUserPriority OBJECT-TYPE
			SYNTAX Integer32 (0..7)
			MAX-ACCESS read-write
			STATUS current
			DESCRIPTION
				"The priority for the Vlan, as defined in IEEE 802.1q and 802.ad."
			DEFVAL { 1 }
			::= { asDot1adBridgeEntry 8 }

		
		-- 1.3.6.1.4.1.989.1.16.5.4.1.1.1.9
		asDot1adBridgeSTagEtherType OBJECT-TYPE
			SYNTAX Integer32 (0..65535)
			MAX-ACCESS read-write
			STATUS current
			DESCRIPTION
				"The Ethertype of the frame with outer S-TAG for providers VLAN bridge mode.
				The typical values used are:
				0x88A8 (34984),
				0x9100 (37120),
				0x9200 (37376),
				0x9300 (37632)
				The object is not defined as an enumeration to allow future extensions.
				NMS should show it as an enumeration on GUI.
				"
			DEFVAL { 37120 }
			::= { asDot1adBridgeEntry 9 }

		
		-- 1.3.6.1.4.1.989.1.16.5.4.1.1.1.10
		asDot1adBridgeMgmtVlanIsTagged OBJECT-TYPE
			SYNTAX AsmaxBooleanSwitch
			MAX-ACCESS read-write
			STATUS current
			DESCRIPTION
				"Denotes whether the Management Vlan is tagged."
			::= { asDot1adBridgeEntry 10 }

		
		-- 1.3.6.1.4.1.989.1.16.5.4.1.1.1.11
		asDot1adBridgeSTagConfigMode OBJECT-TYPE
			SYNTAX INTEGER
				{
				useSSconfiguration(0),
				useBSConfigurationForAllSS(1)
				}
			MAX-ACCESS read-write
			STATUS current
			DESCRIPTION
				"sTag configuration Mode."
			DEFVAL { useSSconfiguration }
			::= { asDot1adBridgeEntry 11 }

		
		-- 1.3.6.1.4.1.989.1.16.5.4.1.1.1.12
		asDot1adBridgeSTagPortVlan OBJECT-TYPE
			SYNTAX Integer32 (0..4095)
			MAX-ACCESS read-write
			STATUS current
			DESCRIPTION
				"sTag Vlan."
			::= { asDot1adBridgeEntry 12 }

		
		-- 1.3.6.1.4.1.989.1.16.5.4.1.1.1.13
		asDot1adBridgeUseCTagPriority OBJECT-TYPE
			SYNTAX AsmaxBooleanSwitch
			MAX-ACCESS read-write
			STATUS current
			DESCRIPTION
				"Use C-Tag priority for S-tag."
			DEFVAL { booleanTrue }
			::= { asDot1adBridgeEntry 13 }

		
		-- 1.3.6.1.4.1.989.1.16.5.4.1.1.1.14
		asDot1adBridgeSTagPriority OBJECT-TYPE
			SYNTAX Integer32 (0..7)
			MAX-ACCESS read-write
			STATUS current
			DESCRIPTION
				"The sTag user priority."
			::= { asDot1adBridgeEntry 14 }

		
		-- 1.3.6.1.4.1.989.1.16.5.4.2
		asDot1adPortObjects OBJECT IDENTIFIER ::= { asMaxAdBridge 2 }

		
		-- 1.3.6.1.4.1.989.1.16.5.4.2.1
		asDot1adSsPortProvTable OBJECT-TYPE
			SYNTAX SEQUENCE OF AsDot1adSsPortProvEntry
			MAX-ACCESS not-accessible
			STATUS current
			DESCRIPTION
				"A table containing static per-port provisioning information for all the SS ports allowed 
				on this bridge. Note that the provisioning is per air interface and SS Mac Address.
				The table is read-create to allow NMS to provision ports' configuration before the first
				address is learned from the port.
				"
			::= { asDot1adPortObjects 1 }

		
		-- 1.3.6.1.4.1.989.1.16.5.4.2.1.1
		asDot1adSsPortProvEntry OBJECT-TYPE
			SYNTAX AsDot1adSsPortProvEntry
			MAX-ACCESS not-accessible
			STATUS current
			DESCRIPTION
				"One row per air-interface, SS port MAC address."
			INDEX { ifIndex, asDot1adSsPortProvAddress }
			::= { asDot1adSsPortProvTable 1 }

		
		AsDot1adSsPortProvEntry ::=
			SEQUENCE { 
				asDot1adSsPortProvAddress
					MacAddress,
				asDot1adSsPortProvAdMode
					AsDot1adPortMode,
				asDot1adSsPortProvIngressFilterEnabled
					AsmaxBooleanSwitch,
				asDot1adSsPortProvPvid
					AsDot1adVlanIdOrNone,
				asDot1adSsPortProvUserPriority
					Integer32,
				asDot1adSsPortProvAllowedFrameTypes
					AsDot1adAllowedFrameTypes,
				asDot1adSsPortProvRowStatus
					RowStatus,
				asDot1adSsPortProvQinqSupported
					AsmaxBooleanSwitch,
				asDot1adSsPortProvSTagVlan
					Integer32,
				asDot1adSsPortProvUseCTagPriority
					AsmaxBooleanSwitch,
				asDot1adSsPortProvsTagPriority
					Integer32
			 }

		-- 1.3.6.1.4.1.989.1.16.5.4.2.1.1.1
		asDot1adSsPortProvAddress OBJECT-TYPE
			SYNTAX MacAddress
			MAX-ACCESS not-accessible
			STATUS current
			DESCRIPTION
				"The MAC Address of the virtual SS air interface port."
			::= { asDot1adSsPortProvEntry 1 }

		
		-- 1.3.6.1.4.1.989.1.16.5.4.2.1.1.2
		asDot1adSsPortProvAdMode OBJECT-TYPE
			SYNTAX AsDot1adPortMode
			MAX-ACCESS read-create
			STATUS current
			DESCRIPTION
				"When the bridge is configured for 'provider' (802.1ad) mode, this parameter indicates 
				the mode the SS port will operate in, or is operating in."
			DEFVAL { portModePnp }
			::= { asDot1adSsPortProvEntry 2 }

		
		-- 1.3.6.1.4.1.989.1.16.5.4.2.1.1.3
		asDot1adSsPortProvIngressFilterEnabled OBJECT-TYPE
			SYNTAX AsmaxBooleanSwitch
			MAX-ACCESS read-create
			STATUS current
			DESCRIPTION
				"When this is booleanTrue, the device will discard incoming
				frames for VLANs that are not included in this Port's
				egress VLAN list as defined by asDot1adSsPortVlanListTable.
				When booleanFalse, the port will accept all incoming frames."
			REFERENCE
				"IEEE 802.1Q/D11 Section 12.10.1.4"
			DEFVAL { booleanFalse }
			::= { asDot1adSsPortProvEntry 3 }

		
		-- 1.3.6.1.4.1.989.1.16.5.4.2.1.1.4
		asDot1adSsPortProvPvid OBJECT-TYPE
			SYNTAX AsDot1adVlanIdOrNone
			MAX-ACCESS read-create
			STATUS current
			DESCRIPTION
				"The PVID, the VLAN-ID assigned to untagged frames or
				Priority-Tagged frames received on this port."
			REFERENCE
				"IEEE 802.1Q/D11 Section 12.10.1.1"
			DEFVAL { 0 }
			::= { asDot1adSsPortProvEntry 4 }

		
		-- 1.3.6.1.4.1.989.1.16.5.4.2.1.1.5
		asDot1adSsPortProvUserPriority OBJECT-TYPE
			SYNTAX Integer32 (0..7)
			MAX-ACCESS read-create
			STATUS current
			DESCRIPTION
				"The user priority of vlan-tagged traffic.
				"
			DEFVAL { 0 }
			::= { asDot1adSsPortProvEntry 5 }

		
		-- 1.3.6.1.4.1.989.1.16.5.4.2.1.1.6
		asDot1adSsPortProvAllowedFrameTypes OBJECT-TYPE
			SYNTAX AsDot1adAllowedFrameTypes
			MAX-ACCESS read-create
			STATUS current
			DESCRIPTION
				"The allowed frame types permitted on incoming traffic to this port.
				When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitOnlyVlanTagged }
			::= { asDot1adSsPortProvEntry 6 }

		
		-- 1.3.6.1.4.1.989.1.16.5.4.2.1.1.7
		asDot1adSsPortProvRowStatus OBJECT-TYPE
			SYNTAX RowStatus
			MAX-ACCESS read-create
			STATUS current
			DESCRIPTION
				"This object indicates the status of this entry."
			::= { asDot1adSsPortProvEntry 7 }

		
		-- 1.3.6.1.4.1.989.1.16.5.4.2.1.1.8
		asDot1adSsPortProvQinqSupported OBJECT-TYPE
			SYNTAX AsmaxBooleanSwitch
			MAX-ACCESS read-create
			STATUS current
			DESCRIPTION
				"QinQ supported for the SS."
			DEFVAL { booleanFalse }
			::= { asDot1adSsPortProvEntry 8 }

		
		-- 1.3.6.1.4.1.989.1.16.5.4.2.1.1.9
		asDot1adSsPortProvSTagVlan OBJECT-TYPE
			SYNTAX Integer32 (0..4095)
			MAX-ACCESS read-create
			STATUS current
			DESCRIPTION
				"sTag Vlan."
			::= { asDot1adSsPortProvEntry 9 }

		
		-- 1.3.6.1.4.1.989.1.16.5.4.2.1.1.10
		asDot1adSsPortProvUseCTagPriority OBJECT-TYPE
			SYNTAX AsmaxBooleanSwitch
			MAX-ACCESS read-create
			STATUS current
			DESCRIPTION
				"Use C-Tag priority for S-tag."
			DEFVAL { booleanTrue }
			::= { asDot1adSsPortProvEntry 10 }

		
		-- 1.3.6.1.4.1.989.1.16.5.4.2.1.1.11
		asDot1adSsPortProvsTagPriority OBJECT-TYPE
			SYNTAX Integer32 (0..7)
			MAX-ACCESS read-create
			STATUS current
			DESCRIPTION
				"The sTag user priority."
			::= { asDot1adSsPortProvEntry 11 }

		
		-- 1.3.6.1.4.1.989.1.16.5.4.2.2
		asDot1adSsPortVlanListTable OBJECT-TYPE
			SYNTAX SEQUENCE OF AsDot1adSsPortVlanListEntry
			MAX-ACCESS not-accessible
			STATUS current
			DESCRIPTION
				"SS port egress VLAN lists. It is defined as a map between VLANs 
				and ports with the tagging behaviour additionally defined.
				Note the provisioning is per air interface, SS Mac address and Vlan ID."
			::= { asDot1adPortObjects 2 }

		
		-- 1.3.6.1.4.1.989.1.16.5.4.2.2.1
		asDot1adSsPortVlanListEntry OBJECT-TYPE
			SYNTAX AsDot1adSsPortVlanListEntry
			MAX-ACCESS not-accessible
			STATUS current
			DESCRIPTION
				"Description."
			INDEX { ifIndex, asDot1adSsPortVlanListPortAddress, asDot1adSsPortVlanListVlanId }
			::= { asDot1adSsPortVlanListTable 1 }

		
		AsDot1adSsPortVlanListEntry ::=
			SEQUENCE { 
				asDot1adSsPortVlanListPortAddress
					MacAddress,
				asDot1adSsPortVlanListVlanId
					AsDot1adVlanId,
				asDot1adSsPortVlanListUntagged
					AsmaxBooleanSwitch,
				asDot1adSsPortVlanListRowStatus
					RowStatus
			 }

		-- 1.3.6.1.4.1.989.1.16.5.4.2.2.1.1
		asDot1adSsPortVlanListPortAddress OBJECT-TYPE
			SYNTAX MacAddress
			MAX-ACCESS not-accessible
			STATUS current
			DESCRIPTION
				"Mac address of the port this table defines VLAN list for egress
				forwarding and ingress filtering."
			::= { asDot1adSsPortVlanListEntry 1 }

		
		-- 1.3.6.1.4.1.989.1.16.5.4.2.2.1.2
		asDot1adSsPortVlanListVlanId OBJECT-TYPE
			SYNTAX AsDot1adVlanId
			MAX-ACCESS not-accessible
			STATUS current
			DESCRIPTION
				"ID of the VLAN member of the port vlan list."
			::= { asDot1adSsPortVlanListEntry 2 }

		
		-- 1.3.6.1.4.1.989.1.16.5.4.2.2.1.3
		asDot1adSsPortVlanListUntagged OBJECT-TYPE
			SYNTAX AsmaxBooleanSwitch
			MAX-ACCESS read-create
			STATUS current
			DESCRIPTION
				"Determines whether frames are untagged for the given VLAN on a given port on egress."
			DEFVAL { booleanFalse }
			::= { asDot1adSsPortVlanListEntry 3 }

		
		-- 1.3.6.1.4.1.989.1.16.5.4.2.2.1.4
		asDot1adSsPortVlanListRowStatus OBJECT-TYPE
			SYNTAX RowStatus
			MAX-ACCESS read-create
			STATUS current
			DESCRIPTION
				"This object indicates the status of this entry."
			::= { asDot1adSsPortVlanListEntry 4 }

		
		-- 1.3.6.1.4.1.989.1.16.5.4.2.3
		asDot1adBsPortProvTable OBJECT-TYPE
			SYNTAX SEQUENCE OF AsDot1adBsPortProvEntry
			MAX-ACCESS not-accessible
			STATUS current
			DESCRIPTION
				"A table containing static per-port provisioning information 
				for all the BS ports on this bridge.
				The table is read-write to allow the BS to initialise the row(s) for its port(s).
				The NMS will provision the port properties by updating existing rows.
				"
			::= { asDot1adPortObjects 3 }

		
		-- 1.3.6.1.4.1.989.1.16.5.4.2.3.1
		asDot1adBsPortProvEntry OBJECT-TYPE
			SYNTAX AsDot1adBsPortProvEntry
			MAX-ACCESS not-accessible
			STATUS current
			DESCRIPTION
				"One row per ethernet interface on the BS."
			INDEX { ifIndex }
			::= { asDot1adBsPortProvTable 1 }

		
		AsDot1adBsPortProvEntry ::=
			SEQUENCE { 
				asDot1adBsPortProvAdMode
					AsDot1adPortMode,
				asDot1adBsPortProvIngressFilterEnabled
					AsmaxBooleanSwitch,
				asDot1adBsPortProvPvid
					AsDot1adVlanIdOrNone,
				asDot1adBsPortProvUserPriority
					Integer32,
				asDot1adBsPortProvAllowedFrameTypes
					AsDot1adAllowedFrameTypes
			 }

		-- 1.3.6.1.4.1.989.1.16.5.4.2.3.1.1
		asDot1adBsPortProvAdMode OBJECT-TYPE
			SYNTAX AsDot1adPortMode
			MAX-ACCESS read-write
			STATUS current
			DESCRIPTION
				"When the bridge is configured for 'provider' (802.1ad) mode, this parameter indicates 
				the mode the BS port will operate in, or is operating in."
			DEFVAL { portModePnp }
			::= { asDot1adBsPortProvEntry 1 }

		
		-- 1.3.6.1.4.1.989.1.16.5.4.2.3.1.2
		asDot1adBsPortProvIngressFilterEnabled OBJECT-TYPE
			SYNTAX AsmaxBooleanSwitch
			MAX-ACCESS read-write
			STATUS current
			DESCRIPTION
				"When this is booleanTrue, the device will discard incoming
				frames for VLANs that are not included in this Port's
				egress VLAN list as defined by asDot1adBsPortVlanListTable.
				When booleanFalse, the port will accept all incoming frames."
			REFERENCE
				"IEEE 802.1Q/D11 Section 12.10.1.4"
			DEFVAL { booleanFalse }
			::= { asDot1adBsPortProvEntry 2 }

		
		-- 1.3.6.1.4.1.989.1.16.5.4.2.3.1.3
		asDot1adBsPortProvPvid OBJECT-TYPE
			SYNTAX AsDot1adVlanIdOrNone
			MAX-ACCESS read-write
			STATUS current
			DESCRIPTION
				"The PVID, the VLAN-ID assigned to untagged frames or
				Priority-Tagged frames received on this port."
			REFERENCE
				"IEEE 802.1Q/D11 Section 12.10.1.1"
			DEFVAL { 0 }
			::= { asDot1adBsPortProvEntry 3 }

		
		-- 1.3.6.1.4.1.989.1.16.5.4.2.3.1.4
		asDot1adBsPortProvUserPriority OBJECT-TYPE
			SYNTAX Integer32 (0..7)
			MAX-ACCESS read-write
			STATUS current
			DESCRIPTION
				"The user priority of vlan-tagged traffic.
				"
			DEFVAL { 0 }
			::= { asDot1adBsPortProvEntry 4 }

		
		-- 1.3.6.1.4.1.989.1.16.5.4.2.3.1.5
		asDot1adBsPortProvAllowedFrameTypes OBJECT-TYPE
			SYNTAX AsDot1adAllowedFrameTypes
			MAX-ACCESS read-write
			STATUS current
			DESCRIPTION
				"The allowed frame types permitted on incoming traffic to this port.
				When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitOnlyVlanTagged }
			::= { asDot1adBsPortProvEntry 5 }

		
		-- 1.3.6.1.4.1.989.1.16.5.4.2.4
		asDot1adBsPortVlanListTable OBJECT-TYPE
			SYNTAX SEQUENCE OF AsDot1adBsPortVlanListEntry
			MAX-ACCESS not-accessible
			STATUS current
			DESCRIPTION
				"BS port egress VLAN lists. It is defined as a map between VLANs 
				and ports with the tagging behaviour additionally defined."
			::= { asDot1adPortObjects 4 }

		
		-- 1.3.6.1.4.1.989.1.16.5.4.2.4.1
		asDot1adBsPortVlanListEntry OBJECT-TYPE
			SYNTAX AsDot1adBsPortVlanListEntry
			MAX-ACCESS not-accessible
			STATUS current
			DESCRIPTION
				"Description."
			INDEX { ifIndex, asDot1adBsPortVlanListVlanId }
			::= { asDot1adBsPortVlanListTable 1 }

		
		AsDot1adBsPortVlanListEntry ::=
			SEQUENCE { 
				asDot1adBsPortVlanListVlanId
					AsDot1adVlanId,
				asDot1adBsPortVlanListUntagged
					AsmaxBooleanSwitch,
				asDot1adBsPortVlanListRowStatus
					RowStatus
			 }

		-- 1.3.6.1.4.1.989.1.16.5.4.2.4.1.1
		asDot1adBsPortVlanListVlanId OBJECT-TYPE
			SYNTAX AsDot1adVlanId
			MAX-ACCESS not-accessible
			STATUS current
			DESCRIPTION
				"ID of the VLAN member of the port vlan list."
			::= { asDot1adBsPortVlanListEntry 1 }

		
		-- 1.3.6.1.4.1.989.1.16.5.4.2.4.1.2
		asDot1adBsPortVlanListUntagged OBJECT-TYPE
			SYNTAX AsmaxBooleanSwitch
			MAX-ACCESS read-create
			STATUS current
			DESCRIPTION
				"Determines whether frames are untagged for the given VLAN on a given port on egress."
			DEFVAL { booleanFalse }
			::= { asDot1adBsPortVlanListEntry 2 }

		
		-- 1.3.6.1.4.1.989.1.16.5.4.2.4.1.3
		asDot1adBsPortVlanListRowStatus OBJECT-TYPE
			SYNTAX RowStatus
			MAX-ACCESS read-create
			STATUS current
			DESCRIPTION
				"This object indicates the status of this entry."
			::= { asDot1adBsPortVlanListEntry 3 }

		
		-- 1.3.6.1.4.1.989.1.16.5.4.2.5
		asDot1adIntPepPortProvTable OBJECT-TYPE
			SYNTAX SEQUENCE OF AsDot1adIntPepPortProvEntry
			MAX-ACCESS not-accessible
			STATUS current
			DESCRIPTION
				"This table, together with asDot1adIntCvidRegistrationTable, contains the per-port 
				provisioning information for the internal ports used when the bridge is operating in 
				Provider-mode (i.e. supports 802.1ad) and the SS port is configured to operate as a CEP
				port.
				This table concentrates principally on the operations applied to traffic entering the
				C-Vlan entity from the S-Vlan entity in the provider bridge.
				The table is read-create to allow NMS to provision port configuration before the 
				address is learnt.
				"
			::= { asDot1adPortObjects 5 }

		
		-- 1.3.6.1.4.1.989.1.16.5.4.2.5.1
		asDot1adIntPepPortProvEntry OBJECT-TYPE
			SYNTAX AsDot1adIntPepPortProvEntry
			MAX-ACCESS not-accessible
			STATUS current
			DESCRIPTION
				"One row per air-interface, SS port MAC address, and S-VID."
			INDEX { ifIndex, asDot1adIntPepPortProvAddress, asDot1adIntPepPortProvSvid }
			::= { asDot1adIntPepPortProvTable 1 }

		
		AsDot1adIntPepPortProvEntry ::=
			SEQUENCE { 
				asDot1adIntPepPortProvAddress
					MacAddress,
				asDot1adIntPepPortProvSvid
					AsDot1adVlanId,
				asDot1adIntPepPortProvPvid
					AsDot1adVlanIdOrNone,
				asDot1adIntPepPortProvUserPriority
					Integer32,
				asDot1adIntPepPortProvAllowedFrameTypes
					AsDot1adAllowedFrameTypes,
				asDot1adIntPepPortProvRowStatus
					RowStatus
			 }

		-- 1.3.6.1.4.1.989.1.16.5.4.2.5.1.1
		asDot1adIntPepPortProvAddress OBJECT-TYPE
			SYNTAX MacAddress
			MAX-ACCESS not-accessible
			STATUS current
			DESCRIPTION
				"MAC Address identifying the port. The port here is the virtual SS air interface port."
			::= { asDot1adIntPepPortProvEntry 1 }

		
		-- 1.3.6.1.4.1.989.1.16.5.4.2.5.1.2
		asDot1adIntPepPortProvSvid OBJECT-TYPE
			SYNTAX AsDot1adVlanId
			MAX-ACCESS not-accessible
			STATUS current
			DESCRIPTION
				"The S-VID, the service Vlan, for which the behaviour on entry to the C-Vlan entity 
				of the provider bridge is being defined.
				"
			::= { asDot1adIntPepPortProvEntry 2 }

		
		-- 1.3.6.1.4.1.989.1.16.5.4.2.5.1.3
		asDot1adIntPepPortProvPvid OBJECT-TYPE
			SYNTAX AsDot1adVlanIdOrNone
			MAX-ACCESS read-create
			STATUS current
			DESCRIPTION
				"The C-VLAN tag to insert into traffic without a C-VLAN as it is passed into the 
				C-Vlan entity."
			REFERENCE
				"IEEE 802.1Q/D11 Section 12.10.1.1"
			DEFVAL { 0 }
			::= { asDot1adIntPepPortProvEntry 3 }

		
		-- 1.3.6.1.4.1.989.1.16.5.4.2.5.1.4
		asDot1adIntPepPortProvUserPriority OBJECT-TYPE
			SYNTAX Integer32 (0..7)
			MAX-ACCESS read-create
			STATUS current
			DESCRIPTION
				"The user priority to insert with the C-VLAN tag."
			DEFVAL { 0 }
			::= { asDot1adIntPepPortProvEntry 4 }

		
		-- 1.3.6.1.4.1.989.1.16.5.4.2.5.1.5
		asDot1adIntPepPortProvAllowedFrameTypes OBJECT-TYPE
			SYNTAX AsDot1adAllowedFrameTypes
			MAX-ACCESS read-create
			STATUS current
			DESCRIPTION
				"The allowed frame types permitted to enter the C-VLAN entity from the S-VLAN entity.
				When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitOnlyVlanTagged }
			::= { asDot1adIntPepPortProvEntry 5 }

		
		-- 1.3.6.1.4.1.989.1.16.5.4.2.5.1.6
		asDot1adIntPepPortProvRowStatus OBJECT-TYPE
			SYNTAX RowStatus
			MAX-ACCESS read-create
			STATUS current
			DESCRIPTION
				"This object indicates the status of this entry."
			::= { asDot1adIntPepPortProvEntry 6 }

		
		-- 1.3.6.1.4.1.989.1.16.5.4.2.6
		asDot1adIntCvidRegistrationProvTable OBJECT-TYPE
			SYNTAX SEQUENCE OF AsDot1adIntCvidRegistrationProvEntry
			MAX-ACCESS not-accessible
			STATUS current
			DESCRIPTION
				"This table, together with asDot1adIntPepPortTable, contains the per-port provisioning
				information for the internal ports used when the bridge is operating in Provider-mode 
				(i.e. supports 802.1ad) and the SS port is configured to operate as a CEP port.
				This table concentrates principally on the operations applied to traffic entering the
				S-Vlan entity from the C-Vlan entity.
				The table is read-create to allow NMS to provision port configuration before the 
				address is learnt.
				"
			::= { asDot1adPortObjects 6 }

		
		-- 1.3.6.1.4.1.989.1.16.5.4.2.6.1
		asDot1adIntCvidRegistrationProvEntry OBJECT-TYPE
			SYNTAX AsDot1adIntCvidRegistrationProvEntry
			MAX-ACCESS not-accessible
			STATUS current
			DESCRIPTION
				"One row per air-interface, SS port MAC address, C-VID."
			INDEX { ifIndex, asDot1adIntCvidRegistrationProvAddress, asDot1adIntCvidRegistrationProvCvid }
			::= { asDot1adIntCvidRegistrationProvTable 1 }

		
		AsDot1adIntCvidRegistrationProvEntry ::=
			SEQUENCE { 
				asDot1adIntCvidRegistrationProvAddress
					MacAddress,
				asDot1adIntCvidRegistrationProvCvid
					AsDot1adVlanId,
				asDot1adIntCvidRegistrationProvSvid
					AsDot1adVlanIdOrNone,
				asDot1adIntCvidRegistrationProvUserPriority
					Integer32,
				asDot1adIntCvidRegistrationProvPepUntagged
					AsmaxBooleanSwitch,
				asDot1adIntCvidRegistrationProvCepUntagged
					AsmaxBooleanSwitch,
				asDot1adIntCvidRegistrationProvRowStatus
					RowStatus
			 }

		-- 1.3.6.1.4.1.989.1.16.5.4.2.6.1.1
		asDot1adIntCvidRegistrationProvAddress OBJECT-TYPE
			SYNTAX MacAddress
			MAX-ACCESS not-accessible
			STATUS current
			DESCRIPTION
				"MAC Address identifying the port. The port here is the virtual SS air interface port."
			::= { asDot1adIntCvidRegistrationProvEntry 1 }

		
		-- 1.3.6.1.4.1.989.1.16.5.4.2.6.1.2
		asDot1adIntCvidRegistrationProvCvid OBJECT-TYPE
			SYNTAX AsDot1adVlanId
			MAX-ACCESS not-accessible
			STATUS current
			DESCRIPTION
				"The C-VID, the customer Vlan, for which the Service Vlan (S-Vlan) tag to insert is 
				being defined.
				"
			REFERENCE
				"IEEE 802.1Q/D11 Section 12.10.1.1"
			::= { asDot1adIntCvidRegistrationProvEntry 2 }

		
		-- 1.3.6.1.4.1.989.1.16.5.4.2.6.1.3
		asDot1adIntCvidRegistrationProvSvid OBJECT-TYPE
			SYNTAX AsDot1adVlanIdOrNone
			MAX-ACCESS read-create
			STATUS current
			DESCRIPTION
				"The S-VID to use in the S-Vlan tag inserted on frames as they enter the S-Vlan entity of
				the  provider bridge from the C-Vlan entity.
				"
			REFERENCE
				"IEEE 802.1Q/D11 Section 12.10.1.1"
			DEFVAL { 0 }
			::= { asDot1adIntCvidRegistrationProvEntry 3 }

		
		-- 1.3.6.1.4.1.989.1.16.5.4.2.6.1.4
		asDot1adIntCvidRegistrationProvUserPriority OBJECT-TYPE
			SYNTAX Integer32 (0..7)
			MAX-ACCESS read-create
			STATUS current
			DESCRIPTION
				"The user priority to insert into the S-Vlan tag.
				"
			::= { asDot1adIntCvidRegistrationProvEntry 4 }

		
		-- 1.3.6.1.4.1.989.1.16.5.4.2.6.1.5
		asDot1adIntCvidRegistrationProvPepUntagged OBJECT-TYPE
			SYNTAX AsmaxBooleanSwitch
			MAX-ACCESS read-create
			STATUS current
			DESCRIPTION
				"Determines whether frames are untagged for the given VLAN on a given port on egress.
				The port referred to here is the internal PEP port that is required when the bridge 
				operates in provider-mode and the SS port is configured for CEP mode.
				The Vlan tag that may be defined as untagged here is the C-Vlan tag."
			DEFVAL { booleanFalse }
			::= { asDot1adIntCvidRegistrationProvEntry 5 }

		
		-- 1.3.6.1.4.1.989.1.16.5.4.2.6.1.6
		asDot1adIntCvidRegistrationProvCepUntagged OBJECT-TYPE
			SYNTAX AsmaxBooleanSwitch
			MAX-ACCESS read-create
			STATUS current
			DESCRIPTION
				"Determines whether frames are untagged for the given VLAN on a given port on egress.
				The port referred to here is the external SS port when the bridge 
				operates in provider-mode and the SS port is configured for CEP mode.
				The Vlan tag that may be defined as untagged here is the C-Vlan tag."
			DEFVAL { booleanFalse }
			::= { asDot1adIntCvidRegistrationProvEntry 6 }

		
		-- 1.3.6.1.4.1.989.1.16.5.4.2.6.1.7
		asDot1adIntCvidRegistrationProvRowStatus OBJECT-TYPE
			SYNTAX RowStatus
			MAX-ACCESS read-create
			STATUS current
			DESCRIPTION
				"This object indicates the status of this entry."
			::= { asDot1adIntCvidRegistrationProvEntry 7 }

		
		-- 1.3.6.1.4.1.989.1.16.5.4.3
		asDot1adPortClassObjects OBJECT IDENTIFIER ::= { asMaxAdBridge 3 }

		
		-- 1.3.6.1.4.1.989.1.16.5.4.3.1
		asDot1adSsPortProvClassTable OBJECT-TYPE
			SYNTAX SEQUENCE OF AsDot1adSsPortProvClassEntry
			MAX-ACCESS not-accessible
			STATUS current
			DESCRIPTION
				"A table containing the default port provisioning information for all the SS ports allowed 
				on this bridge. 
				
				"
			::= { asDot1adPortClassObjects 1 }

		
		-- 1.3.6.1.4.1.989.1.16.5.4.3.1.1
		asDot1adSsPortProvClassEntry OBJECT-TYPE
			SYNTAX AsDot1adSsPortProvClassEntry
			MAX-ACCESS not-accessible
			STATUS current
			DESCRIPTION
				"One row per air-interface, SS port Class."
			INDEX { ifIndex, asDot1adSsPortProvClassName }
			::= { asDot1adSsPortProvClassTable 1 }

		
		AsDot1adSsPortProvClassEntry ::=
			SEQUENCE { 
				asDot1adSsPortProvClassName
					AsDot1adClassName,
				asDot1adSsPortProvClassAdMode
					AsDot1adPortMode,
				asDot1adSsPortProvClassIngressFilterEnabled
					AsmaxBooleanSwitch,
				asDot1adSsPortProvClassPvid
					AsDot1adVlanIdOrNone,
				asDot1adSsPortProvClassUserPriority
					Integer32,
				asDot1adSsPortProvClassAllowedFrameTypes
					AsDot1adAllowedFrameTypes,
				asDot1adSsPortProvClassRowStatus
					RowStatus,
				asDot1adSsPortProvClassQinqSupported
					AsmaxBooleanSwitch,
				asDot1adSsPortProvClassSTagVlan
					Integer32,
				asDot1adSsPortProvClassUseCTagPriority
					AsmaxBooleanSwitch,
				asDot1adSsPortProvClassSTagPriority
					Integer32
			 }

		-- 1.3.6.1.4.1.989.1.16.5.4.3.1.1.1
		asDot1adSsPortProvClassName OBJECT-TYPE
			SYNTAX AsDot1adClassName
			MAX-ACCESS not-accessible
			STATUS current
			DESCRIPTION
				"The name of the SS Port Class"
			::= { asDot1adSsPortProvClassEntry 1 }

		
		-- 1.3.6.1.4.1.989.1.16.5.4.3.1.1.2
		asDot1adSsPortProvClassAdMode OBJECT-TYPE
			SYNTAX AsDot1adPortMode
			MAX-ACCESS read-create
			STATUS current
			DESCRIPTION
				"When the bridge is configured for 'provider' (802.1ad) mode, this parameter indicates 
				the mode the SS port will operate in, or is operating in."
			DEFVAL { portModeCnp }
			::= { asDot1adSsPortProvClassEntry 2 }

		
		-- 1.3.6.1.4.1.989.1.16.5.4.3.1.1.3
		asDot1adSsPortProvClassIngressFilterEnabled OBJECT-TYPE
			SYNTAX AsmaxBooleanSwitch
			MAX-ACCESS read-create
			STATUS current
			DESCRIPTION
				"When this is booleanTrue, the device will discard incoming
				frames for VLANs that are not included in this Port's
				egress VLAN list as defined by asDot1adSsPortClassVlanListTable.
				When booleanFalse, the port will accept all incoming frames."
			REFERENCE
				"IEEE 802.1Q/D11 Section 12.10.1.4"
			DEFVAL { booleanFalse }
			::= { asDot1adSsPortProvClassEntry 3 }

		
		-- 1.3.6.1.4.1.989.1.16.5.4.3.1.1.4
		asDot1adSsPortProvClassPvid OBJECT-TYPE
			SYNTAX AsDot1adVlanIdOrNone
			MAX-ACCESS read-create
			STATUS current
			DESCRIPTION
				"The PVID, the VLAN-ID assigned to untagged frames or
				Priority-Tagged frames received on this port."
			REFERENCE
				"IEEE 802.1Q/D11 Section 12.10.1.1"
			DEFVAL { 0 }
			::= { asDot1adSsPortProvClassEntry 4 }

		
		-- 1.3.6.1.4.1.989.1.16.5.4.3.1.1.5
		asDot1adSsPortProvClassUserPriority OBJECT-TYPE
			SYNTAX Integer32 (0..7)
			MAX-ACCESS read-create
			STATUS current
			DESCRIPTION
				"The user priority of vlan-tagged traffic.
				"
			DEFVAL { 0 }
			::= { asDot1adSsPortProvClassEntry 5 }

		
		-- 1.3.6.1.4.1.989.1.16.5.4.3.1.1.6
		asDot1adSsPortProvClassAllowedFrameTypes OBJECT-TYPE
			SYNTAX AsDot1adAllowedFrameTypes
			MAX-ACCESS read-create
			STATUS current
			DESCRIPTION
				"The allowed frame types permitted on incoming traffic to this port.
				When this is admitOnlyVlanTagged, the device will discard 
				untagged frames or Priority-Tagged frames received on this port.
				When admitAll(1), untagged frames or Priority-Tagged frames 
				received on this port will be accepted and assigned to 
				a VID based on the PVID of for this port.
				When admitOnlyUntagged(3), is set the device will discard 
				all VLAN tagged frames."
			REFERENCE
				"IEEE 802.1Q/D11 Section 12.10.1.3"
			DEFVAL { admitOnlyVlanTagged }
			::= { asDot1adSsPortProvClassEntry 6 }

		
		-- 1.3.6.1.4.1.989.1.16.5.4.3.1.1.7
		asDot1adSsPortProvClassRowStatus OBJECT-TYPE
			SYNTAX RowStatus
			MAX-ACCESS read-create
			STATUS current
			DESCRIPTION
				"This object indicates the status of this entry."
			::= { asDot1adSsPortProvClassEntry 7 }

		
		-- 1.3.6.1.4.1.989.1.16.5.4.3.1.1.8
		asDot1adSsPortProvClassQinqSupported OBJECT-TYPE
			SYNTAX AsmaxBooleanSwitch
			MAX-ACCESS read-create
			STATUS current
			DESCRIPTION
				"QinQ supported for the SS."
			DEFVAL { booleanFalse }
			::= { asDot1adSsPortProvClassEntry 8 }

		
		-- 1.3.6.1.4.1.989.1.16.5.4.3.1.1.9
		asDot1adSsPortProvClassSTagVlan OBJECT-TYPE
			SYNTAX Integer32 (0..4095)
			MAX-ACCESS read-create
			STATUS current
			DESCRIPTION
				"sTagVlan."
			::= { asDot1adSsPortProvClassEntry 9 }

		
		-- 1.3.6.1.4.1.989.1.16.5.4.3.1.1.10
		asDot1adSsPortProvClassUseCTagPriority OBJECT-TYPE
			SYNTAX AsmaxBooleanSwitch
			MAX-ACCESS read-create
			STATUS current
			DESCRIPTION
				"Use C-Tag priority for S-tag
				."
			DEFVAL { booleanTrue }
			::= { asDot1adSsPortProvClassEntry 10 }

		
		-- 1.3.6.1.4.1.989.1.16.5.4.3.1.1.11
		asDot1adSsPortProvClassSTagPriority OBJECT-TYPE
			SYNTAX Integer32 (0..7)
			MAX-ACCESS read-create
			STATUS current
			DESCRIPTION
				"The sTag user priority."
			::= { asDot1adSsPortProvClassEntry 11 }

		
		-- 1.3.6.1.4.1.989.1.16.5.4.3.2
		asDot1adSsPortClassVlanListTable OBJECT-TYPE
			SYNTAX SEQUENCE OF AsDot1adSsPortClassVlanListEntry
			MAX-ACCESS not-accessible
			STATUS current
			DESCRIPTION
				"SS port class egress VLAN lists. It is defined as a map between VLANs 
				and the port class with the tagging behaviour additionally defined.
				Note the provisioning is per air interface, SS Port class and Vlan ID."
			::= { asDot1adPortClassObjects 2 }

		
		-- 1.3.6.1.4.1.989.1.16.5.4.3.2.1
		asDot1adSsPortClassVlanListEntry OBJECT-TYPE
			SYNTAX AsDot1adSsPortClassVlanListEntry
			MAX-ACCESS not-accessible
			STATUS current
			DESCRIPTION
				"One row per air-interface, SS port Class and Vlan ID."
			INDEX { ifIndex, asDot1adSsPortProvClassName, asDot1adSsPortClassVlanListVlanId }
			::= { asDot1adSsPortClassVlanListTable 1 }

		
		AsDot1adSsPortClassVlanListEntry ::=
			SEQUENCE { 
				asDot1adSsPortClassVlanListVlanId
					AsDot1adVlanId,
				asDot1adSsPortClassVlanListUntagged
					AsmaxBooleanSwitch,
				asDot1adSsPortClassVlanListRowStatus
					RowStatus
			 }

		-- 1.3.6.1.4.1.989.1.16.5.4.3.2.1.1
		asDot1adSsPortClassVlanListVlanId OBJECT-TYPE
			SYNTAX AsDot1adVlanId
			MAX-ACCESS not-accessible
			STATUS current
			DESCRIPTION
				"ID of the VLAN member of the port vlan list."
			::= { asDot1adSsPortClassVlanListEntry 1 }

		
		-- 1.3.6.1.4.1.989.1.16.5.4.3.2.1.2
		asDot1adSsPortClassVlanListUntagged OBJECT-TYPE
			SYNTAX AsmaxBooleanSwitch
			MAX-ACCESS read-create
			STATUS current
			DESCRIPTION
				"Determines whether frames are untagged for the given VLAN on a given port on egress."
			DEFVAL { booleanFalse }
			::= { asDot1adSsPortClassVlanListEntry 2 }

		
		-- 1.3.6.1.4.1.989.1.16.5.4.3.2.1.3
		asDot1adSsPortClassVlanListRowStatus OBJECT-TYPE
			SYNTAX RowStatus
			MAX-ACCESS read-create
			STATUS current
			DESCRIPTION
				"This object indicates the status of this entry."
			::= { asDot1adSsPortClassVlanListEntry 3 }

		
		-- 1.3.6.1.4.1.989.1.16.5.4.4
		asDot1adBridgeConformance OBJECT IDENTIFIER ::= { asMaxAdBridge 4 }

		
		-- 1.3.6.1.4.1.989.1.16.5.4.4.1
		asDot1adBridgeConfigGroup OBJECT-GROUP
			OBJECTS { asDot1adBridgeMode, asDot1adBridgeMgmtVlanId, asDot1adVlanProvFwdingDbid, asDot1adVlanProvSsToSsEnabled, asDot1adVlanProvFloodUnknownEnabled, 
				asDot1adVlanProvBroadcastMode, asDot1adVlanProvUntaggedMcastSfid, asDot1adVlanProvTaggedMcastSfid, asDot1adVlanProvDhcpRelayAgentActive, asDot1adVlanProvMacForceForwardingEnabled, 
				asDot1adVlanProvRowStatus, asDot1adSsPortProvAdMode, asDot1adSsPortProvIngressFilterEnabled, asDot1adSsPortProvPvid, asDot1adSsPortProvUserPriority, 
				asDot1adSsPortProvAllowedFrameTypes, asDot1adSsPortProvRowStatus, asDot1adSsPortVlanListUntagged, asDot1adSsPortVlanListRowStatus, asDot1adBsPortProvAdMode, 
				asDot1adBsPortProvIngressFilterEnabled, asDot1adBsPortProvPvid, asDot1adBsPortProvUserPriority, asDot1adBsPortProvAllowedFrameTypes, asDot1adBsPortVlanListUntagged, 
				asDot1adBsPortVlanListRowStatus, asDot1adIntPepPortProvPvid, asDot1adIntPepPortProvUserPriority, asDot1adIntPepPortProvAllowedFrameTypes, asDot1adIntPepPortProvRowStatus, 
				asDot1adIntCvidRegistrationProvSvid, asDot1adIntCvidRegistrationProvUserPriority, asDot1adIntCvidRegistrationProvPepUntagged, asDot1adIntCvidRegistrationProvCepUntagged, asDot1adSsPortProvClassUserPriority, 
				asDot1adSsPortProvClassAdMode, asDot1adSsPortProvClassPvid, asDot1adSsPortProvClassIngressFilterEnabled, asDot1adSsPortClassVlanListRowStatus, asDot1adSsPortClassVlanListUntagged, 
				asDot1adIntCvidRegistrationProvRowStatus, asDot1adBridgeNumRoutes, asDot1adSsPortProvClassRowStatus, asDot1adBridgeSTagEtherType, asDot1adBridgeAsnGwVlanUserPriority, 
				asDot1adBridgeAsnGwVlanId, asDot1adBridgeMgmtVlanUserPriority, asDot1adSsPortProvClassAllowedFrameTypes, asDot1adBridgeRouteLife, asDot1adVlanProvBcastServiceClassIndex, 
				asDot1adBridgeSTagConfigMode, asDot1adBridgeSTagPortVlan, asDot1adBridgeUseCTagPriority, asDot1adBridgeSTagPriority, asDot1adSsPortProvQinqSupported, 
				asDot1adSsPortProvSTagVlan, asDot1adSsPortProvUseCTagPriority, asDot1adSsPortProvsTagPriority, asDot1adSsPortProvClassQinqSupported, asDot1adSsPortProvClassSTagVlan, 
				asDot1adSsPortProvClassUseCTagPriority, asDot1adSsPortProvClassSTagPriority, asDot1adVlanProvEdgeRouterIpAddress, asDot1adVlanProvIpAddressType, asDot1adVlanProvArpSourceIpAddress, 
				asDot1adVlanProvLocalIpAddress, asDot1adVlanProvLocalIpNetMask, asDot1adBridgeMgmtVlanIsTagged }
			STATUS current
			DESCRIPTION 
				"A collection of objects providing device-level control
				and status information for the Virtual LAN bridge
				services."
			::= { asDot1adBridgeConformance 1 }

		
		-- 1.3.6.1.4.1.989.1.16.5.4.4.2
		asDot1adBridgeCompliance MODULE-COMPLIANCE
			STATUS current
			DESCRIPTION 
				"Description."
			MODULE -- this module
				MANDATORY-GROUPS { asDot1adBridgeConfigGroup }
			::= { asDot1adBridgeConformance 2 }

		
	
	END

--
-- ASMAX-AD-BRIDGE-MIB.mib
--
