--
-- AIRSPAN-ASMAX-BS-COMMON-MIB.mib
-- MIB generated by MG-SOFT Visual MIB Builder 2010 Version 8.0  Build 400
-- Friday, December 03, 2010 at 10:24:20
--

	AIRSPAN-ASMAX-BS-COMMON-MIB DEFINITIONS ::= BEGIN
 
		IMPORTS
			AsmaxBooleanSwitch			
				FROM AIRSPAN-ASMAX-COMMON-MIB			
			asMaxBS			
				FROM AIRSPAN-PRODUCTS-MIB			
			ifIndex			
				FROM IF-MIB			
			InetAddressType, InetAddress			
				FROM INET-ADDRESS-MIB			
			OBJECT-GROUP, NOTIFICATION-GROUP			
				FROM SNMPv2-CONF			
			Integer32, OBJECT-TYPE, MODULE-IDENTITY, NOTIFICATION-TYPE			
				FROM SNMPv2-SMI			
			DisplayString, TEXTUAL-CONVENTION			
				FROM SNMPv2-TC;
	
	
		-- 1.3.6.1.4.1.989.1.16.2.1
		asMaxBSCommon MODULE-IDENTITY 
			LAST-UPDATED "200804271742Z"		-- April 27, 2008 at 17:42 GMT
			ORGANIZATION 
				"Airspan"
			CONTACT-INFO 
				"kdudzins@airspan.com"
			DESCRIPTION 
				"MIB module with definition of objects to be used by more than one BS type."
			REVISION "200710171029Z"		-- October 17, 2007 at 10:29 GMT
			DESCRIPTION 
				"Draft 15
				- added bandwidth3MHz to AsmaxBandwidthCode
				
				Draft 14 
				200707191642Z		-- July 19, 2007 at 16:42 GMT
				- added bandwidth code 2,5 MHz to AsmaxBandwidthCode
				
				Draft 13
				200706201600Z		-- June 20, 2007 at 16:00 GMT
				- added asMaxBsCmVoipServerEnabled
				- deprecated asMaxBsCmVoipServerStorageSize
				
				Draft 12
				200706011700Z		-- June 01, 2007 at 17:00 GMT
				- added bandiwth code 2.75 MHz to AsmaxBandwidthCode
				
				Draft 11
				200704241100Z		-- April 24, 2007 at 11:00 GMT
				- changed or added defaults for:
				asMaxBsCmVoipServerSswIpAddressType
				asMaxBsCmVoipServerSswIpAddress
				asMaxBsCmVoipServerMaxCalls
				asMaxBsCmVoipServerRestartPolicy
				- fixed units to match implementaion
				asMaxBsCmVoipServerMaxBandwidth
				- removed AsDot1qVlanIdOrNone to avoid importing symbols from AIRSPAN-Q-BRIDGE-MIB 
				(incompatibility with AIRSPAN-DEMOMAX-MIB)
				- added AsmaxVlanIdOrNone, AsmaxExtendedVlanIdOrNone
				
				Draft 10
				200704041600Z		-- April 04, 2007 at 16:00 GMT
				- Added protocol VLAN configuration objects 
				to asMaxBsCmVoipQosTable
				
				Draft 9
				200610181014Z		-- October 18, 2006 at 10:14 GMT
				- Added swTypeBsdu to AsmaxBsSoftwareType enumeration
				- Added columns required for upgrade with FTP server:
				asMaxBsCmSwServerType
				asMaxBsCmSwServerUserName
				asMaxBsCmSwServerPassword
								
				Draft 8A:
				200607131704Z		-- July 13, 2006 at 17:04 GMT
				- fixed default in asMaxBsCmVoipServerRestartPolicy
				
				Draft 8:
				200607040829Z		-- July 04, 2006 at 08:29 GMT
				- Reworked asMaxBsCmSwUpgradeTable to allow for 2 phase activation
				and reporting 3 versions of software. Change names of objects (safe as not used yet by 
				anything different than SOC):
				ActiveVersion => PrimaryVersion
				StandbyVersion => SecondaryVersion
				Added RunningVersion.
				
				Draft 7
				200606291550Z		-- June 29, 2006 at 15:50 GMT
				- additional swtypes added to AsmaxBsSoftwareType
				
				Draft 6:
				200606261205Z		-- June 26, 2006 at 12:05 GMT
				- Moved asMaxBsCmSwType type definition to textual convention
				for use by other MIB modules
				- Reworked Ntp config to use InetAddress instead of IpAddress
				
				Draft 5D:
				200604181124Z		-- April 18, 2006 at 11:24 GMT
				- added some textual conventions for use in other BS MIB modules
				
				Draft 5C:
				200603301601Z		-- March 30, 2006 at 16:01 GMT
				- Corrected ACCESS for some columns in asMaxBsCmSwUpgradeTable
				
				Draft 5B
				200603230912Z		-- March 23, 2006 at 09:12 GMT
				- unified name prefixes to asMaxBsCm in objects in asMaxBsCmSwUpgradeTable
				- improved definition of asMaxBsCmVoipServerRestartPolicy
				
				Draft 5A
				200603221114Z		-- March 22, 2006 at 11:14 GMT
				- added table asMaxBsCmVoipQosTable
				- added columns to asMaxBsCmGpsDeviceStatusTable:
				- asMaxBsCmGpsHbsqHR
				- asMaxBsCmGpsWtrWR
				- added columns to asMaxBsCmGpsDeviceConfigEntry:
				- asMaxBsCmGpsHbsqHU
				- asMaxBsCmGpsWtrWU
								
				Draft 4A
				200603202318Z		-- March 20, 2006 at 23:18 GMT
				- added asMaxBsCmNtpConfigTable
				
				Draft 3A
				200603171943Z		-- March 17, 2006 at 19:43 GMT
				- Added SW upgrade table
				
				Draft 2B
				200603091045Z		-- March 09, 2006 at 10:45 GMT
				- Moved carrier sense objects to interface MIB
				- Added descriptions and other details to Gps trap objects
				
				Draft 2A
				200603070041Z		-- March 07, 2006 at 00:41 GMT
				- Created notificatio objects for Gps traps
				- Created notification objects for Carrier Sense system
								
				Draft 1A
				200511230240Z		-- November 23, 2005 at 02:40 GMT
				-Created for common objects implemented by all or most of BSs
				Gps tables in the first draft."
			REVISION "200711301010Z"		-- November 30, 2007 at 10:10 GMT
			DESCRIPTION 
				"Draft16
				gpsAlarms moved to textual conventions."
			REVISION "200802251109Z"		-- February 25, 2008 at 11:09 GMT
			DESCRIPTION 
				"Draft17
				- added swTypeBoot to AsmaxBsSoftwareType"
			REVISION "200803271213Z"		-- March 27, 2008 at 12:13 GMT
			DESCRIPTION 
				"Draft 18
				- added 1.5MHz bandwidth"
			REVISION "200804161200Z"		-- April 16, 2008 at 12:00 GMT
			DESCRIPTION 
				"Draft 19
				- added 6MHz bandwidth"
			REVISION "200805141628Z"		-- May 14, 2008 at 16:28 GMT
			DESCRIPTION 
				"Draft 20:
				GpsModuleType added to GpsStatus table."
			REVISION "200806111724Z"		-- June 11, 2008 at 17:24 GMT
			DESCRIPTION 
				"Draft 21:
				enumerations for asMaxBsCmGpsTrapStatusGpsComms and Lock extended.
				new trap asMaxBsCmGpsSnrChangeTrap added."
			REVISION "200806121034Z"		-- June 12, 2008 at 10:34 GMT
			DESCRIPTION 
				"Draft 22:
				GpsModuleType enum corrected based on IIB.
				extended to have unknown."
			REVISION "200806121131Z"		-- June 12, 2008 at 11:31 GMT
			DESCRIPTION 
				"Draft 23:
				asMaxBsCmGpsTrapStatusGpsSnr made as read-only."
			REVISION "200806231025Z"		-- June 23, 2008 at 10:25 GMT
			DESCRIPTION 
				"Draft 24:
				GpsSnrChangeTrapEnabled introduced."
			REVISION "200902101601Z"		-- February 10, 2009 at 16:01 GMT
			DESCRIPTION 
				"Draft 25:
				AsmaxBsSoftwareType extended for DtoE and EtoD"
			REVISION "200904211016Z"		-- April 21, 2009 at 10:16 GMT
			DESCRIPTION 
				"Draft 26:
				SwTypes corrected to include CombinedBsMobile."
			REVISION "200904241707Z"		-- April 24, 2009 at 17:07 GMT
			DESCRIPTION 
				"Draft 28:
				Added trap asMaxBsCmGpsOsaAlarmsChangeTrap"
			REVISION "200904271742Z"		-- April 27, 2009 at 17:42 GMT
			DESCRIPTION 
				"Draft 29:
				Added object asMaxBsCmGpsOsaAlarmsChangeTrapEnabled.
				Added defaults for all trap control objects in asMaxBsCmTrapControlTable."
			REVISION "200908181659Z"		-- August 18, 2009 at 16:59 GMT
			DESCRIPTION 
				"Draft 30:
				Added asMaxBsCmVoipCommsChangeTrap
				Added asMaxBsCmVoipTrapStatusTable"
			REVISION "201011171117Z"		-- November 17, 2010 at 11:17 GMT
			DESCRIPTION 
				"Draft 31:
				swTypeAirSynergy(17) added to AsmaxBsSoftwareType"
			REVISION "201012031022Z"		-- December 03, 2010 at 10:22 GMT
			DESCRIPTION 
				"Draft 32:
				axMaxBsCmGpsModuleType value 2 changed from unknown to condorGpsModule, GpsAlarms now has bits 6 and 7 defined"
			::= { asMaxBS 1 }

		
	
--
-- Textual conventions
--
	
		GpsAlarms ::= TEXTUAL-CONVENTION
			STATUS current
			DESCRIPTION 
				"Description."
			SYNTAX BITS
				{
				alarmOcxoWarmUpOrFailure(0),
				alarmTrackingFast(1),
				alarmHoldoverMode(2),
				alarmInitWarmUp(3),
				alarmAntenna(4),
				alarmGpsTiming(5),
				alarmSnRange(6),
				alarmNoLock(7)
				}

		AsmaxBsSoftwareType ::= TEXTUAL-CONVENTION
			STATUS current
			DESCRIPTION 
				"Defines the type of image or image package to install. 
				Different types may require different implementation.
				Some types are implicitly linked to specific type of hardware 
				e.g. swTypeBsdu will be used by BSDU.
				"
			SYNTAX INTEGER
				{
				swTypeOs(1),
				swTypeApp(2),
				swTypeScrt(3),
				swTypeMcrt(4),
				swTypeCombinedMicromax(5),
				swTypeCombinedHipermax(6),
				swTypeSecurityCertificates(7),
				swTypeSocObsoleted(11),
				swTypeBsdu(12),
				swTypeBoot(13),
				swTypeCombinedBsMobile(14),
				swTypeDtoE(15),
				swTypeEtoD(16),
				swTypeAirSynergy(17)
				}

		AsmaxVlanIdOrNone ::= TEXTUAL-CONVENTION
			DISPLAY-HINT 
				"d"
			STATUS current
			DESCRIPTION 
				"The VLAN-ID that uniquely identifies a specific VLAN,
				or no VLAN.  The special value of zero is used to
				indicate that no VLAN-ID is present or used.  This can
				be used in any situation where an object or a table entry
				must refer either to a specific VLAN, or to no VLAN.
				
				Note that a MIB object that is defined using this
				TEXTUAL-CONVENTION should clarify the meaning of
				'no VLAN' (i.e., the special value 0).
				
				This textual convetion is copied from AIRSPAN-Q-BRIDGE-MIB.
				It is not imported though to allow compatibility with BSs
				implementing AIRSPAN-DEMOMAX-MIB."
			SYNTAX Integer32 (0 | 1..4094)

		AsmaxBandwidthCode ::= TEXTUAL-CONVENTION
			STATUS current
			DESCRIPTION 
				"Defines common encoding of available channel bandwidths."
			SYNTAX INTEGER
				{
				bandwidth1dot75MHz(0),
				bandwidth3dot5MHz(1),
				bandwidth5MHz(2),
				bandwidth7MHz(3),
				bandwidth10MHz(4),
				bandwidth2dot75MHz(5),
				bandwidth2dot5MHz(6),
				bandwidth3MHz(7),
				bandwidth1dot5MHz(8),
				bandwidth6MHz(9)
				}

		AsmaxExtendedVlanId ::= TEXTUAL-CONVENTION
			DISPLAY-HINT 
				"d"
			STATUS current
			DESCRIPTION 
				"Defines VLAN ID for use in Airspan specifc 
				implementation of VLAN bridge.
				Range 1.4094 is reserved for standard (802.1Q) VLAN IDs.
				Value of 4096 is used for untagged traffic."
			REFERENCE 
				"RFC2674, IEEE802.1Q, IEEE801.3"
			SYNTAX INTEGER (1..4094 | 4096)

		AsmaxExtendedVlanIdOrNone ::= TEXTUAL-CONVENTION
			DISPLAY-HINT 
				"d"
			STATUS current
			DESCRIPTION 
				"Defines VLAN ID for use in Airspan specifc 
				implementation of VLAN bridge.
				Range 1.4094 is reserved for standard (802.1Q) VLAN IDs.
				Value of 4096 is used for untagged traffic.
				Value of 0 means none."
			REFERENCE 
				"RFC2674, IEEE802.1Q, IEEE801.3"
			SYNTAX INTEGER (0 | 1..4094 | 4096)

		AsmaxVlanId ::= TEXTUAL-CONVENTION
			STATUS current
			DESCRIPTION 
				"Defines VLAN ID as per standard (802.1Q) VLAN IDs."
			SYNTAX INTEGER (1..4094)

	
--
-- Node definitions
--
	
		-- 1.3.6.1.4.1.989.1.16.2.1.1
		asMaxBsCmConformance OBJECT IDENTIFIER ::= { asMaxBSCommon 1 }

		
		-- 1.3.6.1.4.1.989.1.16.2.1.1.1
		asMaxBsCmGroups OBJECT IDENTIFIER ::= { asMaxBsCmConformance 1 }

		
		-- 1.3.6.1.4.1.989.1.16.2.1.1.1.1
		asMaxBsCmGpsGroup OBJECT-GROUP
			OBJECTS { asMaxBsCmGpsTauTR, asMaxBsCmGpsModeMR, asMaxBsCmGpsNumVisibleSatellites, asMaxBsCmGpsNumTrackedSatellites, asMaxBsCmGpsLatitude, 
				asMaxBsCmGpsLongitude, asMaxBsCmGpsHeight, asMaxBsCmGpsAlarms, asMaxBsCmGpsLedStatus, asMaxBsCmGpsAlarmsMask, 
				asMaxBsCmGpsTauTU, asMaxBsCmGpsModeMU, asMaxBsCmGpsPpsCableDelay, asMaxBsCmGpsHbsqHR, asMaxBsCmGpsModuleType, 
				asMaxBsCmGpsTrapStatusGpsSnr, asMaxBsCmGpsSnrChangeTrapEnabled, asMaxBsCmGpsOsaAlarmsChangeTrapEnabled, asMaxBsCmGpsPpsUserOffset, asMaxBsCmGpsCommsChangeTrapEnabled, 
				asMaxBsCmGpsLockChangeTrapEnabled, asMaxBsCmGpsTrapStatusGpsInstance, asMaxBsCmGpsTrapStatusGpsComms, asMaxBsCmGpsTrapStatusGpsLock, asMaxBsCmGpsWtrWR, 
				asMaxBsCmGpsHbsqHU, asMaxBsCmGpsWtrWU }
			STATUS current
			DESCRIPTION 
				"Description."
			::= { asMaxBsCmGroups 1 }

		
		-- 1.3.6.1.4.1.989.1.16.2.1.1.1.2
		asMaxBsCmGpsNotificationGroup NOTIFICATION-GROUP
			NOTIFICATIONS { asMaxBsCmGpsCommsChangeTrap, asMaxBsCmGpsLockChangeTrap, asMaxBsCmGpsSnrChangeTrap, asMaxBsCmGpsOsaAlarmsChangeTrap }
			STATUS current
			DESCRIPTION 
				"Description."
			::= { asMaxBsCmGroups 2 }

		
		-- 1.3.6.1.4.1.989.1.16.2.1.1.1.3
		asMaxBsCmDeviceGroup OBJECT-GROUP
			OBJECTS { asMaxBsCmSwCfgCommand, asMaxBsCmSwCfgFileServerAddrType, asMaxBsCmSwCfgFileServerAddr, asMaxBsCmSwStatusCode, asMaxBsCmSwStatusProgress, 
				asMaxBsCmNtpConfigIpAddress1Server, asMaxBsCmNtpConfigIpAddress2Server, asMaxBsCmNtpConfigIpAddress3Server, asMaxBsCmNtpConfigIpAddress4Server, asMaxBsCmSwTypeDescription, 
				asMaxBsCmNtpConfigIpAddressType4Server, asMaxBsCmNtpConfigIpAddressType3Server, asMaxBsCmNtpConfigIpAddressType2Server, asMaxBsCmNtpConfigIpAddressType1Server, asMaxBsCmSwRunningVersionDetails, 
				asMaxBsCmSwRunningVersion, asMaxBsCmSwSecondaryVersionDetails, asMaxBsCmSwSecondaryVersion, asMaxBsCmSwPrimaryVersionDetails, asMaxBsCmSwPrimaryVersion, 
				asMaxBsCmSwCfgVersionToBecomePrimary, asMaxBsCmSwServerPassword, asMaxBsCmSwServerUserName, asMaxBsCmSwServerType, asMaxBsCmSwStatusString, 
				asMaxBsCmSwCfgFileToInstall }
			STATUS current
			DESCRIPTION 
				"Description."
			::= { asMaxBsCmGroups 3 }

		
		-- 1.3.6.1.4.1.989.1.16.2.1.1.1.4
		asMaxBsCmVoipGroup OBJECT-GROUP
			OBJECTS { asMaxBsCmVoipServerSswIpAddressType, asMaxBsCmVoipServerSswIpAddress, asMaxBsCmVoipServerListenPort, asMaxBsCmVoipServerMaxBandwidth, asMaxBsCmVoipServerMaxCalls, 
				asMaxBsCmVoipServerKeepAliveRetries, asMaxBsCmVoipServerRestartPolicy, asMaxBsCmVoipServerQTagEnabled, asMaxBsCmVoipServerQTagVlanID, asMaxBsCmVoipServerQTagPriority, 
				asMaxBsCmVoipServerEnabled, asMaxBsCmVoipTrapInstance, asMaxBsCmVoipTrapCommsStatus }
			STATUS current
			DESCRIPTION 
				"Description."
			::= { asMaxBsCmGroups 4 }

		
		-- 1.3.6.1.4.1.989.1.16.2.1.1.1.5
		asMaxBsCmDeprecatedGroup OBJECT-GROUP
			OBJECTS { asMaxBsCmVoipServerStorageSize }
			STATUS deprecated
			DESCRIPTION 
				"Description."
			::= { asMaxBsCmGroups 5 }

		
		-- 1.3.6.1.4.1.989.1.16.2.1.1.1.6
		asMaxBsCmVoipNotificationGroup NOTIFICATION-GROUP
			NOTIFICATIONS { asMaxBsCmVoipCommsChangeTrap }
			STATUS current
			DESCRIPTION 
				"Description."
			::= { asMaxBsCmGroups 6 }

		
		-- 1.3.6.1.4.1.989.1.16.2.1.1.2
		asMaxBsCmCompliances OBJECT IDENTIFIER ::= { asMaxBsCmConformance 2 }

		
		-- 1.3.6.1.4.1.989.1.16.2.1.2
		asMaxBsCmNotifications OBJECT IDENTIFIER ::= { asMaxBSCommon 2 }

		
		-- 1.3.6.1.4.1.989.1.16.2.1.2.0
		asMaxBsCmTrapPrefix OBJECT IDENTIFIER ::= { asMaxBsCmNotifications 0 }

		
		-- 1.3.6.1.4.1.989.1.16.2.1.2.0.1
		asMaxBsCmGpsCommsChangeTrap NOTIFICATION-TYPE
			OBJECTS { asMaxBsCmGpsTrapStatusGpsInstance, asMaxBsCmGpsTrapStatusGpsComms }
			STATUS current
			DESCRIPTION 
				"Trap signifies GPS module communications with the Management 
				processor status changes."
			::= { asMaxBsCmTrapPrefix 1 }

		
		-- 1.3.6.1.4.1.989.1.16.2.1.2.0.2
		asMaxBsCmGpsLockChangeTrap NOTIFICATION-TYPE
			OBJECTS { asMaxBsCmGpsTrapStatusGpsInstance, asMaxBsCmGpsTrapStatusGpsLock }
			STATUS current
			DESCRIPTION 
				"Trap signifies GPS has lost or recovered timing lock with satellite(s)."
			::= { asMaxBsCmTrapPrefix 2 }

		
		-- 1.3.6.1.4.1.989.1.16.2.1.2.0.3
		asMaxBsCmGpsSnrChangeTrap NOTIFICATION-TYPE
			OBJECTS { asMaxBsCmGpsTrapStatusGpsInstance, asMaxBsCmGpsTrapStatusGpsSnr }
			STATUS current
			DESCRIPTION 
				"Trap sent each time the value of asMaxBsCmGpsTrapStatusGpsSnr changes indicating 
				that GPS antenna signal SNR is out of range."
			::= { asMaxBsCmTrapPrefix 3 }

		
		-- 1.3.6.1.4.1.989.1.16.2.1.2.0.4
		asMaxBsCmGpsOsaAlarmsChangeTrap NOTIFICATION-TYPE
			OBJECTS { asMaxBsCmGpsTrapStatusGpsInstance, asMaxBsCmGpsAlarms }
			STATUS current
			DESCRIPTION 
				"Trap sent each time the value of  asMaxBsCmGpsAlarms changes.
				For some bits of status register the alarm should be raised by EMS."
			::= { asMaxBsCmTrapPrefix 4 }

		
		-- 1.3.6.1.4.1.989.1.16.2.1.2.0.5
		asMaxBsCmVoipCommsChangeTrap NOTIFICATION-TYPE
			OBJECTS { asMaxBsCmVoipTrapInstance, asMaxBsCmVoipTrapCommsStatus }
			STATUS current
			DESCRIPTION 
				"Trap signifies change of commications status with VOIP server."
			::= { asMaxBsCmTrapPrefix 5 }

		
		-- 1.3.6.1.4.1.989.1.16.2.1.2.1
		asMaxBsCmTrapControlTable OBJECT-TYPE
			SYNTAX SEQUENCE OF AsMaxBsCmTrapControlEntry
			MAX-ACCESS not-accessible
			STATUS current
			DESCRIPTION
				"Defines enable/disable controls for traps."
			::= { asMaxBsCmNotifications 1 }

		
		-- 1.3.6.1.4.1.989.1.16.2.1.2.1.1
		asMaxBsCmTrapControlEntry OBJECT-TYPE
			SYNTAX AsMaxBsCmTrapControlEntry
			MAX-ACCESS not-accessible
			STATUS current
			DESCRIPTION
				"Single row."
			INDEX { asMaxBsCmTrapControlIndex }
			::= { asMaxBsCmTrapControlTable 1 }

		
		AsMaxBsCmTrapControlEntry ::=
			SEQUENCE { 
				asMaxBsCmTrapControlIndex
					INTEGER,
				asMaxBsCmGpsCommsChangeTrapEnabled
					AsmaxBooleanSwitch,
				asMaxBsCmGpsLockChangeTrapEnabled
					AsmaxBooleanSwitch,
				asMaxBsCmGpsSnrChangeTrapEnabled
					AsmaxBooleanSwitch,
				asMaxBsCmGpsOsaAlarmsChangeTrapEnabled
					AsmaxBooleanSwitch
			 }

		-- 1.3.6.1.4.1.989.1.16.2.1.2.1.1.1
		asMaxBsCmTrapControlIndex OBJECT-TYPE
			SYNTAX INTEGER (1)
			MAX-ACCESS not-accessible
			STATUS current
			DESCRIPTION
				"Arbitrary index - single row."
			::= { asMaxBsCmTrapControlEntry 1 }

		
		-- 1.3.6.1.4.1.989.1.16.2.1.2.1.1.2
		asMaxBsCmGpsCommsChangeTrapEnabled OBJECT-TYPE
			SYNTAX AsmaxBooleanSwitch
			MAX-ACCESS read-write
			STATUS current
			DESCRIPTION
				"Enables/disables GpsCommsChangeTrap."
			DEFVAL { booleanTrue }
			::= { asMaxBsCmTrapControlEntry 2 }

		
		-- 1.3.6.1.4.1.989.1.16.2.1.2.1.1.3
		asMaxBsCmGpsLockChangeTrapEnabled OBJECT-TYPE
			SYNTAX AsmaxBooleanSwitch
			MAX-ACCESS read-write
			STATUS current
			DESCRIPTION
				"Enables/disables GpsLockChangeTrap."
			DEFVAL { booleanTrue }
			::= { asMaxBsCmTrapControlEntry 3 }

		
		-- 1.3.6.1.4.1.989.1.16.2.1.2.1.1.4
		asMaxBsCmGpsSnrChangeTrapEnabled OBJECT-TYPE
			SYNTAX AsmaxBooleanSwitch
			MAX-ACCESS read-write
			STATUS current
			DESCRIPTION
				"Enables/disables GpsSnrChangeTrap."
			DEFVAL { booleanTrue }
			::= { asMaxBsCmTrapControlEntry 4 }

		
		-- 1.3.6.1.4.1.989.1.16.2.1.2.1.1.5
		asMaxBsCmGpsOsaAlarmsChangeTrapEnabled OBJECT-TYPE
			SYNTAX AsmaxBooleanSwitch
			MAX-ACCESS read-write
			STATUS current
			DESCRIPTION
				"Description."
			DEFVAL { booleanTrue }
			::= { asMaxBsCmTrapControlEntry 5 }

		
		-- 1.3.6.1.4.1.989.1.16.2.1.2.2
		asMaxBsCmGpsTrapStatusTable OBJECT-TYPE
			SYNTAX SEQUENCE OF AsMaxBsCmGpsTrapStatusEntry
			MAX-ACCESS not-accessible
			STATUS current
			DESCRIPTION
				"Contains status of objects assotiated with traps."
			::= { asMaxBsCmNotifications 2 }

		
		-- 1.3.6.1.4.1.989.1.16.2.1.2.2.1
		asMaxBsCmGpsTrapStatusEntry OBJECT-TYPE
			SYNTAX AsMaxBsCmGpsTrapStatusEntry
			MAX-ACCESS not-accessible
			STATUS current
			DESCRIPTION
				"One row per "
			INDEX { asMaxBsCmGpsInstance }
			::= { asMaxBsCmGpsTrapStatusTable 1 }

		
		AsMaxBsCmGpsTrapStatusEntry ::=
			SEQUENCE { 
				asMaxBsCmGpsTrapStatusGpsInstance
					INTEGER,
				asMaxBsCmGpsTrapStatusGpsComms
					INTEGER,
				asMaxBsCmGpsTrapStatusGpsLock
					INTEGER,
				asMaxBsCmGpsTrapStatusGpsSnr
					INTEGER
			 }

		-- 1.3.6.1.4.1.989.1.16.2.1.2.2.1.1
		asMaxBsCmGpsTrapStatusGpsInstance OBJECT-TYPE
			SYNTAX INTEGER (1..255)
			MAX-ACCESS read-only
			STATUS current
			DESCRIPTION
				"Index identifying GPS instance as defined in GpsDeviceStatusTable."
			::= { asMaxBsCmGpsTrapStatusEntry 1 }

		
		-- 1.3.6.1.4.1.989.1.16.2.1.2.2.1.2
		asMaxBsCmGpsTrapStatusGpsComms OBJECT-TYPE
			SYNTAX INTEGER
				{
				statusGpsCommsActive(0),
				statusGpsCommsInactive(1),
				statusGpsCommsResetting(2)
				}
			MAX-ACCESS read-only
			STATUS current
			DESCRIPTION
				"Defines the state of GPS-control processor comms."
			::= { asMaxBsCmGpsTrapStatusEntry 2 }

		
		-- 1.3.6.1.4.1.989.1.16.2.1.2.2.1.3
		asMaxBsCmGpsTrapStatusGpsLock OBJECT-TYPE
			SYNTAX INTEGER
				{
				statusGpsLocked(0),
				statusGpsLockLossDegraded(1),
				statusGpsLockLostExpired(2)
				}
			MAX-ACCESS read-only
			STATUS current
			DESCRIPTION
				"Defines the current state of GPS signal lock."
			::= { asMaxBsCmGpsTrapStatusEntry 3 }

		
		-- 1.3.6.1.4.1.989.1.16.2.1.2.2.1.4
		asMaxBsCmGpsTrapStatusGpsSnr OBJECT-TYPE
			SYNTAX INTEGER
				{
				statusGpsSnrNormal(0),
				statusGpsSnrLow(1)
				}
			MAX-ACCESS read-only
			STATUS current
			DESCRIPTION
				"Defines the current state of GPS snr."
			::= { asMaxBsCmGpsTrapStatusEntry 4 }

		
		-- 1.3.6.1.4.1.989.1.16.2.1.2.3
		asMaxBsCmVoipTrapStatusTable OBJECT-TYPE
			SYNTAX SEQUENCE OF AsMaxBsCmVoipTrapStatusEntry
			MAX-ACCESS not-accessible
			STATUS current
			DESCRIPTION
				"Reports status of VOIP server"
			::= { asMaxBsCmNotifications 3 }

		
		-- 1.3.6.1.4.1.989.1.16.2.1.2.3.1
		asMaxBsCmVoipTrapStatusEntry OBJECT-TYPE
			SYNTAX AsMaxBsCmVoipTrapStatusEntry
			MAX-ACCESS not-accessible
			STATUS current
			DESCRIPTION
				"Each row reports a status of a VoiceMax server (normally
				only one instance present).
				"
			INDEX { asMaxBsCmVoipTrapInstance }
			::= { asMaxBsCmVoipTrapStatusTable 1 }

		
		AsMaxBsCmVoipTrapStatusEntry ::=
			SEQUENCE { 
				asMaxBsCmVoipTrapInstance
					Integer32,
				asMaxBsCmVoipTrapCommsStatus
					INTEGER
			 }

		-- 1.3.6.1.4.1.989.1.16.2.1.2.3.1.1
		asMaxBsCmVoipTrapInstance OBJECT-TYPE
			SYNTAX Integer32 (1..255)
			MAX-ACCESS read-only
			STATUS current
			DESCRIPTION
				"Voip Server Instance (normally 1)"
			::= { asMaxBsCmVoipTrapStatusEntry 1 }

		
		-- 1.3.6.1.4.1.989.1.16.2.1.2.3.1.2
		asMaxBsCmVoipTrapCommsStatus OBJECT-TYPE
			SYNTAX INTEGER
				{
				none(1),
				connected(2),
				disconnected(3)
				}
			MAX-ACCESS read-only
			STATUS current
			DESCRIPTION
				"Connection state of Voip Server.
				none - This is used when Voip Server is not expected
				connected/disconnected - Used when a Voip Server is expected"
			DEFVAL { none }
			::= { asMaxBsCmVoipTrapStatusEntry 2 }

		
		-- 1.3.6.1.4.1.989.1.16.2.1.3
		asMaxBsCmGps OBJECT IDENTIFIER ::= { asMaxBSCommon 3 }

		
		-- 1.3.6.1.4.1.989.1.16.2.1.3.3
		asMaxBsCmGpsDeviceStatusTable OBJECT-TYPE
			SYNTAX SEQUENCE OF AsMaxBsCmGpsDeviceStatusEntry
			MAX-ACCESS not-accessible
			STATUS current
			DESCRIPTION
				"Reports status of GPS receiver."
			::= { asMaxBsCmGps 3 }

		
		-- 1.3.6.1.4.1.989.1.16.2.1.3.3.1
		asMaxBsCmGpsDeviceStatusEntry OBJECT-TYPE
			SYNTAX AsMaxBsCmGpsDeviceStatusEntry
			MAX-ACCESS not-accessible
			STATUS current
			DESCRIPTION
				"Each row reports a status of an instance of GPS receiver (normally
				only one instance present).
				General parameters in this table are shared by all types of GPS modules.
				Specific parameters in this table are for OSA type only.
				Refer to corresponding specific table for those parameters for other types of GPS modules."
			INDEX { asMaxBsCmGpsInstance }
			::= { asMaxBsCmGpsDeviceStatusTable 1 }

		
		AsMaxBsCmGpsDeviceStatusEntry ::=
			SEQUENCE { 
				asMaxBsCmGpsInstance
					INTEGER,
				asMaxBsCmGpsTauTR
					INTEGER,
				asMaxBsCmGpsModeMR
					INTEGER,
				asMaxBsCmGpsNumVisibleSatellites
					INTEGER,
				asMaxBsCmGpsNumTrackedSatellites
					INTEGER,
				asMaxBsCmGpsLatitude
					INTEGER,
				asMaxBsCmGpsLongitude
					INTEGER,
				asMaxBsCmGpsHeight
					INTEGER,
				asMaxBsCmGpsAlarms
					GpsAlarms,
				asMaxBsCmGpsLedStatus
					INTEGER,
				asMaxBsCmGpsHbsqHR
					INTEGER,
				asMaxBsCmGpsWtrWR
					INTEGER,
				asMaxBsCmGpsModuleType
					INTEGER
			 }

		-- 1.3.6.1.4.1.989.1.16.2.1.3.3.1.1
		asMaxBsCmGpsInstance OBJECT-TYPE
			SYNTAX INTEGER (1..255)
			MAX-ACCESS not-accessible
			STATUS current
			DESCRIPTION
				"Identifies instance of GPS device (normally only one instance-row 
				expected), used as an index to GPS configuation and status tables."
			::= { asMaxBsCmGpsDeviceStatusEntry 1 }

		
		-- 1.3.6.1.4.1.989.1.16.2.1.3.3.1.2
		asMaxBsCmGpsTauTR OBJECT-TYPE
			SYNTAX INTEGER (100..50000)
			UNITS "s"
			MAX-ACCESS read-only
			STATUS current
			DESCRIPTION
				"TimeLoop Constant currently used by system."
			DEFVAL { 2000 }
			::= { asMaxBsCmGpsDeviceStatusEntry 2 }

		
		-- 1.3.6.1.4.1.989.1.16.2.1.3.3.1.3
		asMaxBsCmGpsModeMR OBJECT-TYPE
			SYNTAX INTEGER
				{
				modeUnknown(0),
				modeInit(1),
				modeWarmUp(2),
				modeTrackedFast(3),
				modeTracked(4),
				modeHoldover(5)
				}
			MAX-ACCESS read-only
			STATUS current
			DESCRIPTION
				"Current working mode."
			DEFVAL { modeUnknown }
			::= { asMaxBsCmGpsDeviceStatusEntry 3 }

		
		-- 1.3.6.1.4.1.989.1.16.2.1.3.3.1.4
		asMaxBsCmGpsNumVisibleSatellites OBJECT-TYPE
			SYNTAX INTEGER (0..12)
			MAX-ACCESS read-only
			STATUS current
			DESCRIPTION
				"Number of visible satellites."
			DEFVAL { 0 }
			::= { asMaxBsCmGpsDeviceStatusEntry 4 }

		
		-- 1.3.6.1.4.1.989.1.16.2.1.3.3.1.5
		asMaxBsCmGpsNumTrackedSatellites OBJECT-TYPE
			SYNTAX INTEGER (0..8)
			MAX-ACCESS read-only
			STATUS current
			DESCRIPTION
				"Number of tracked satellites."
			DEFVAL { 0 }
			::= { asMaxBsCmGpsDeviceStatusEntry 5 }

		
		-- 1.3.6.1.4.1.989.1.16.2.1.3.3.1.6
		asMaxBsCmGpsLatitude OBJECT-TYPE
			SYNTAX INTEGER (-900000..900000)
			UNITS "ddmmss"
			MAX-ACCESS read-only
			STATUS current
			DESCRIPTION
				"Latitude represented in +/- ddmmss"
			DEFVAL { 0 }
			::= { asMaxBsCmGpsDeviceStatusEntry 6 }

		
		-- 1.3.6.1.4.1.989.1.16.2.1.3.3.1.7
		asMaxBsCmGpsLongitude OBJECT-TYPE
			SYNTAX INTEGER (-1800000..1800000)
			UNITS "dddmmss"
			MAX-ACCESS read-only
			STATUS current
			DESCRIPTION
				"Longitude represented in +/- dddmmss"
			DEFVAL { 0 }
			::= { asMaxBsCmGpsDeviceStatusEntry 7 }

		
		-- 1.3.6.1.4.1.989.1.16.2.1.3.3.1.8
		asMaxBsCmGpsHeight OBJECT-TYPE
			SYNTAX INTEGER (-100000..999999)
			UNITS "cm"
			MAX-ACCESS read-only
			STATUS current
			DESCRIPTION
				"Height in centimetres"
			DEFVAL { 0 }
			::= { asMaxBsCmGpsDeviceStatusEntry 8 }

		
		-- 1.3.6.1.4.1.989.1.16.2.1.3.3.1.9
		asMaxBsCmGpsAlarms OBJECT-TYPE
			SYNTAX GpsAlarms
			MAX-ACCESS read-only
			STATUS current
			DESCRIPTION
				"Returns current status of GPS-SB. It includes the alarms information
				ALARMS: for each bit, '0' means alarm condition not active 
				while '1' means alarm condition active
				"
			::= { asMaxBsCmGpsDeviceStatusEntry 9 }

		
		-- 1.3.6.1.4.1.989.1.16.2.1.3.3.1.10
		asMaxBsCmGpsLedStatus OBJECT-TYPE
			SYNTAX INTEGER
				{
				ledsOff(0),
				ledsRedOn(1),
				ledsRedBlinking(2),
				ledsGreenOn(3),
				ledsGreenBlinking(4),
				ledsGreenRedBlinking(5)
				}
			MAX-ACCESS read-only
			STATUS current
			DESCRIPTION
				"Description."
			DEFVAL { ledsOff }
			::= { asMaxBsCmGpsDeviceStatusEntry 10 }

		
		-- 1.3.6.1.4.1.989.1.16.2.1.3.3.1.11
		asMaxBsCmGpsHbsqHR OBJECT-TYPE
			SYNTAX INTEGER (0..7200)
			UNITS "minutes"
			MAX-ACCESS read-only
			STATUS current
			DESCRIPTION
				"Remaining time of Holdover Before Squelch (HBSQ) function in minutes. 
				In normal operation, this value is equal to the configured HBSQ."
			DEFVAL { 1440 }
			::= { asMaxBsCmGpsDeviceStatusEntry 11 }

		
		-- 1.3.6.1.4.1.989.1.16.2.1.3.3.1.12
		asMaxBsCmGpsWtrWR OBJECT-TYPE
			SYNTAX INTEGER (0..2500)
			UNITS "s"
			MAX-ACCESS read-only
			STATUS current
			DESCRIPTION
				"Remaining time for Wait to Restore (WTR) on GPS input in seconds"
			DEFVAL { 60 }
			::= { asMaxBsCmGpsDeviceStatusEntry 12 }

		
		-- 1.3.6.1.4.1.989.1.16.2.1.3.3.1.13
		asMaxBsCmGpsModuleType OBJECT-TYPE
			SYNTAX INTEGER
				{
				osa(0),
				cw25(1),
				condorGpsModule(2)
				}
			MAX-ACCESS read-only
			STATUS current
			DESCRIPTION
				"Module type as one of the enumerated ones.
				By default, it is assumed as OSA. 
				This enumeration matches definition in IIB."
			::= { asMaxBsCmGpsDeviceStatusEntry 13 }

		
		-- 1.3.6.1.4.1.989.1.16.2.1.3.4
		asMaxBsCmGpsDeviceConfigTable OBJECT-TYPE
			SYNTAX SEQUENCE OF AsMaxBsCmGpsDeviceConfigEntry
			MAX-ACCESS not-accessible
			STATUS current
			DESCRIPTION
				"Table used to configure GPS receiver."
			::= { asMaxBsCmGps 4 }

		
		-- 1.3.6.1.4.1.989.1.16.2.1.3.4.1
		asMaxBsCmGpsDeviceConfigEntry OBJECT-TYPE
			SYNTAX AsMaxBsCmGpsDeviceConfigEntry
			MAX-ACCESS not-accessible
			STATUS current
			DESCRIPTION
				"Each row is used to configure an instance of GPS receiver (normally
				only one instance present)."
			INDEX { asMaxBsCmGpsInstance }
			::= { asMaxBsCmGpsDeviceConfigTable 1 }

		
		AsMaxBsCmGpsDeviceConfigEntry ::=
			SEQUENCE { 
				asMaxBsCmGpsAlarmsMask
					GpsAlarms,
				asMaxBsCmGpsTauTU
					INTEGER,
				asMaxBsCmGpsModeMU
					INTEGER,
				asMaxBsCmGpsPpsCableDelay
					INTEGER,
				asMaxBsCmGpsPpsUserOffset
					INTEGER,
				asMaxBsCmGpsHbsqHU
					INTEGER,
				asMaxBsCmGpsWtrWU
					INTEGER
			 }

		-- 1.3.6.1.4.1.989.1.16.2.1.3.4.1.1
		asMaxBsCmGpsAlarmsMask OBJECT-TYPE
			SYNTAX GpsAlarms
			MAX-ACCESS read-write
			STATUS current
			DESCRIPTION
				"Current alarm mask i.e. Gawhfo - 
				g: GPS Input, 
				a: Antenna, 
				w: Initialisation/warm-up, 
				h: holdover mode, 
				f: trackingfast, 
				o: ocxo fast mode"
			::= { asMaxBsCmGpsDeviceConfigEntry 1 }

		
		-- 1.3.6.1.4.1.989.1.16.2.1.3.4.1.2
		asMaxBsCmGpsTauTU OBJECT-TYPE
			SYNTAX INTEGER (100..50000)
			UNITS "s"
			MAX-ACCESS read-write
			STATUS current
			DESCRIPTION
				"User Timeloop Constant in Seconds."
			DEFVAL { 2000 }
			::= { asMaxBsCmGpsDeviceConfigEntry 2 }

		
		-- 1.3.6.1.4.1.989.1.16.2.1.3.4.1.3
		asMaxBsCmGpsModeMU OBJECT-TYPE
			SYNTAX INTEGER
				{
				modeAutomatic(0),
				modeHoldover(1)
				}
			MAX-ACCESS read-write
			STATUS current
			DESCRIPTION
				"User Working Mode."
			DEFVAL { modeAutomatic }
			::= { asMaxBsCmGpsDeviceConfigEntry 3 }

		
		-- 1.3.6.1.4.1.989.1.16.2.1.3.4.1.4
		asMaxBsCmGpsPpsCableDelay OBJECT-TYPE
			SYNTAX INTEGER (0..999999)
			UNITS "ns"
			MAX-ACCESS read-write
			STATUS current
			DESCRIPTION
				"Negative Offset of the 1PPS signal to compensate cable delay."
			DEFVAL { 0 }
			::= { asMaxBsCmGpsDeviceConfigEntry 4 }

		
		-- 1.3.6.1.4.1.989.1.16.2.1.3.4.1.5
		asMaxBsCmGpsPpsUserOffset OBJECT-TYPE
			SYNTAX INTEGER (0..999999999)
			UNITS "ns"
			MAX-ACCESS read-write
			STATUS current
			DESCRIPTION
				"Positve User offset of the 1 PPS signal."
			DEFVAL { 0 }
			::= { asMaxBsCmGpsDeviceConfigEntry 5 }

		
		-- 1.3.6.1.4.1.989.1.16.2.1.3.4.1.6
		asMaxBsCmGpsHbsqHU OBJECT-TYPE
			SYNTAX INTEGER (0..7200)
			UNITS "minutes"
			MAX-ACCESS read-write
			STATUS current
			DESCRIPTION
				"Delay in holdover mode before outputs are squelched in minutes"
			DEFVAL { 1440 }
			::= { asMaxBsCmGpsDeviceConfigEntry 6 }

		
		-- 1.3.6.1.4.1.989.1.16.2.1.3.4.1.7
		asMaxBsCmGpsWtrWU OBJECT-TYPE
			SYNTAX INTEGER (0..250)
			UNITS "10 s"
			MAX-ACCESS read-write
			STATUS current
			DESCRIPTION
				"Wait to restore time for GPS input in 10s of seconds "
			DEFVAL { 6 }
			::= { asMaxBsCmGpsDeviceConfigEntry 7 }

		
		-- 1.3.6.1.4.1.989.1.16.2.1.4
		asMaxBsCmDevice OBJECT IDENTIFIER ::= { asMaxBSCommon 4 }

		
		-- 1.3.6.1.4.1.989.1.16.2.1.4.1
		asMaxBsCmNtpConfigTable OBJECT-TYPE
			SYNTAX SEQUENCE OF AsMaxBsCmNtpConfigEntry
			MAX-ACCESS not-accessible
			STATUS current
			DESCRIPTION
				"NTP configuration."
			::= { asMaxBsCmDevice 1 }

		
		-- 1.3.6.1.4.1.989.1.16.2.1.4.1.1
		asMaxBsCmNtpConfigEntry OBJECT-TYPE
			SYNTAX AsMaxBsCmNtpConfigEntry
			MAX-ACCESS not-accessible
			STATUS current
			DESCRIPTION
				"Each row configures the network time server (normally
				only one instance present)."
			INDEX { asMaxBsCmNtpInstance }
			::= { asMaxBsCmNtpConfigTable 1 }

		
		AsMaxBsCmNtpConfigEntry ::=
			SEQUENCE { 
				asMaxBsCmNtpInstance
					INTEGER,
				asMaxBsCmNtpConfigIpAddressType1Server
					InetAddressType,
				asMaxBsCmNtpConfigIpAddress1Server
					InetAddress,
				asMaxBsCmNtpConfigIpAddressType2Server
					InetAddressType,
				asMaxBsCmNtpConfigIpAddress2Server
					InetAddress,
				asMaxBsCmNtpConfigIpAddressType3Server
					InetAddressType,
				asMaxBsCmNtpConfigIpAddress3Server
					InetAddress,
				asMaxBsCmNtpConfigIpAddressType4Server
					InetAddressType,
				asMaxBsCmNtpConfigIpAddress4Server
					InetAddress
			 }

		-- 1.3.6.1.4.1.989.1.16.2.1.4.1.1.1
		asMaxBsCmNtpInstance OBJECT-TYPE
			SYNTAX INTEGER (1..255)
			MAX-ACCESS not-accessible
			STATUS current
			DESCRIPTION
				"Identifies instance of NTP configuration (normally only one instance-row 
				expected)."
			::= { asMaxBsCmNtpConfigEntry 1 }

		
		-- 1.3.6.1.4.1.989.1.16.2.1.4.1.1.2
		asMaxBsCmNtpConfigIpAddressType1Server OBJECT-TYPE
			SYNTAX InetAddressType
			MAX-ACCESS read-write
			STATUS current
			DESCRIPTION
				"This specifies the IP address type of a network time server."
			DEFVAL { ipv4 }
			::= { asMaxBsCmNtpConfigEntry 2 }

		
		-- 1.3.6.1.4.1.989.1.16.2.1.4.1.1.3
		asMaxBsCmNtpConfigIpAddress1Server OBJECT-TYPE
			SYNTAX InetAddress
			MAX-ACCESS read-write
			STATUS current
			DESCRIPTION
				"This specifies the IP address of a network time server."
			DEFVAL { "" }
			::= { asMaxBsCmNtpConfigEntry 3 }

		
		-- 1.3.6.1.4.1.989.1.16.2.1.4.1.1.4
		asMaxBsCmNtpConfigIpAddressType2Server OBJECT-TYPE
			SYNTAX InetAddressType
			MAX-ACCESS read-write
			STATUS current
			DESCRIPTION
				"This specifies the IP address type of a network time server."
			DEFVAL { ipv4 }
			::= { asMaxBsCmNtpConfigEntry 4 }

		
		-- 1.3.6.1.4.1.989.1.16.2.1.4.1.1.5
		asMaxBsCmNtpConfigIpAddress2Server OBJECT-TYPE
			SYNTAX InetAddress
			MAX-ACCESS read-write
			STATUS current
			DESCRIPTION
				"This specifies the IP address of a network time server."
			DEFVAL { "" }
			::= { asMaxBsCmNtpConfigEntry 5 }

		
		-- 1.3.6.1.4.1.989.1.16.2.1.4.1.1.6
		asMaxBsCmNtpConfigIpAddressType3Server OBJECT-TYPE
			SYNTAX InetAddressType
			MAX-ACCESS read-write
			STATUS current
			DESCRIPTION
				"This specifies the IP address type of a network time server."
			DEFVAL { ipv4 }
			::= { asMaxBsCmNtpConfigEntry 6 }

		
		-- 1.3.6.1.4.1.989.1.16.2.1.4.1.1.7
		asMaxBsCmNtpConfigIpAddress3Server OBJECT-TYPE
			SYNTAX InetAddress
			MAX-ACCESS read-write
			STATUS current
			DESCRIPTION
				"This specifies the IP address of a network time server."
			DEFVAL { "" }
			::= { asMaxBsCmNtpConfigEntry 7 }

		
		-- 1.3.6.1.4.1.989.1.16.2.1.4.1.1.8
		asMaxBsCmNtpConfigIpAddressType4Server OBJECT-TYPE
			SYNTAX InetAddressType
			MAX-ACCESS read-write
			STATUS current
			DESCRIPTION
				"This specifies the IP address type of a network time server."
			DEFVAL { ipv4 }
			::= { asMaxBsCmNtpConfigEntry 8 }

		
		-- 1.3.6.1.4.1.989.1.16.2.1.4.1.1.9
		asMaxBsCmNtpConfigIpAddress4Server OBJECT-TYPE
			SYNTAX InetAddress
			MAX-ACCESS read-write
			STATUS current
			DESCRIPTION
				"This specifies the IP address of a network time server."
			DEFVAL { "" }
			::= { asMaxBsCmNtpConfigEntry 9 }

		
		-- 1.3.6.1.4.1.989.1.16.2.1.4.2
		asMaxBsCmSwUpgradeTable OBJECT-TYPE
			SYNTAX SEQUENCE OF AsMaxBsCmSwUpgradeEntry
			MAX-ACCESS not-accessible
			STATUS current
			DESCRIPTION
				"Description."
			::= { asMaxBsCmDevice 2 }

		
		-- 1.3.6.1.4.1.989.1.16.2.1.4.2.1
		asMaxBsCmSwUpgradeEntry OBJECT-TYPE
			SYNTAX AsMaxBsCmSwUpgradeEntry
			MAX-ACCESS not-accessible
			STATUS current
			DESCRIPTION
				"Description."
			INDEX { asMaxBsCmSwType }
			::= { asMaxBsCmSwUpgradeTable 1 }

		
		AsMaxBsCmSwUpgradeEntry ::=
			SEQUENCE { 
				asMaxBsCmSwType
					AsmaxBsSoftwareType,
				asMaxBsCmSwCfgCommand
					INTEGER,
				asMaxBsCmSwCfgFileToInstall
					DisplayString,
				asMaxBsCmSwCfgFileServerAddrType
					InetAddressType,
				asMaxBsCmSwCfgFileServerAddr
					InetAddress,
				asMaxBsCmSwCfgVersionToBecomePrimary
					DisplayString,
				asMaxBsCmSwStatusCode
					INTEGER,
				asMaxBsCmSwStatusString
					DisplayString,
				asMaxBsCmSwStatusProgress
					INTEGER,
				asMaxBsCmSwPrimaryVersion
					DisplayString,
				asMaxBsCmSwPrimaryVersionDetails
					DisplayString,
				asMaxBsCmSwSecondaryVersion
					DisplayString,
				asMaxBsCmSwSecondaryVersionDetails
					DisplayString,
				asMaxBsCmSwTypeDescription
					DisplayString,
				asMaxBsCmSwRunningVersion
					DisplayString,
				asMaxBsCmSwRunningVersionDetails
					DisplayString,
				asMaxBsCmSwServerType
					INTEGER,
				asMaxBsCmSwServerUserName
					DisplayString,
				asMaxBsCmSwServerPassword
					DisplayString
			 }

		-- 1.3.6.1.4.1.989.1.16.2.1.4.2.1.1
		asMaxBsCmSwType OBJECT-TYPE
			SYNTAX AsmaxBsSoftwareType
			MAX-ACCESS not-accessible
			STATUS current
			DESCRIPTION
				"Identifies the type of image or image package to install. 
				Different types may require different implementation
				of the upgrade process.
				'swTypeOs' is typically a maintenance operation 
				used in exceptional circumstance and by default doesn't 
				have the standby storage."
			::= { asMaxBsCmSwUpgradeEntry 1 }

		
		-- 1.3.6.1.4.1.989.1.16.2.1.4.2.1.2
		asMaxBsCmSwCfgCommand OBJECT-TYPE
			SYNTAX INTEGER
				{
				swCommandIdle(0),
				swCommandAbort(1),
				swCommandInstallOnly(2),
				swCommandSwapToPrimary(3),
				swCommandResetToPrimary(4),
				swCommandSwapAndResetToPrimary(5)
				}
			MAX-ACCESS read-write
			STATUS current
			DESCRIPTION
				"Object carries request to initiate a part of upgrate process as follows:
				- swCommandIdle - no action
				- swCommandAbort - aborts any upgrade operation reported 
				  as failed or in progress.
				- swCommandInstallOnly - instructs target to download and store 
				  the file from the file server. The file to install is identified 
				  by object 'asdmaxSwCfgFileToInstall'. The newly installed file version 
				  is reported in 'asMaxBsCmSwSecondaryVersion' object.
				- swCommandSwapToPrimary - instructs the target to swap versions in the storage
				  such that the version of primary storage (asMaxBsCmSwPrimaryVersion) matches 
				  the version set in object 'asMaxBsCmSwCfgVersionToBecomePrimary'. 
				  If primary storage already contains requested version no action is required.
				- swCommandResetToPrimary - instructs the target to auto-reset in order to
				  change running version to match the primary storage version. The reported 
				  running version (asMaxBsCmSwRunningVersion) should change as a result.
				- swCommandSwapAndResetToPrimary - instructs the target to execute the command
				  swCommandSwapToPrimary and subsequently the command swCommandResetToPrimary
				  as one atomic operation. All objects reporting versions should be updated 
				  accordingly but only after the whole operation is completed.
				This object should be treated as write-only but if read by 
				generic browser it should return always a value of 'swCommandIdle'
				"
			::= { asMaxBsCmSwUpgradeEntry 2 }

		
		-- 1.3.6.1.4.1.989.1.16.2.1.4.2.1.3
		asMaxBsCmSwCfgFileToInstall OBJECT-TYPE
			SYNTAX DisplayString
			MAX-ACCESS read-write
			STATUS current
			DESCRIPTION
				"The name of the file to install when command 'swCommandInstallOnly' is issued."
			::= { asMaxBsCmSwUpgradeEntry 3 }

		
		-- 1.3.6.1.4.1.989.1.16.2.1.4.2.1.4
		asMaxBsCmSwCfgFileServerAddrType OBJECT-TYPE
			SYNTAX InetAddressType
			MAX-ACCESS read-write
			STATUS current
			DESCRIPTION
				"Defines the type of 'asdmaxSwCfgFileServerAddr'."
			DEFVAL { ipv4 }
			::= { asMaxBsCmSwUpgradeEntry 4 }

		
		-- 1.3.6.1.4.1.989.1.16.2.1.4.2.1.5
		asMaxBsCmSwCfgFileServerAddr OBJECT-TYPE
			SYNTAX InetAddress
			MAX-ACCESS read-write
			STATUS current
			DESCRIPTION
				"Defines the address of the server the file to install 
				is available to download from."
			::= { asMaxBsCmSwUpgradeEntry 5 }

		
		-- 1.3.6.1.4.1.989.1.16.2.1.4.2.1.6
		asMaxBsCmSwCfgVersionToBecomePrimary OBJECT-TYPE
			SYNTAX DisplayString
			MAX-ACCESS read-write
			STATUS current
			DESCRIPTION
				"Defines the version of the software to become version of image stored 
				in the primary storage (bank, file etc.). This object is used as an additional
				information for command 'swCommandSwapToPrimary'.
				If the version is not installed i.e. not reported by neither asMaxBsCmSwPrimaryVersion
				nor asMaxBsCmSwSecondaryVersion the requested operation 
				(swCommandSwapToPrimary, swCommandSwapAndResetToPrimary) should fail 
				and the relevant error code should be reported in 'asMaxBsCmSwStatusCode'."
			::= { asMaxBsCmSwUpgradeEntry 6 }

		
		-- 1.3.6.1.4.1.989.1.16.2.1.4.2.1.7
		asMaxBsCmSwStatusCode OBJECT-TYPE
			SYNTAX INTEGER
				{
				swStatusIdle(1),
				swStatusInstallInProgress(2),
				swStatusActivationInProgress(3),
				swStatusInstallFailure(4),
				swStatusActivationFailure(5)
				}
			MAX-ACCESS read-only
			STATUS current
			DESCRIPTION
				"Reported status of the operation in progress. The values 
				of this object mean:
				  swStatusIdle - no operation in progress or last requested 
				operation completed successfully
				  swStatusInstallInProgress - Install operation in progress
				  swStatusActivationInProgress - Activation operation in progress
				  swStatusInstallFailure - Install operation terminated with error
				  swStatusActivationFailure - Activation operation terminated with error where
				activation is the process defined by 3 commands: swCommandSwapToPrimary,
				swCommandResetToPrimary, swCommandSwapAndResetToPrimary
				
				"
			::= { asMaxBsCmSwUpgradeEntry 7 }

		
		-- 1.3.6.1.4.1.989.1.16.2.1.4.2.1.8
		asMaxBsCmSwStatusString OBJECT-TYPE
			SYNTAX DisplayString
			MAX-ACCESS read-only
			STATUS current
			DESCRIPTION
				"Implementation specific reporting message. If operation is 
				terminated with an error this object will report error details."
			::= { asMaxBsCmSwUpgradeEntry 8 }

		
		-- 1.3.6.1.4.1.989.1.16.2.1.4.2.1.9
		asMaxBsCmSwStatusProgress OBJECT-TYPE
			SYNTAX INTEGER (0..100)
			UNITS "%"
			MAX-ACCESS read-only
			STATUS current
			DESCRIPTION
				"The progress of the operation expressed in %. If exact 
				progress is not available the object should report:
				0% if no operation is in progress
				50% if operation is in progress
				100% when operation is complete
				The progress value can change from non zero value back 
				to zero percent only when the operation has been aborted 
				or when a new operation has been requested by setting 
				the object asdmaxSwCfgCommand.
				"
			::= { asMaxBsCmSwUpgradeEntry 9 }

		
		-- 1.3.6.1.4.1.989.1.16.2.1.4.2.1.10
		asMaxBsCmSwPrimaryVersion OBJECT-TYPE
			SYNTAX DisplayString
			MAX-ACCESS read-only
			STATUS current
			DESCRIPTION
				"The version of the software image stored in primary storage (bank, file etc).
				There is no format restriction on reported version.
				Typically the primary software image is stored in FLASH or other non-volatile
				memory."
			::= { asMaxBsCmSwUpgradeEntry 10 }

		
		-- 1.3.6.1.4.1.989.1.16.2.1.4.2.1.11
		asMaxBsCmSwPrimaryVersionDetails OBJECT-TYPE
			SYNTAX DisplayString
			MAX-ACCESS read-only
			STATUS current
			DESCRIPTION
				"The details of version of the software image stored in primary 
				storage (bank, file etc). This is implementation specific."
			::= { asMaxBsCmSwUpgradeEntry 11 }

		
		-- 1.3.6.1.4.1.989.1.16.2.1.4.2.1.12
		asMaxBsCmSwSecondaryVersion OBJECT-TYPE
			SYNTAX DisplayString
			MAX-ACCESS read-only
			STATUS current
			DESCRIPTION
				"The version of the software image stored in secondary storage (bank, file etc).
				There is no format restriction on reported version.
				Typically the secondary software image is stored in FLASH or other non-volatile
				memory."
			::= { asMaxBsCmSwUpgradeEntry 12 }

		
		-- 1.3.6.1.4.1.989.1.16.2.1.4.2.1.13
		asMaxBsCmSwSecondaryVersionDetails OBJECT-TYPE
			SYNTAX DisplayString
			MAX-ACCESS read-only
			STATUS current
			DESCRIPTION
				"The details of version of the software image stored in secondary 
				storage (bank, file etc). This is implementation specific."
			::= { asMaxBsCmSwUpgradeEntry 13 }

		
		-- 1.3.6.1.4.1.989.1.16.2.1.4.2.1.14
		asMaxBsCmSwTypeDescription OBJECT-TYPE
			SYNTAX DisplayString
			MAX-ACCESS read-only
			STATUS current
			DESCRIPTION
				"Describes the role of the software type. This object has a free text format
				and is implementation specific. The role of this object is to provide textual 
				definition of the type of the image identified by asMaxBsCmSwType code.
				"
			::= { asMaxBsCmSwUpgradeEntry 14 }

		
		-- 1.3.6.1.4.1.989.1.16.2.1.4.2.1.15
		asMaxBsCmSwRunningVersion OBJECT-TYPE
			SYNTAX DisplayString
			MAX-ACCESS read-only
			STATUS current
			DESCRIPTION
				"The version of the software the target is now running.
				There is no format restriction on reported version.
				Typically the running software is stored in RAM."
			::= { asMaxBsCmSwUpgradeEntry 15 }

		
		-- 1.3.6.1.4.1.989.1.16.2.1.4.2.1.16
		asMaxBsCmSwRunningVersionDetails OBJECT-TYPE
			SYNTAX DisplayString
			MAX-ACCESS read-only
			STATUS current
			DESCRIPTION
				"The details of version of the software the target is now running. 
				This is implementation specific."
			::= { asMaxBsCmSwUpgradeEntry 16 }

		
		-- 1.3.6.1.4.1.989.1.16.2.1.4.2.1.17
		asMaxBsCmSwServerType OBJECT-TYPE
			SYNTAX INTEGER
				{
				swServerTypeFtp(1),
				swServerTypeTftp(2)
				}
			MAX-ACCESS read-write
			STATUS current
			DESCRIPTION
				"Defines the type of file server used to install(download) file image.
				FTP server requires user name and password defined by objects 
				asMaxBsCmSwServerUserName and asMaxBsCmSwServerPassword."
			DEFVAL { swServerTypeTftp }
			::= { asMaxBsCmSwUpgradeEntry 17 }

		
		-- 1.3.6.1.4.1.989.1.16.2.1.4.2.1.18
		asMaxBsCmSwServerUserName OBJECT-TYPE
			SYNTAX DisplayString
			MAX-ACCESS read-write
			STATUS current
			DESCRIPTION
				"User name is required to open session on file servers with user authentication
				implemented like FTP."
			::= { asMaxBsCmSwUpgradeEntry 18 }

		
		-- 1.3.6.1.4.1.989.1.16.2.1.4.2.1.19
		asMaxBsCmSwServerPassword OBJECT-TYPE
			SYNTAX DisplayString
			MAX-ACCESS read-write
			STATUS current
			DESCRIPTION
				"Password is required to open session on file servers with user authentication
				implemented like FTP. The password is given for the user specified by object
				asMaxBsCmSwServerUserName."
			::= { asMaxBsCmSwUpgradeEntry 19 }

		
		-- 1.3.6.1.4.1.989.1.16.2.1.5
		asMaxBsCmVoip OBJECT IDENTIFIER ::= { asMaxBSCommon 5 }

		
		-- 1.3.6.1.4.1.989.1.16.2.1.5.1
		asMaxBsCmVoipQosTable OBJECT-TYPE
			SYNTAX SEQUENCE OF AsMaxBsCmVoipQosEntry
			MAX-ACCESS not-accessible
			STATUS current
			DESCRIPTION
				"Description."
			::= { asMaxBsCmVoip 1 }

		
		-- 1.3.6.1.4.1.989.1.16.2.1.5.1.1
		asMaxBsCmVoipQosEntry OBJECT-TYPE
			SYNTAX AsMaxBsCmVoipQosEntry
			MAX-ACCESS not-accessible
			STATUS current
			DESCRIPTION
				"Description."
			INDEX { ifIndex }
			::= { asMaxBsCmVoipQosTable 1 }

		
		AsMaxBsCmVoipQosEntry ::=
			SEQUENCE { 
				asMaxBsCmVoipServerSswIpAddressType
					InetAddressType,
				asMaxBsCmVoipServerSswIpAddress
					InetAddress,
				asMaxBsCmVoipServerListenPort
					INTEGER,
				asMaxBsCmVoipServerMaxBandwidth
					INTEGER,
				asMaxBsCmVoipServerMaxCalls
					INTEGER,
				asMaxBsCmVoipServerStorageSize
					INTEGER,
				asMaxBsCmVoipServerKeepAliveRetries
					INTEGER,
				asMaxBsCmVoipServerRestartPolicy
					INTEGER,
				asMaxBsCmVoipServerQTagEnabled
					AsmaxBooleanSwitch,
				asMaxBsCmVoipServerQTagVlanID
					AsmaxVlanIdOrNone,
				asMaxBsCmVoipServerQTagPriority
					INTEGER,
				asMaxBsCmVoipServerEnabled
					AsmaxBooleanSwitch
			 }

		-- 1.3.6.1.4.1.989.1.16.2.1.5.1.1.1
		asMaxBsCmVoipServerSswIpAddressType OBJECT-TYPE
			SYNTAX InetAddressType
			MAX-ACCESS read-write
			STATUS current
			DESCRIPTION
				"Address type specifier for asMaxBsCmVoipServerSswIpAddress."
			DEFVAL { ipv4 }
			::= { asMaxBsCmVoipQosEntry 1 }

		
		-- 1.3.6.1.4.1.989.1.16.2.1.5.1.1.2
		asMaxBsCmVoipServerSswIpAddress OBJECT-TYPE
			SYNTAX InetAddress
			MAX-ACCESS read-write
			STATUS current
			DESCRIPTION
				"IP address of Voip SSW."
			DEFVAL { "" }
			::= { asMaxBsCmVoipQosEntry 2 }

		
		-- 1.3.6.1.4.1.989.1.16.2.1.5.1.1.3
		asMaxBsCmVoipServerListenPort OBJECT-TYPE
			SYNTAX INTEGER (0..65535)
			MAX-ACCESS read-write
			STATUS current
			DESCRIPTION
				"Voip servers listen port."
			DEFVAL { 2000 }
			::= { asMaxBsCmVoipQosEntry 3 }

		
		-- 1.3.6.1.4.1.989.1.16.2.1.5.1.1.4
		asMaxBsCmVoipServerMaxBandwidth OBJECT-TYPE
			SYNTAX INTEGER (0..65535)
			UNITS "Mbps"
			MAX-ACCESS read-write
			STATUS current
			DESCRIPTION
				"maximum bandwidth available for VOIP calls"
			DEFVAL { 10 }
			::= { asMaxBsCmVoipQosEntry 4 }

		
		-- 1.3.6.1.4.1.989.1.16.2.1.5.1.1.5
		asMaxBsCmVoipServerMaxCalls OBJECT-TYPE
			SYNTAX INTEGER (0..65535)
			MAX-ACCESS read-write
			STATUS current
			DESCRIPTION
				"maximum VOIP calls handled by BS"
			DEFVAL { 500 }
			::= { asMaxBsCmVoipQosEntry 5 }

		
		-- 1.3.6.1.4.1.989.1.16.2.1.5.1.1.6
		asMaxBsCmVoipServerStorageSize OBJECT-TYPE
			SYNTAX INTEGER (0..65535)
			MAX-ACCESS read-write
			STATUS deprecated
			DESCRIPTION
				"storage size in bytes for commands unsent to the SSW"
			DEFVAL { 1024 }
			::= { asMaxBsCmVoipQosEntry 6 }

		
		-- 1.3.6.1.4.1.989.1.16.2.1.5.1.1.7
		asMaxBsCmVoipServerKeepAliveRetries OBJECT-TYPE
			SYNTAX INTEGER (0..65535)
			MAX-ACCESS read-write
			STATUS current
			DESCRIPTION
				"number of keep Alive retries to the SSW"
			DEFVAL { 3 }
			::= { asMaxBsCmVoipQosEntry 7 }

		
		-- 1.3.6.1.4.1.989.1.16.2.1.5.1.1.8
		asMaxBsCmVoipServerRestartPolicy OBJECT-TYPE
			SYNTAX INTEGER
				{
				restartPolicyKeepBandwidth(0),
				restartPolicyReleaseBandwidth(1)
				}
			MAX-ACCESS read-write
			STATUS current
			DESCRIPTION
				"When the value of the asdmaxVoipServerSswIpAddress parameter has been changed, 
				the VoIP will close the link with the SSW and send instruction 
				to the Connection manager to release all bandwidth in case if 
				asdmaxVoipServerRestartPolicy is set to  restartPolicyReleaseBandwidth. 
				If asdmaxVoipServerRestartPolicy is set to restartPolicyKeepBandwidth, 
				the release instruction will not be sent"
			DEFVAL { restartPolicyKeepBandwidth }
			::= { asMaxBsCmVoipQosEntry 8 }

		
		-- 1.3.6.1.4.1.989.1.16.2.1.5.1.1.9
		asMaxBsCmVoipServerQTagEnabled OBJECT-TYPE
			SYNTAX AsmaxBooleanSwitch
			MAX-ACCESS read-write
			STATUS current
			DESCRIPTION
				"When enabled each voip real time data of the related VoIP server shall have
				a VLAN tag inserted with VLAN ID defined by asMaxBsCmVoipServerQTagVlanID
				and VLAN priority defined by asMaxBsCmVoipServerQTagPriority."
			DEFVAL { booleanFalse }
			::= { asMaxBsCmVoipQosEntry 9 }

		
		-- 1.3.6.1.4.1.989.1.16.2.1.5.1.1.10
		asMaxBsCmVoipServerQTagVlanID OBJECT-TYPE
			SYNTAX AsmaxVlanIdOrNone
			MAX-ACCESS read-write
			STATUS current
			DESCRIPTION
				"VLAN ID of the VLAN tag inserted in the packet when packet carries
				the VoIP real time data and the tagging is enabled by the object 
				asMaxBsCmVoipServerQTagEnabled. A value of 0 should be used when 
				the tagging is disabled."
			DEFVAL { 0 }
			::= { asMaxBsCmVoipQosEntry 10 }

		
		-- 1.3.6.1.4.1.989.1.16.2.1.5.1.1.11
		asMaxBsCmVoipServerQTagPriority OBJECT-TYPE
			SYNTAX INTEGER (0..7)
			MAX-ACCESS read-write
			STATUS current
			DESCRIPTION
				"VLAN priority (as defined in 802.1Q) of the VLAN tag inserted 
				in the packet when packet carries the VoIP real time date of
				the related VoIP server and the tagging is enabled by the object 
				asMaxBsCmVoipServerQTagEnabled."
			DEFVAL { 0 }
			::= { asMaxBsCmVoipQosEntry 11 }

		
		-- 1.3.6.1.4.1.989.1.16.2.1.5.1.1.12
		asMaxBsCmVoipServerEnabled OBJECT-TYPE
			SYNTAX AsmaxBooleanSwitch
			MAX-ACCESS read-write
			STATUS current
			DESCRIPTION
				"Enables/disables the BS process resposible for VoIP service admition."
			DEFVAL { booleanTrue }
			::= { asMaxBsCmVoipQosEntry 12 }

		
	
	END

--
-- AIRSPAN-ASMAX-BS-COMMON-MIB.mib
--
