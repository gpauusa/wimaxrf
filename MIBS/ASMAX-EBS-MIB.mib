--
-- ASMAX-EBS-MIB.mib
-- MIB generated by MG-SOFT Visual MIB Builder 2010 Version 8.0  Build 400
-- Tuesday, January 03, 2012 at 14:25:21
--

    ASMAX-EBS-MIB DEFINITIONS ::= BEGIN
 
        IMPORTS
            asMaxBsCmGpsInstance, AsmaxBandwidthCode            
                FROM AIRSPAN-ASMAX-BS-COMMON-MIB            
            AsmaxBooleanSwitch            
                FROM AIRSPAN-ASMAX-COMMON-MIB            
            asMaxBS, asMaxBSHiperMax, asMaxBSPicoMax, asMaxBSDemoMax, asMaxBSSoc, 
            asMaxBsStats            
                FROM AIRSPAN-PRODUCTS-MIB            
            ifIndex, InterfaceIndex            
                FROM IF-MIB            
            InetAddressType, InetAddress            
                FROM INET-ADDRESS-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            MacAddress, DisplayString, RowStatus, TEXTUAL-CONVENTION            
                FROM SNMPv2-TC            
            wmanIf2BsSsMacAddress, wmanIf2BsOfdmaUiucIndex, wmanIf2BsOfdmaDiucIndex, WmanIf2OfdmaDcdFecCode            
                FROM WMAN-IF2-BS-MIB            
            wmanIf2fBsSfId            
                FROM WMAN-IF2F-BS-MIB;
    
    
        -- 1.3.6.1.4.1.989.1.16.2.7
        asMaxEbs MODULE-IDENTITY 
            LAST-UPDATED "201008111500Z"		-- August 11, 2010 at 15:00 GMT
            ORGANIZATION 
                "Airspan Communications Ltd"
            CONTACT-INFO 
                "kdudzins@airspan.com"
            DESCRIPTION 
                "Propriatory MIB for Airspan BS for WiMAX mobile systems.
                This modules covers BS interfaces and device configuration.
                
                ===========================================================
                Below is integrated release history from Draft 1 to Draft 56.
                Later revisions are defined in the REVISION clauses.
                ===========================================================
                 
                -- October 18, 2007 at 14:15 GMT
                Draft 1:
                - initial with extention for OFDMA burst profiles tables
                
                -- October 22, 2007 at 15:23 GMT
                Draft 2:
                - SS Capability Options added as textual convention.
                
                -- November 09, 2007 at 10:47 GMT
                Draft 3:
                - ZoneTable added.
                
                -- November 12, 2007 at 12:16 GMT
                Draft 4:
                - zone table made as read-create.
                - stcMode corrected.
                
                -- November 13, 2007 at 11:59 GMT
                Draft 5:
                - subChannelGroupMap added to SectorCfg. 
                
                -- November 16, 2007 at 10:00 GMT
                Draft 6:
                - Added DIUC and UIUC referece objects in Sector table
                
                -- November 22, 2007 at 10:06 GMT
                Draft 7:
                - Added provisioned SS extension table and object CSType
                
                -- November 23, 2007 at 16:35 GMT
                Draft 8
                - Changed syntax of asxEbsStdOfdmaDlBurstRepetitionCoding and asxEbsStdOfdmaUlBurstRepetitionCoding
                
                -- November 29, 2007 at 16:49 GMT
                Draft 9:
                - use AsmaxBooleanSwitch instead of TruthValue
                
                -- December 10, 2007 at 16:02 GMT
                Draft 10:
                - added objects: asxEbsSectorCfgBandwidth, asxEbsSectorCfgTddSplit, 
                  asxEbsSectorCfgFrameDuplex, asxEbsSectorCfgPhyType
                  
                -- December 12, 2007 at 15:30 GMT
                Draft 11
                - added object asxEbsBsFramePeriodOfdma
                
                -- December 13, 2007 at 16:29 GMT
                Draft 12:
                - changed imported MIB modules to use WMAN-IF2-BS-MIB
                
                -- December 14, 2007 at 10:24 GMT
                Draft 13:
                - added RxLevelSetpoint, RfGain and LicenseExempt columns to asxEbsSectorCfgTable
                
                -- December 17, 2007 at 12:52 GMT
                Draft 14:
                - added columns to tables asxEbsBsCfgTable and asxEbsSectorCfgTable to support
                  the Network Profile holding AAA server and ASN gateway configuration
                 
                -- December 18, 2007 at 13:19 GMT
                Draft 15:
                - Added columns to asxEbsSectorCfgTable for System Default Profile
                
                -- December 20, 2007 at 15:47 GMT
                Draft 16:
                - Corrected OIDs of all columns in asxEbsSectorCfgTable
                - Added 3 more columns to asxEbsSectorCfgTable
                
                -- January 04, 2008 at 11:11 GMT
                Draft 17:
                - Changed asxEbsSectorCfgLicenseExempt to use AsmaxBooleanSwitch
                - Removed asxEbsSectorCfgInitialBurstTtg
                - Removed asxEbsSectorCfgContentionTtg
                - Removed asxEbsSectorCfgInitialBurstSubchanWidth
                
                -- January 23, 2008 at 15:07 GMT
                Draft 18:
                - Added asxEbsSectorCfgInService
                - Added asxEbsSectorCfgAllowInsecureSs
                - Added asxEbsSectorCfgAllowPkmv1Authentication
                - Added asxEbsSectorCfgAllowPkmv2Authentication
                
                -- January 24, 2008 at 11:31 GMT
                Draft 19:
                Additional properties added to asxEbsStdZoneTable.
                
                -- January 28, 2008 at 17:45 GMT
                Draft 20;
                - added dynamic modulation thresholds to tables 
                  asxEbsStdOfdmaUlBurstProfTable and asxEbsStdOfdmaDlBurstProfTable
                - changed the table names and their objects:
                  asxEbsStdProvSsExtTable => asxEbsSsProvTable
                  asxEbsStdSsCapabilitiesTable => asxEbsSsStatTable
                - added new table asxEbsSsClassTable
                - Added Zone configuration objects and modulation configuration objects 
                  to asxEbsSsProvTable and asxEbsSsClassTable.
                - Added default classes to asxEbsSectorCfgTable:
                  asxEbsSectorCfgDefaultSsClass, asxEbsSectorCfgDefaultServiceProduct, asxEbsSectorCfgDefaultPortClass
                  
                -- January 29, 2008 at 10:07 GMT
                Draft 21
                - added asxEbsSsClassInService and asxEbsSsProvInService
                
                -- February 04, 2008 at 16:12 GMT
                Draft 22:
                - added asxEbsBsCfgResetPhy
                
                -- February 06, 2008 at 14:38 GMT
                Draft 23:
                - uiuc range corrected.
                - zoneindex range unrestricted.
                
                -- February 29, 2008 at 09:58 GMT
                Draft 24:
                - IpCfg table added.
                
                -- March 04, 2008 at 15:14 GMT
                Draft 25:
                - Added object asxEbsCfgMgmtPortIfIndex to asxEbsBsCfgTable
                
                -- March 06, 2008 at 10:59 GMT
                Draft 26:
                - Added asxEbsSectorNeighbourTable.
                
                -- March 26, 2008 at 10:40 GMT
                Draft 27:
                - Added asxEbsSectorCfgTxPower to asxEbsSectorCfgTable
                
                -- March 26, 2008 at 11:06 GMT
                Draft 28:
                - Added asxEbsBsCfgResetRequest
                
                -- March 27, 2008 at 10:16 GMT
                Draft 29:
                - Added the property: asxEbsSectorCfgAsnGatewayId
                - Added the property: asxEbsBsCfgAsnGatewayProtocolFamily
                - Added the property: asxEbsBsCfgAsnGatewayProtocolVersion
                
                -- March 27, 2008 at 18:01 GMT
                Draft 30:
                asxEbsMgmtServiceClassCfgTable added.
                
                -- March 28, 2008 at 09:07 GMT
                Draft 31:
                - Added asxEbsBsCfgClockSourceForSync
                
                -- March 28, 2008 at 15:56 GMT
                Draft 32:
                - Additional properties added to sector config.
                - Number of properties extracted and grouped together into different tables.
                
                -- April 22, 2008 at 16:20 GMT
                Draft 33:
                - asxEbsSectorCfgTxPower range and units changed
                
                -- April 22, 2008 at 16:32 GMT
                Draft 34:
                - Added new property asxEbsAsnCfgInetAddress to represebt the IPv4 or IPv6 address
                  used by the BS when talking to this sector's ASN-Gateway
                  
                -- May 08, 2008 at 17:36 GMT
                Draft 35:
                - Added ASN-GW default service class objects to asxEsvcServiceClassExtTable
                - Added achieved TX power and RF gain objects to asxEbsSectorStatusTable
                
                -- May 20, 2008 at 14:57 GMT
                Draft 36:
                - Added handover trigger table asxEbsHoTriggerTable
                
                -- May 27, 2008 at 16:14 GMT
                Draft 37:
                - Added the asxEbsSectorCfgPreambleIndex property to the SectorCfgTable
                - Added the asxEbsSectorNeighbourPreambleSubchannelIndex 
                  and asxEbsSectorNeighbourColocated properties to the SectorNeighbour table
                  
                -- June 04, 2008 at 16:14 GMT
                Draft 38:
                - Added new branches asxEbsRf and asxEbsMsm
                - Added new traps asxEbsBsOperationalStatusChangedTrap, asxEbsRfPathStatusChangedTrap, asxEbsMsmStatusChangedTrap
                - asxEbsObsaiLinkTrap and all related objects.
                - Changed syntax for AsxEbsHoTriggerId
                
                -- June 11, 2008 at 17:50 GMT
                Draft 39:
                - 1ppsFrameLockTrap added.                         
                
                -- June 12, 2008 at 11:22 GMT
                Draft 40:
                - Table asxEbsGpsCw25StatusTable added.
                - 1ppsFrameLockStatus and 1ppsClockDetected made read-only.
                
                -- June 18, 2008 at 12:24 GMT
                Draft 41:
                - GpsCw25Config table added.
                
                -- July 04, 2008 at 15:39 GMT
                Draft 42:
                - Added tables PagingGroup, PagingCycle and Paging Opportunity
                
                -- July 07, 2008 at 11:30 GMT
                Draft 43:
                - Added PagingGroupInterval,
                - removed Qos column from paging cycle,
                - modified desriptions & default values
                  for paging cycle number and paging opportunity offset
                  
                -- July 08, 2008 at 15:30 GMT
                Draft 44:
                - asxEbsPagingOpportunityOffset range changed
                
                -- July 23, 2008 at 15:30 GMT
                Draft 45:
                - AsxEbsOperationalStatus values changed to align with NBIF requirements
                
                -- August 06, 2008 at 15:13 GMT
                Draft 46:
                - Added 2 columns,asxEbsRfStatusAchivedTxPower and asxEbsRfStatusAchievedRxGain to AsxEbsRfStatusTable
                
                -- August 12, 2008 at 09:01 GMT
                Draft 47:
                - Zone Index values for SS Class and SS Prov tables changed to allow starting with
                  0 instead of 1, because the zone index is now allowed to start from 0 to match the BS implementation
                  (the use of 0 as an index throws up a warning which is ignored)
                  
                -- August 12, 2008 at 10:17 GMT
                Draft 48:
                - RfPathStatus bit field values extended to 41
                
                -- August 18, 2008 at 08:53 GMT
                Draft 49:
                - RfPathId range changed to start from 0
                
                -- August 19, 2008 at 15:10 GMT
                Draft 50:
                - Added asxEbsGpsCw25ResetGps
                
                -- August 21, 2008 at 10:34 GMT
                Draft 51:
                - 1ppsFrameLockTrapEnabled added
                
                -- September 02, 2008 at 10:34 GMT
                Draft 52:
                - RfPathStatus bit field values extended to 43 bits to align with IIB
                
                -- September 10, 2008 at 12:00 GMT
                Draft 53
                - Added objects for IIB table 17:
                  asxEbsSectorCfgSignonMaxUlSubchannels(206),
                  asxEbsSectorCfgFirstCidToPartition(211),
                  asxEbsSectorCfgNumCidsToPartition(212),
                  asxEbsSectorCfgControlledHoWaitPeriod(213),
                  asxEbsSectorCfgAutoGenerateHoCnf(214),
                  asxEbsSectorCfgT42HoRngRspTimeout(215),
                  asxEbsSectorCfgHoHysteresisMargin(218),
                  asxEbsSectorCfgHoTimeToTriggerDuration(219),
                  asxEbsSectorCfgIncludeMsTxPowerLimit(220),
                  asxEbsSectorCfgMsTxPowerLimit(221),
                  asxEbsSecurityAllowCcmAesKeyWrapEncryption(209),
                  asxEbsSecurityAllowNoEncryption(210),
                  asxEbsAsnCfgGreIpAddressType(207),
                  asxEbsAsnCfgGreIpAddress(208),
                  asxEbsAsnCfgAuthenticatorId(216),
                  asxEbsAsnCfgPcId(217)
                - Added objects for IIB table 7:
                  asxEbsBsCfgPagingMacHashLifetime(91),
                  asxEbsBsCfgPagingMacHashTransmissions(92)
                  
                -- September 17, 2008 at 12:01 GMT
                Draft 54
                - Added objects:
                  asxEbsSectorCfgDeadPeriodicRangingInterval,
                  asxEbsSectorCfgRadioConfigReportPeriod,
                  asxEbsSectorCfgMissingRadioConfigReportPeriod
                  
                -- September 19, 2008 at 14:52 GMT
                Draft 55:
                - Added asxEbsSsProvMaxUlSubchannels and asxEbsSsClassMaxUlSubchannels
                - Added NoiseMesurement items
                
                -- September 22, 2008 at 12:00 GMT
                Draft 56:
                - Added new table asxEbsRfTrapStausTable
                  Notification asxEbsRfPathStatusChangedTrap now reports objects from this table.
                  asxEbsRfPathStatusInfo deprecated."
            REVISION "200810011611Z"		-- October 01, 2008 at 16:11 GMT
            DESCRIPTION 
                "Draft 57:
                - Added: asxEbsSectorCfgEnableNormalizedCnOverride and asxEbsSectorCfgNormalizedCnOverride"
            REVISION "200810211028Z"		-- October 21, 2008 at 10:28 GMT
            DESCRIPTION 
                "Draft 58:
                - Added: asxEbsSsProvDlMatrixStyle, asxEbsSsProvFixedDlMatrixMode, asxEbsSsClassDlMatrixStyle and asxEbsSsClassFixedDlMatrixMode"
            REVISION "200810211530Z"		-- October 21, 2008 at 15:30 GMT
            DESCRIPTION 
                "Draft 59:
                - Renamed: asxEbsSsProvFixedDlMatrixMode to asxEbsSsProvFixedDlMatrix and asxEbsSsClassFixedDlMatrixMode to asxEbsSsClassFixedDlMatrix"
            REVISION "200811181041Z"		-- November 18, 2008 at 10:41 GMT
            DESCRIPTION 
                "Draft 60:
                - added rfPath status objects: asxEbsRfStatusMeasuredTxPower, asxEbsRfStatusMeasuredVswr"
            REVISION "200811211211Z"		-- November 21, 2008 at 12:11 GMT
            DESCRIPTION 
                "Draft 61:
                - added new commands to asxEbsBsCfgResetRequest
                - added table asxEbsRrmCfgTable with objects for RRM phase 2 (downlink)
                - added new objects:
                  asxEbsSectorCfgMsPeriodicRangingTimeout,
                  asxEbsSectorCfgDregCmdWaitTime,
                  asxEbsSectorCfgDregCmdNumRetries,
                  asxEbsSectorCfgTimingOffsetAdjustment,
                  asxEbsArqCfgHarqAckDelay"
            REVISION "200811241211Z"		-- November 24, 2008 at 12:11 GMT
            DESCRIPTION 
                "Draft 62:
                - added support for MSM Traps and status.
                - added asxEbsMsmPortStatusChangedTrap
                - added additional objects to the asxEbsMsmStatusTable
                - added tables asxEbsMsmCfgTable, asxEbsMsmPortCfgTable and asxEbsMsmPortStatusTable"
            REVISION "200812091211Z"		-- December 09, 2008 at 12:11 GMT
            DESCRIPTION 
                "Draft 63:
                - added new object asxEbsAsnCfgBsNetMask in asxEbsAsnCfgTable"
            REVISION "200812101248Z"		-- December 10, 2008 at 12:48 GMT
            DESCRIPTION 
                "Draft 64:
                - Added new objects:
                  asxEbsRrmCfgIncludeTxPowerReport
                  asxEbsRrmCfgTxPowerReportThreshold
                  asxEbsRrmCfgTxPowerReportInterval
                  asxEbsRrmCfgTxPowerReportAlpha
                  asxEbsRrmCfgTxPowerReportCqichThreshold
                  asxEbsRrmCfgTxPowerReportCqichInterval
                  asxEbsRrmCfgTxPowerReportCqichAlpha
                  asxEbsSectorCfgUlPermutationBase
                  asxEbsSectorCfgDlPermutationBase
                  asxEbsSectorCfgPermutationBaseSource"
            REVISION "200812101456Z"		-- December 10, 2008 at 14:56 GMT
            DESCRIPTION 
                "Draft 65:
                - Added new object: asxEbsRrmCfgUlCinrMargin
                - Changed default and range for: asxEbsRrmCfgDlPcinrThreshToReuse1
                - Changed range for: asxEbsRrmDlMcsMargin"
            REVISION "200812151706Z"		-- December 15, 2008 at 17:06 GMT
            DESCRIPTION 
                "Draft 66:
                - Added new device properties:
                  asxEbsBsCfgNoSignalCinrThreshold
                  asxEbsBsCfgRfDlPropagationDelay
                  asxEbsBsCfgRfUlPropagationDelay
                  asxEbsBsCfgAlarmThresholdLowGain
                  asxEbsBsCfgAlarmThresholdHighGain
                  asxEbsBsCfgAlarmThresholdVswr
                  asxEbsBsCfgPhyFrameIndAdvance
                  asxEbsBsCfgFrameBuildTimeLimit
                  asxEbsBsCfgFrameBuildPduLimit
                  asxEbsBsCfgDiversityMode
                  asxEbsBsCfgDegradedTxPowerReduction
                  asxEbsBsCfgPhyApiErrorThreshold
                  asxEbsBsCfgArpRetryPeriod
                  asxEbsBsCfgArpRefreshPeriod"
            REVISION "200902051248Z"		-- February 05, 2009 at 12:48 GMT
            DESCRIPTION 
                "Draft 67:
                - Added asxEbsSectorNeighbourUlPermutationBase
                - Added new bits to AsxEbsRfPathStatus
                  asxEbsRfPathStatusPaOverPower
                  asxEbsRfPathStatusTxPowerOutOfRange
                  asxEbsRfPathStatusAsnGwInhibit"
            REVISION "200902061019Z"		-- February 06, 2009 at 10:19 GMT
            DESCRIPTION 
                "Draft 68:
                - Added:
                  asxEbsSectorCfgAsnGwCommsR6Timeout
                  asxEbsSectorCfgAsnGwCommsPingTimeout
                  asxEbsSectorCfgAsnGwCommsPingFailsMax
                  asxEbsAsnGwR6CommsTrapEnabled
                  asxEbsAsnGwR6CommsStatus
                - Added trap asxEbsAsnGwR6CommsChangedTrap"
            REVISION "200902161019Z"		-- February 16, 2009 at 10:19 GMT
            DESCRIPTION 
                "Draft 69:
                - Added:
                  asxEbsStdZoneHarqEnabled"
            REVISION "200902251707Z"		-- February 25, 2009 at 17:07 GMT
            DESCRIPTION 
                "Draft 70:
                - Added:
                  asxEbsAsnCfgPcIpAddress and Type"
            REVISION "200903030940Z"		-- March 03, 2009 at 09:40 GMT
            DESCRIPTION 
                "Draft 71:
                - added asxEbsSectorCfgSnReportingBase"
            REVISION "200903041240Z"		-- March 04, 2009 at 12:40 GMT
            DESCRIPTION 
                "Draft 72:
                - added asxEbsRrmCfgExcessBwBetaVal"
            REVISION "200903051036Z"		-- March 05, 2009 at 10:36 GMT
            DESCRIPTION 
                "Draft 73:
                - added asxEbsSectorCfgInitialRangingThrottleTime"
            REVISION "200903051108Z"		-- March 05, 2009 at 11:08 GMT
            DESCRIPTION 
                "Draft 74:
                - added asxEbsSectorCfgPagingAdvertAdvance
                - added asxEbsSectorCfgAccuratePagingAdverts"
            REVISION "200903261645Z"		-- March 26, 2009 at 16:45 GMT
            DESCRIPTION 
                "Draft 75:
                - added asxEbsBsCfgPhyActivityMonitorPeriod
                - added asxEbsSectorCfgSizeOfCqichIdFieldUcd
                - added asxEbsSectorCfgUlAdaptationEfficiencyMode"
            REVISION "200904211534Z"		-- April 21, 2009 at 15:34 GMT
            DESCRIPTION 
                "Draft 76:
                asxEbsRrmCfgDlCinrAlphaLow, asxEbsRrmCfgDlCinrAlphaHigh added."
            REVISION "200905081345Z"		-- May 08, 2009 at 13:45 GMT
            DESCRIPTION 
                "Draft 77:
                - added asxEbsSectorCfgForceAsnUncontrolledHandover
                - added asxEbsSectorCfgCqichReallocationPeriod
                - added asxEbsRrmCfgMatrixBThresholdCinr"
            REVISION "200905131125Z"		-- May 13, 2009 at 11:25 GMT
            DESCRIPTION 
                "Draft 78:
                - Added asxEbsSsStatusNotificationTrapEnabled
                - Added asxBsSsRegisterTrapEnabled"
            REVISION "200906021416Z"		-- June 02, 2009 at 14:16 GMT
            DESCRIPTION 
                "Draft 79:
                - added object asxEbsSectorCfgIndefiniteCqichDuration
                - added object asxEbsRrmCfgMatrixBExtraMargin
                - added object asxEbsRrmCfgMatrixBMinMcs"
            REVISION "200906081100Z"		-- June 08, 2009 at 11:00 GMT
            DESCRIPTION 
                "Draft 80:
                - added objects for encryption licence control:
                  asxEbsBsCfgLicenceCertificate, 
                  asxEbsBsStatusActiveEncryptionMode with (AsxEbsEncryptionMode textual convention)
                  asxEbsBsStatusLicenceCertCapabilities, 
                  asxEbsBsStatusLicenceCertInvalid, 
                  asxEbsBsEncryptionLicenceCertTrapEnabled
                - added trap asxEbsBsEncryptionLicenceCertTrap"
            REVISION "200906081205Z"		-- June 08, 2009 at 12:05 GMT
            DESCRIPTION 
                "Draft 81:
                - renamed objects for encryption licence control:
                  asxEbsBsCfgLicenceCertificate to asxEbsBsCfgEncryptionLicenceCertificate, 
                  asxEbsBsStatusLicenceCertCapabilities to asxEbsBsStatusEncryptionLicenceCertCapabilities, 
                  asxEbsBsStatusLicenceCertInvalid to asxEbsBsStatusEncryptionLicenceCertInvalid, 
                - changed default value for asxEbsBsEncryptionLicenceCertTrapEnabled to true from false"
            REVISION "200906081505Z"		-- June 08, 2009 at 15:05 GMT
            DESCRIPTION 
                "Draft 82:
                - Added object asxEbsBsIndex to asxEbsBsEncryptionLicenceCertTrap
                - Changed MAX-ACCESS for asxEbsBsIndex to permit use in trap"
            REVISION "200906101100Z"		-- June 10, 2009 at 11:00 GMT
            DESCRIPTION 
                "Draft 83:
                - changed allowed values for AsxEbsEncryptionMode textual convention
                - changed allowedValues for asxEbsBsCfgAsnGatewayProtocolVersion"
            REVISION "200909021100Z"		-- September 02, 2009 at 11:00 GMT
            DESCRIPTION 
                "Draft 84:
                - added new table asxEbsBsStaticIpRouteTable"
            REVISION "200909031213Z"		-- September 03, 2009 at 12:13 GMT
            DESCRIPTION 
                "Draft 85:
                - Added objects for BS config:
                  asxEbsBsCfgRequestedMobilityMode (7:113)
                  asxEbsBsCfgFeatureLicenceCertificate (7:116)
                - Added objects for BS status:
                  asxEbsBsStatusOperationalMobilityMode (7:114)
                  asxEbsBsStatusLicencedFeatures (7:115)
                  asxEbsBsStatusFeatureLicenceCertCapabilities (7:117)
                - Added objects for sector config:
                  asxEbsSectorCfgMsHoRetransmissionTimer (17:311)
                  asxEbsSectorCfgPowerControlMode (17:312)
                  asxEbsSectorCfgNiIePeriod (17:313)
                - Added objects for ARQ/HARQ config:
                  asxEbsArqCfgHarqNumAckChannels (iib 17:315)"
            REVISION "200909151221Z"		-- September 15, 2009 at 12:21 GMT
            DESCRIPTION 
                "Draft 86:
                - added SS commands objects:
                  asxEbsSsStatDeregisterCmd
                  asxEbsSsStatDeregisterAction
                  asxEbsSsStatResetCmd"
            REVISION "200909211221Z"		-- September 21, 2009 at 12:21 GMT
            DESCRIPTION 
                "Draft 87:
                - added new trap asxEbsBsFeatureLicenceCertInvalidTrap and related objects"
            REVISION "200909221221Z"		-- September 22, 2009 at 12:21 GMT
            DESCRIPTION 
                "Draft 88:
                - added new object asxEbsBsStatusFeatureLicenceCertInvalidInfo which is included in the asxEbsBsFeatureLicenceCertInvalidTrap"
            REVISION "200909231221Z"		-- September 23, 2009 at 12:21 GMT
            DESCRIPTION 
                "Draft 89:
                - added object asxEbsBsStatusFeatureLicenceCertInvalidInfo to the actual trap definition for asxEbsBsFeatureLicenceCertInvalidTrap"
            REVISION "200910131221Z"		-- October 13, 2009 at 12:21 GMT
            DESCRIPTION 
                "Draft 90: 
                Changes to Textual Convention AsxEbsRfPathStatus
                - added new bits rfPathStatusOutOfService, rfPathStatusFrameUnlocked
                and rfPathStatusBsResetting.
                - renamed bit rfPathStatusNoDprf to rfPathStatusNoRfModule"
            REVISION "200911031221Z"		-- November 03, 2009 at 12:21 GMT
            DESCRIPTION 
                "Draft 91: 
                Added new trap asxEbsBsFeatureLicenceExpiringTrap and related objects"
            REVISION "200911091221Z"		-- November 09, 2009 at 12:21 GMT
            DESCRIPTION 
                "Draft 92: 
                Added additional rfPathStatusLowForwardPower bit to AsxEbsRfPathStatus"
            REVISION "200911091311Z"		-- November 09, 2009 at 13:11 GMT
            DESCRIPTION 
                "Draft 93:
                Added asxEbsBsNtpServerTable"
            REVISION "200912011510Z"		-- December 01, 2009 at 15:10 GMT
            DESCRIPTION 
                "Draft 94:
                - Added obejects to asxEbsSectorCfgTable:
                  asxEbsSectorCfgCarrierSenseThreshold
                  asxEbsSectorCfgCarrierSenseBackoffTime
                  asxEbsSectorCfgDisableDlMgmtHarq
                  asxEbsSectorCfgMsMaxTxPowerBackoff
                - Added objects to asxEbsBsCfgTable:
                  asxEbsBsCfgUseNtp
                  asxEbsBsCfgAaaServerAddressType"
            REVISION "200912011626Z"		-- December 01, 2009 at 16:26 GMT
            DESCRIPTION 
                "Draft 95:
                - removed incorrectly added asxEbsCfgAaaServerAddressType"
            REVISION "200912081626Z"		-- December 08, 2009 at 16:26 GMT
            DESCRIPTION 
                "Draft 96:
                - asxEbsSectorCfgCarrierSenseEnabled property added.
                - Changed description and range for asxEbsSectorCfgCarrierSenseThreshold"
            REVISION "200912211703Z"		-- December 21, 2009 at 17:03 GMT
            DESCRIPTION 
                "Draft 97:
                - Added new table asxEbsBsStaticArpTable"
            REVISION "201002041706Z"		-- February 04, 2010 at 17:06 GMT
            DESCRIPTION 
                "Draft 98:
                - Added asxEbsBsStaticArpIpAddressType object to the table asxEbsBsStaticArpTable"
            REVISION "201002081206Z"		-- February 08, 2010 at 12:06 GMT
            DESCRIPTION 
                "Draft 99:
                - Added new bit definitions rfPathStatusOnePpsInvalid and rfPathStatusLowTxIqPower to 
                  AsxEbsRfPathStatus Textual convention"
            REVISION "201002181210Z"		-- February 18, 2010 at 12:10 GMT
            DESCRIPTION 
                "Draft 100:
                - Added asxEbsTenMhzClockTrap"
            REVISION "201002261506Z"		-- February 26, 2010 at 15:06 GMT
            DESCRIPTION 
                "Draft 101:
                asxEbsRrmCfgMatrixBMaxMcs
                asxEbsSsProvDlMatrixBMaxMcs
                asxEbsSsClassDlMatrixBMaxMcs"
            REVISION "201003021506Z"		-- March 02, 2010 at 15:06 GMT
            DESCRIPTION 
                "Draft 102:
                Mapping for new Bs Feature Licence scheme
                New Textual Convention AsxEbsBsLicensedFeatures - bit field defining features subject to licensing
                New objects asxEbsBsStatusLicensedFeatures2, asxEbsBsStatusImplementedFeatures, 
                asxEbsSectorCfgRequestedLicensedFeatures, asxEbsSectorStatusOperationalLicensedFeatures, 
                plus all objects related to definition on new traps asxEbsBsFeatureNotImplementedTrap, asxEbsBsFeatureNotLicensedTrap
                Deprecated object asxEbsBsStatusLicencedFeatures"
            REVISION "201004131506Z"		-- April 13, 2010 at 15:06 GMT
            DESCRIPTION 
                "Draft 103:
                - Added new bit definitions rfPathStatusFccModeUnlicensed, rfPathStatusFccCarrierSenseInterference and 
                  rfPathStatusHighFccCarrierSenseInterference to AsxEbsRfPathStatus Textual convention.
                - Added objects asxEbsSectorCfgCarrierSenseMonitorPeriod and asxEbsSectorCfgCarrierSenseHighThresholdPercentageMuting to 
                  asxEbsSectorCfg table"
            REVISION "201006091506Z"		-- June 09, 2010 at 15:06 GMT
            DESCRIPTION 
                "Draft 104:
                - Added new bit definitions asxEbsBsLicensedFeaturesAsnGwSupport and asxEbsBsLicensedFeaturesBsOperationsSupport
                to AsxEbsBsLicensedFeatures"
            REVISION "201006151506Z"		-- June 15, 2010 at 15:06 GMT
            DESCRIPTION 
                "Draft 105:
                - Added new trap asxEbsNtpStatusChangedTrap and related objects"
            REVISION "201006211720Z"		-- June 21, 2010 at 17:20 GMT
            DESCRIPTION 
                "Draft 106:
                - Added carrier sense objects:
                  asxEbsSectorCfgCarrierSenseHysteresis
                  asxEbsSectorCfgCarrierSenseContentionTime
                  asxEbsSectorCfgCarrierSenseMeasurePeriod
                - Added RRM objects:
                  asxEbsRrmCfgDlR3PcinrThreshold
                  asxEbsRrmCfgDlMngPcinrMargin
                  asxEbsRrmCfgDlHarqErrWindowSize
                  asxEbsRrmCfgDlHarqErrFastWindowSize
                  asxEbsRrmCfgDlHarqErrLow
                  asxEbsRrmCfgDlHarqErrHigh
                  asxEbsRrmCfgDlHarqErrFastHigh
                  asxEbsRrmCfgDlHarqPurgeTimeout"
            REVISION "201006251440Z"		-- June 25, 2010 at 14:40 GMT
            DESCRIPTION 
                "Draft 107:
                - added AsxEbsRfPathStatus bit rfPathStatusFrequencyNotSet"
            REVISION "201006281730Z"		-- June 28, 2010 at 17:30 GMT
            DESCRIPTION 
                "Draft 108:
                - Deprecated asxEbsBsCfgAAAServerPassword
                - Added asxEbsBsCfgAAAServerPort
                - Added asxEbsBsCfgAAAServerMyIpAddressType and asxEbsBsCfgAAAServerMyIpAddress"
            REVISION "201006291815Z"		-- June 29, 2010 at 18:15 GMT
            DESCRIPTION 
                "Draft 109:
                - Added object asxEbsBsCfgAAAServerAccountingPort
                - Change to obsolete object asxEbsBsCfgAAAServerPassword
                - Changed units from 0.5 to 0.25 dB for objects: asxEbsRrmCfgDlR3PcinrThreshold, asxEbsRrmCfgDlMngPcinrMargin"
            REVISION "201007061450Z"		-- July 06, 2010 at 14:50 GMT
            DESCRIPTION 
                "Draft 110:
                - Added asxEbsSsProvControlMode and asxEbsSsClassControlMode"
            REVISION "201007081211Z"		-- July 08, 2010 at 12:11 GMT
            DESCRIPTION 
                "Draft 111:
                - Added AsxRfPathStatus bit asxRfPathStatusScrtIsDeaf"
            REVISION "201007141700Z"		-- July 14, 2010 at 17:00 GMT
            DESCRIPTION 
                "Draft 112:
                - Obsoleted asxEbsBsStaticArpTable
                - Created asxEbsBsStaticArp2Table"
            REVISION "201007211032Z"		-- July 21, 2010 at 10:32 GMT
            DESCRIPTION 
                "Draft 113:
                - Added asxEbsBsCfgAsnGatewayProtocolFamily wichorus and aricent."
            REVISION "201008041032Z"		-- August 04, 2010 at 10:32 GMT
            DESCRIPTION 
                "Draft 114:
                - Added asxEbsSectorCfgPrivateMapMode."
            REVISION "201008111500Z"		-- August 11, 2010 at 15:00 GMT
            DESCRIPTION 
                "Draft 115:
                - Added object asxEbsBsCfgRelayAgentCircuitId"
            REVISION "201010221149Z"		-- October 22, 2010 at 11:49 GMT
            DESCRIPTION 
                "Draft 116:
                - Added module asxEbsVoip and tables asxEbsVoipCfg and asxEbsVoipStatus."
            REVISION "201010221523Z"		-- October 22, 2010 at 15:23 GMT
            DESCRIPTION 
                "Draft 117:
                - Added asxEbsVoipCfgEnabled property to asxEbsVoipCfg table"
            REVISION "201010271142Z"		-- October 27, 2010 at 11:42 GMT
            DESCRIPTION 
                "Draft 118:
                - Added asxEbsVoipCfgServerAddressType defaults to ipv4 instead of value 1"
            REVISION "201011171541Z"		-- November 17, 2010 at 15:41 GMT
            DESCRIPTION 
                "Draft 119:
                - Added generic to asxEbsBsCfgAsnGatewayProtocolFamily"
            REVISION "201012021435Z"		-- December 02, 2010 at 14:35 GMT
            DESCRIPTION 
                "Draft 120:
                - Changes to asxEbsBsCfg table.Added asxEbxBsCfgNumberOfAntennas property and deprecated asxEbsBsCfgNumAntennas property."
            REVISION "201102171536Z"		-- February 17, 2011 at 15:36 GMT
            DESCRIPTION 
                "Draft 121:
                - Added asxEbsSsClassForceCsFromMib"
            REVISION "201103080939Z"		-- March 08, 2011 at 09:39 GMT
            DESCRIPTION 
                "Draft 122:
                - Added asxEbsBsCfgNumberOfSectors
                - Added asxEbsBsCfgRtFileLogLevel"
            REVISION "201103241020Z"		-- March 24, 2011 at 10:20 GMT
            DESCRIPTION 
                "Draft 123:
                - Added asxEbsAsnCfgSecondaryAsnGatewayIpAddress
                - Added asxEbsAsnCfgSecondaryPagingControllerIpAddress
                - Added asxEbsAsnCfgAsnGatewayRedundancyAutoResume
                - Added asxEbsAsnCfgAsnGatewayKeepAliveMethod
                - Added asxEbsAsnCfgActiveAsnGateway
                - Added asxEbsAsnCfgActiveAsnGatewayAction"
            REVISION "201103241152Z"		-- March 24, 2011 at 11:52 GMT
            DESCRIPTION 
                "Draft 124:
                - asxEbsAsnCfgAsnGatewayKeepaliveMethod default value changed to r6
                - asxEbsAsnCfgActiveAsnGateway default value changed to primary"
            REVISION "201103241354Z"		-- March 24, 2011 at 13:54 GMT
            DESCRIPTION 
                "Draft 125:
                - asxEbsAsnCfgAsnGatewayKeepaliveMethod default value changed back to disable"
            REVISION "201103291557Z"		-- March 29, 2011 at 15:57 GMT
            DESCRIPTION 
                "Draft 126:
                - asxEbsActiveAsnGwTrap added
                - asxEbsAsnGwR6CommsStatus has additional values asnR6CommsStandbyFailure and asnR6CommsUndefined"
            REVISION "201103291658Z"		-- March 29, 2011 at 16:58 GMT
            DESCRIPTION 
                "Draft 127:
                - asxEbsAsnGwR6CommsStatus enums changed"
            REVISION "201107081415Z"		-- July 08, 2011 at 14:15 GMT
            DESCRIPTION 
                "Draft 128:
                - Added asxEbsBsCfgGpsAdjustHoldoff
                - Added asxEbsBsCfgPaCurrentAlarmMinThresh
                - Added asxEbsBsCfgPaCurrentAlarmMaxThresh
                - Added asxEbsBsCfgAntMismatchAlarmThresh
                - Added asxEbsBsCfgLowFwdPwrAlarmThresh
                - Added asxEbsGpsCw25StatusSvSnr"
            REVISION "201107251400Z"		-- July 25, 2011 at 14:00 GMT
            DESCRIPTION 
                "Draft 129:
                - Added asxEbsRfStatusScrtFwdPower
                - Added asxEbsRfStatusScrtRevPower"
            REVISION "201108181112Z"		-- August 18, 2011 at 11:12 GMT
            DESCRIPTION 
                "Draft 130:
                - Added: asxEbsSectorCfgPagingAdvertMode and asxEbsSectorCfgStaticPagingAdvertInterval
                - Added: asxEbsSectorStatusCurrentPagingAdvertInterval
                - Added: asxEbsSectorMcastMemberTable"
            REVISION "201110171601Z"		-- October 17, 2011 at 16:01 GMT
            DESCRIPTION 
                "Draft 131:
                - Added: asxEbsBsCfgAaaCompatibilityMode
                "
            REVISION "201110241505Z"		-- October 24, 2011 at 15:05 GMT
            DESCRIPTION 
                "Draft 132:
                - Added asxEbsSsProvUlMatrixStyle
                - Added asxEbsSsProvFixedUlMatrix
                - Added asxEbsSsClassUlMatrixStyle
                - Added asxEbsSsClassFixedUlMatrix"
            REVISION "201110311316Z"		-- October 31, 2011 at 13:16 GMT
            DESCRIPTION 
                "Draft 133:
                - Added asxEbsSectorCfgScanScheduleEnable
                - Added asxEbsSectorCfgScanScheduleTriggerTime
                - Added asxEbsSectorCfgScanInterleavingInterval
                - Added asxEbsSectorCfgScanDuration"
            REVISION "201111141506Z"		-- November 14, 2011 at 15:06 GMT
            DESCRIPTION 
                "Draft 134:
                - Added asxEbsBsCfgAaaAcctInterimPeriod"
            REVISION "201201031232Z"		-- January 03, 2012 at 12:32 GMT
            DESCRIPTION 
                "Draft 135:
                - Added asxEbsCfgAsnGatewayKeepaliveMethod and asxEbsCfgAsnGatewayRedundancyAutoResume"
            REVISION "201201031423Z"		-- January 03, 2012 at 14:23 GMT
            DESCRIPTION 
                "Draft 136:
                - Deprecated asxEbsAsnCfgAsnGatewayRedundancyAutoResume and asxEbsAsnCfgAsnGatewayKeepaliveMethod"
            ::= { asMaxBS 7 }

        
    
--
-- Textual conventions
--
    
        AsxEbsRfPathStatus ::= TEXTUAL-CONVENTION
            STATUS current
            DESCRIPTION 
                "Identifies the status of the RF Path channel"
            SYNTAX BITS
                {
                rfPathStatusInitialisationError(0),
                rfPathStatusCalibrationFault(1),
                rfPathStatusPaOverCurrent(2),
                rfPathStatusTxOffConfigured(3),
                rfPathStatusUnknownFreqVariant(4),
                rfPathStatusTxOffTimingLoss(5),
                rfPathStatusAntennaMismatch(6),
                rfPathStatusFreqOutOfRange(7),
                rfPathStatusPaDisabled(8),
                rfPathStatusHighGainAlarm(9),
                rfPathStatusLowGainAlarm(10),
                rfPathStatusImDegradation(11),
                rfPathStatusTddSwFail(12),
                rfPathStatusRxflrAlarm(13),
                rfPathStatusApdWdtTimeOut(14),
                rfPathStatusMuFpgaPllUnlock(15),
                rfPathStatusTooLowTemperature(16),
                rfPathStatusTooHighTemperature(17),
                rfPathStatusNoRfModule(18),
                rfPathStatusMuFpgaConfigurationFail(19),
                rfPathStatusVupuBootError(20),
                rfPathStatusVupuCodeDownloadTimeOut(21),
                rfPathStatusVupuCrcError(22),
                rfPathStatusInitialDataOnEepromCrcError(23),
                rfPathStatusRfPeripheralInitialisationFail(24),
                rfPathStatusMuFpgaBootTimeOut(25),
                rfPathStatusVupuBootTimeOut(26),
                rfPathStatusPaBiasSetupTimeOut(27),
                rfPathStatusVupuVersionError(28),
                rfPathStatusInternalError(29),
                rfPathStatusChannelBandwidthOutOfRange(30),
                rfPathStatusCyclicPrefixOutOfRange(31),
                rfPathStatusFrameDuplexOutOfRange(32),
                rfPathStatusTtgOutOfRange(33),
                rfPathStatusRtgOutOfRange(34),
                rfPathStatusRfGainOutOfRange(35),
                rfPathStatusDlSubframeSizeOutOfRange(36),
                rfPathStatusUlSubframeSizeOutOfRange(37),
                rfPathStatusFramePeriodOutOfRange(38),
                rfPathStatusNumAntennasOutOfRange(39),
                rfPathStatusAlarmThresholdLowGainOutOfRange(40),
                rfPathStatusAlarmThresholdHighGainOutOfRange(41),
                rfPathStatusAlarmThresholdVswrOutOfRange(42),
                rfPathStatusPaOverPower(43),
                rfPathStatusTxPowerOutOfRange(44),
                rfPathStatusAsnGwInhibit(45),
                rfPathStatusOutOfService(46),
                rfPathStatusFrameUnlocked(47),
                rfPathStatusBsResetting(48),
                rfPathStatusLowForwardPower(49),
                rfPathStatusOnePpsInvalid(50),
                rfPathStatusLowTxIqPower(51),
                rfPathStatusFccModeUnlicensed(52),
                rfPathStatusFccCarrierSenseInterference(53),
                rfPathStatusHighFccCarrierSenseInterference(54),
                rfPathStatusFrequencyNotSet(55),
                rfPathStatusScrtIsDeaf(56)
                }

        AsxEbsSubchannelGroupMap ::= TEXTUAL-CONVENTION
            STATUS current
            DESCRIPTION 
                "Description."
            SYNTAX BITS
                {
                group0(0),
                group1(1),
                group2(2),
                group3(3),
                group4(4),
                group5(5)
                }

        AsxEbsClassName ::= TEXTUAL-CONVENTION
            STATUS current
            DESCRIPTION 
                "Type used for naming provisioning classes."
            SYNTAX OCTET STRING (SIZE (0..64))

        AsxEbsBsLicensedFeatures ::= TEXTUAL-CONVENTION
            STATUS current
            DESCRIPTION 
                "Identifies the features which are subject to licensing on the BS"
            SYNTAX BITS
                {
                asxEbsBsLicensedFeaturesReserved1(0),
                asxEbsBsLicensedFeaturesReserved2(1),
                asxEbsBsLicensedFeaturesFeatureDualMacPhy(2),
                asxEbsBsLicensedFeaturesUplink64Qam(3),
                asxEbsBsLicensedFeaturesDownlinkMimo(4),
                asxEbsBsLicensedFeaturesUplinkMimo(5),
                asxEbsBsLicensedFeaturesUplinkCsm(6),
                asxEbsBsLicensedFeaturesFractionalFrequencyReuse(7),
                asxEbsBsLicensedFeaturesExtendedRange(8),
                asxEbsBsLicensedFeaturesCarrierSense(9),
                asxEbsBsLicensedFeaturesEthernetConvSublayer(10),
                asxEbsBsLicensedFeaturesHandover(11),
                asxEbsBsLicensedFeaturesIdleMode(12),
                asxEbsBsLicensedFeaturesSleepMode(13),
                asxEbsBsLicensedFeaturesMulticastBroadcastService(14),
                asxEbsBsLicensedFeaturesStandbyAsnGwSupport(15),
                asxEbsBsLicensedFeaturesEmbeddedPacketClassification(16),
                asxEbsBsLicensedFeaturesEmbeddedRadiusClient(17),
                asxEbsBsLicensedFeaturesWholesaleMessagingSupport(18),
                asxEbsBsLicensedFeaturesAsnGwSupport(19),
                asxEbsBsLicensedFeaturesBsOperationsSupport(20)
                }

        AsxEbsSectorPrivateMapMode ::= TEXTUAL-CONVENTION
            STATUS current
            DESCRIPTION 
                "The type of compression to use on the private maps."
            SYNTAX INTEGER
                {
                asxEbsSectorPrivateMapModeRegular(0),
                asxEbsSectorPrivateMapModeCompressed(1)
                }

        AsxEbsBsIdType ::= TEXTUAL-CONVENTION
            STATUS current
            DESCRIPTION 
                "Defines the encoding of BSID. The BSID is a 6 byte number
                and follows the encoding rules of MacAddress textual
                convention, i.e. as if it were transmitted 
                least-significant bit first. The value should be displayed
                with 2 parts clearly separated by a colon e.g:
                001DFF:00003A. The most significant part is representing
                the Operator ID."
            SYNTAX OCTET STRING (SIZE (6))

        AsxEbsOperationalStatus ::= TEXTUAL-CONVENTION
            STATUS current
            DESCRIPTION 
                "The possible operational status for the basestation."
            SYNTAX INTEGER
                {
                operationalStatusNone(0),
                operationalStatusInService(1),
                operationalStatusOutOfService(2),
                operationalStatusMaintenance(3)
                }

        AsxEbsMobilityMode ::= TEXTUAL-CONVENTION
            STATUS current
            DESCRIPTION 
                "Mode of operation Fixed or Mobile. Fixed mode prevents MS from perfoming 
                handover by send Dreg instead of MOB_BSHO_RSP and Reject to Idle Mode entry.
                Survey only mode is used for test and maintenance."
            SYNTAX INTEGER
                {
                mobilityModeFixed(0),
                mobilityModeMobile(1),
                mobilityModeSurveyOnly(2)
                }

        AsxEbsEncryptionMode ::= TEXTUAL-CONVENTION
            STATUS current
            DESCRIPTION 
                "Defines the 'maximum' encryption mode that the
                BS will permit for an SS."
            SYNTAX INTEGER
                {
                encryptNone(0),
                encryptAes(1)
                }

        AsxEbsExpiryStatus ::= TEXTUAL-CONVENTION
            STATUS current
            DESCRIPTION 
                "Type used to indicate the status of the Bs feature licence expiry.
                - A value of asxEbsExpiryStatusNone(0) indicates that the licence is not close to expiry.
                            - A Value of asxEbsExpiryStatusWarning(1) indicates that the licence is close to expiry with a further property specifying the number of days remaining.
                            - A value of asxEbsExpiryStatusError(2) indicates that the licence has expired."
            SYNTAX INTEGER
                {
                asxEbsExpiryStatusNone(0),
                asxEbsExpiryStatusWarning(1),
                asxEbsExpiryStatusError(2)
                }

        AsxEbsNtpStatus ::= TEXTUAL-CONVENTION
            STATUS current
            DESCRIPTION 
                "The current state of the BS clock set as a result of NTP responses received"
            SYNTAX INTEGER
                {
                asxEbsNtpStatusNoError(0),
                asxEbsNtpStatusClockNotSet(1)
                }

        AsEbsStdRepetitionCodingType ::= TEXTUAL-CONVENTION
            STATUS current
            DESCRIPTION 
                "Repetition coding indication as used in OFDMA Phy messages e.g. UL-MAP and DL-MAP."
            REFERENCE 
                "Tables 275 and 287 in IEEE802.16e-2005 standard."
            SYNTAX INTEGER
                {
                repetitionRateNone(0),
                repetitionRate2(1),
                repetitionRate4(2),
                repetitionRate6(3)
                }

        AsxEbsZoneType ::= TEXTUAL-CONVENTION
            STATUS current
            DESCRIPTION 
                "Description."
            SYNTAX INTEGER
                {
                ofdmDl(0),
                ofdmDlStc(1),
                ofdmUl(2),
                ofdmaDlPusc(3),
                ofdmaUlPusc(4)
                }

        AsxEbsStcMode ::= TEXTUAL-CONVENTION
            STATUS current
            DESCRIPTION 
                "Description."
            SYNTAX INTEGER
                {
                none(0),
                stc2antennas(1),
                stc3antennas(2),
                stc4antennas(3),
                fhdc2antennas(4)
                }

        AsxEbsStcMatrix ::= TEXTUAL-CONVENTION
            STATUS current
            DESCRIPTION 
                "Description."
            SYNTAX INTEGER
                {
                matrixA(0),
                matrixB(1),
                matrixC(2)
                }

        AsxEbsAmcType ::= TEXTUAL-CONVENTION
            STATUS current
            DESCRIPTION 
                "Description."
            SYNTAX INTEGER
                {
                oneXsix(0),
                twoXthree(1),
                threeXtwo(2)
                }

        AsxEbsSsConfigSelStyle ::= TEXTUAL-CONVENTION
            STATUS current
            DESCRIPTION 
                "Defines the style of selection of SS config value as fixed or dynamic.
                Used for dynamic modulation, dynamic zones etc."
            SYNTAX INTEGER
                {
                selStyleDynamic(0),
                selStyleFixed(1)
                }

        CSTypes ::= TEXTUAL-CONVENTION
            STATUS current
            DESCRIPTION 
                "Convergence Sublayer types"
            SYNTAX INTEGER
                {
                packetIpV4(1),
                packetIpV6(2),
                packet802dot3Ethernet(3),
                packet802dot1QVlan(4),
                packetIpV4Over802dot3(5),
                packetIpV6Over802dot3(6),
                packetIpV4Over802dot1Q(7),
                packetIpV6Over802dot1Q(8),
                packetAtm(9),
                packetEthernetWithRohc(10),
                packetEthernetWithEcrtp(11),
                packetIpWithRohc(12),
                packetIpWithEcrtp(13)
                }

        AsxEbsMsControlMode ::= TEXTUAL-CONVENTION
            STATUS current
            DESCRIPTION 
                "Defines how the MS will be contolled and provisioned."
            SYNTAX INTEGER
                {
                msControlModeNone(1),
                msControlModeAsnGw(2),
                msControlModeAaaServer(3),
                msControlModeMibAndAsnGw(4),
                msControlModeMibOnly(5)
                }

        SsCapabilityOptions ::= TEXTUAL-CONVENTION
            STATUS current
            DESCRIPTION 
                "Description."
            SYNTAX BITS
                {
                bwAllocSupportFullDuplex(0),
                macPduAbilityPiggybackReqs(1),
                macPduAbility3BitFsn(2),
                ofdmFftSize256(3),
                ofdmFftSize2048(4),
                ofdmSsDemod64Qam(5),
                ofdmSsDemodBtc(6),
                ofdmSsDemodCtc(7),
                ofdmSsDemodStc(8),
                ofdmSsDemodAas(9),
                ofdmSsDemodSubchannelization(10),
                ofdmSsMod64Qam(11),
                ofdmSsModBtc(12),
                ofdmSsModCtc(13),
                ofdmSsModSubchannelization(14),
                ofdmSsModFocusedContentionBwReq(15),
                ofdmSsModCyclicDelay(16),
                ofdmSsFocusedContentionSupported(17),
                ofdmSsTcSupport(18),
                ofdmPrivateMapSupportRegular(19),
                ofdmPrivateMapSupportCompressed(20),
                ofdmSsUlPowerCtlOpenLoop(21),
                ofdmSsUlPowerCtlAasPreamble(22),
                ofdmaFftSize256(23),
                ofdmaFftSize2048(24),
                ofdmaFftSize128(25),
                ofdmaFftSize512(26),
                ofdmaFftSize1024(27),
                ofdmaSsDemod64Qam(28),
                ofdmaSsDemodBtc(29),
                ofdmaSsDemodCtc(30),
                ofdmaSsDemodStc(31),
                ofdmaSsDemodCcOptInterleaver(32),
                ofdmaSsDemodHarqChase(33),
                ofdmaSsDemodHarqCtcIr(34),
                ofdmaSsDemodHarqCcIr(35),
                ofdmaSsDemodLdpc(36),
                ofdmaSsDemodDedicatedPilots(37),
                ofdmaSsMod64Qam(38),
                ofdmaSsModBtc(39),
                ofdmaSsModCtc(40),
                ofdmaSsModStc(41),
                ofdmaSsModHarqChase(42),
                ofdmaSsModCtcIr(43),
                ofdmaSsModCcIr(44),
                ofdmaSsModLdpc(45),
                ofdmaSsPermSupportOptionalPusc(46),
                ofdmaSsPermSupportOptionalFusc(47),
                ofdmaSsPermSupportAmc1x6(48),
                ofdmaSsPermSupportAmc2x3(49),
                ofdmaSsPermSupportAmc3x2(50),
                ofdmaSsPermSupportAmcHarq(51),
                ofdmaSsPermSupportTusc1(52),
                ofdmaSsPermSupportTusc2(53),
                ofdmaSsDlMimo2AntMatA(54),
                ofdmaSsDlMimo2AntMatBVert(55),
                ofdmaSsDlMimo2AntMatBHorz(56),
                ofdmaSsDlMimo4AntMatA(57),
                ofdmaSsDlMimo4AntMatBVert(58),
                ofdmaSsDlMimo4AntMatBHorz(59),
                ofdmaSsDlMimo4AntMatCVert(60),
                ofdmaSsDlMimo4AntMatCHorz(61),
                ofdmaSsDemodMimo2AntMatA(62),
                ofdmaSsDemodMimo2AntMatBVert(63),
                ofdmaSsDemodMimo4RxAnt(64),
                ofdmaSsDemodMimo4AntMatA(65),
                ofdmaSsDemodMimo4AntMatBVert(66),
                ofdmaSsDemodMimo4AntMatBHorz(67),
                ofdmaSsDemodMimo4AntMatCVert(68),
                ofdmaSsDemodMimo4AntMatCHorz(69),
                ofdmaSsDemodMimo3AntMatA(70),
                ofdmaSsDemodMimo3AntMatB(71),
                ofdmaSsDemodMimo3AntMatCVert(72),
                ofdmaSsDemodMimo3AntMatCHorz(73),
                ofdmaSsDemodMimoPrecodeWtCalc(74),
                ofdmaSsDemodMimoAdapativeRateCtl(75),
                ofdmaSsDemodMimoChanMatCalc(76),
                ofdmaSsDemodMimoAntGouping(77),
                ofdmaSsDemodMimoAntSelection(78),
                ofdmaSsDemodMimoCodebookPrecode(79),
                ofdmaSsDemodMimoLongTermPrecode(80),
                ofdmaSsDemodMimoMidamble(81),
                ofdmaSsUlMimo2AntSttd(82),
                ofdmaSsDlMimo2AntSmVert(83),
                ofdmaSsDlMimo1AntCoopSm(84),
                ofdmaPrivateMapSupportHarq(85),
                ofdmaPrivateMapSupport(86),
                ofdmaPrivateMapSupportReduced(87),
                ofdmaPrivateMapSupportChainEnable(88),
                ofdmaPrivateMapSupportDlFrmOffset1(89),
                ofdmaPrivateMapSupportUlFrmOffset1(90),
                ofdmaAasCapsZone(91),
                ofdmaAasCapsDiversityMapScan(92),
                ofdmaAasCapsFbckRsp(93),
                ofdmaAasCapsDlPreamble(94),
                ofdmaAasCapsUlPreamble(95),
                ofdmaSsCinrMeasCapPhysPreamble(96),
                ofdmaSsCinrMeasCapPhysPermPilots(97),
                ofdmaSsCinrMeasCapPhysPermData(98),
                ofdmaSsCinrMeasCapEffPreamble(99),
                ofdmaSsCinrMeasCapEffPermPilots(100),
                ofdmaSsCinrMeasCapEffPermData(101),
                ofdmaSsCinrMeasCap2CqiChans(102),
                ofdmaSsCinrMeasCapFreqSel(103),
                ofdmaSsUlPowerCtlOpenLoop(104),
                ofdmaSsUlPowerCtlAasPreamble(105),
                ofdmaMapCapHarq(106),
                ofdmaMapCapExtendedHarq(107),
                ofdmaMapCapSubmapFirstZone(108),
                ofdmaMapCapSubmapOtherZones(109),
                ofdmaMapCapDlRegionDef(110),
                ofdmaUlControlChannelCap3BitMimoFf(111),
                ofdmaUlControlChannelCapEnhancedFf(112),
                ofdmaUlControlChannelCapAck(113),
                ofdmaUlControlChannelCapUepFf(114),
                ofdmaUlControlChannelCapMeasLastDlBurst(115),
                ofdmaUlControlChannelCapPriSecFf(116),
                ofdmaUlControlChannelCapDiucCqiFf(117),
                ofdmaSsCsitCapTypeA(118),
                ofdmaSsCsitCapTypeB(119),
                ofdmaSsCsitCapPowerAssignment(120),
                ofdmaSsCsitCapTypeANotP9P18(121),
                harqBurstPerFrmCapUlIncludesNonHarqBurst(122),
                ofdmaSsMimoModSupport2TxAnts(123),
                ofdmaSsMimoModSupportTxDiversity(124),
                ofdmaSsMimoModSupportSpatialMux(125),
                ofdmaSsMimoModSupportBeamForming(126),
                ofdmaSsMimoModSupportAdaptiveRateCtl(127),
                ofdmaSsMimoModSupport1Ant(128),
                ofdmaSsMimoModSupport2Ant(129),
                ofdmaDlBurstProfCapDl(130),
                ofdmaDlBurstProfCapUl(131),
                harqIncRedBuffCapDlAggregate(132),
                harqIncRedBuffCapUlAggregate(133),
                harqChaseCmbBuffCapDlAggregate(134),
                harqChaseCmbBuffCapUlAggregate(135),
                pkmVersionSupport1(136),
                pkmVersionSupport2(137),
                authPolicySupportRsaInitialEntry(138),
                authPolicySupportEapInitialEntry(139),
                authPolicySupportAuthEapInitialEntry(140),
                authPolicySupportRsaReentry(141),
                authPolicySupportEapReentry(142),
                authPolicySupportAuthEapReentry(143),
                macModeHmac(144),
                macModeCmac(145),
                macModeHmac64(146),
                macModeHmac80(147),
                macModeHmac96(148),
                powerSaveClassCapType1(149),
                powerSaveClassCapType2(150),
                powerSaveClassCapType3(151),
                extensionCapSubheader(152),
                hoTriggerMetricBsCinrMean(153),
                hoTriggerMetricMsRssiMean(154),
                hoTriggerMetricRelativeDelay(155),
                hoTriggerMetricBsRtd(156),
                associationSupportNone(157),
                associationSupportLevel0(158),
                associationSupportLevel1(159),
                associationSupportLevel2(160),
                associationSupportDirected(161),
                authPolicySupportIeee(162),
                smcSupported(163),
                ipManagedMode(164),
                handoverSupportMdhoFbssNotSupported(165),
                handoverSupportMdhoFbssDlRfCombMaps(166),
                handoverSupportMdhoDlSoftCombOneMap(167),
                handoverSupportMdhoDlSoftCombMaps(168),
                handoverSupportMdhoUpMultipleTx(169),
                mobilitySupportHandover(170),
                mobilitySupportSleepMode(171),
                mobilitySupportIdleMode(172),
                arqAckTypeSelective(173),
                arqAckTypeCumulative(174),
                arqAckTypeCumulativeWithSelective(175),
                arqAckTypeCumulativeWithBlockSequence(176),
                ipVersion4(177),
                ipVersion6(178),
                convergenceSublayerAtm(179),
                convergenceSublayerIpv4(180),
                convergenceSublayerIpv6(181),
                convergenceSublayerEthernet(182),
                convergenceSublayerVlan(183),
                convergenceSublayerEthernetIpv4(184),
                convergenceSublayerEthernetIpv6(185),
                convergenceSublayerVlanIpv4(186),
                convergenceSublayerVlanIpv6(187),
                convergenceSublayerEthernetRohc(188),
                convergenceSublayerEthernetEcrtp(189),
                convergenceSublayerIpRohc(190),
                convergenceSublayerIpEcrtp(191),
                phsSupportAtm(192),
                phsSupportPacket(193),
                arqSupport(194),
                packingSupport(195),
                extendedRtpsSupport(196),
                smcIpAllocationMethodDhcp(197),
                smcIpAllocationMethodMobileIpv4(198),
                smcIpAllocationMethodDhcpv6(199),
                smcIpAllocationMethodIpv6StatelessAuto(200),
                headerSupportBwReqAndUlTxPwrReport(201),
                headerSupportBwReqAndCinrReport(202),
                headerSupportCqichAllocReq(203),
                headerSupportPhyChanReport(204),
                headerSupportBwReqAndUlSleepCtl(205),
                headerSupportSnReport(206),
                headerSupportFeedback(207),
                headerSupportSduSn(208),
                headerSupportDlSleepCtl(209),
                headerSupportFeedbackReq(210),
                headerSupportMimoFeedback(211),
                headerSupportUlTxPwrReport(212),
                headerSupportMiniFeedback(213),
                headerSupportSnRequest(214),
                headerSupportShortPduSn(215),
                headerSupportLongPduSn(216),
                suiteNoData3DesKey(217),
                suiteDesData3DesKey(218),
                suiteNoDataRsaKey(219),
                suiteDesDataRsaKey(220),
                suiteAesDataAesKey(221),
                numberOfOptions(222)
                }

        AsxEbsCommand ::= TEXTUAL-CONVENTION
            STATUS current
            DESCRIPTION 
                "Type used to encode standard command request. 
                When set to commandDo the command is requested.
                BS should always respond to get request with value commandIdle."
            SYNTAX INTEGER
                {
                commandIdle(0),
                commandDo(1)
                }

        AsxEbsMsmStatus ::= TEXTUAL-CONVENTION
            STATUS current
            DESCRIPTION 
                "The status of the MSM as a whole."
            SYNTAX INTEGER
                {
                msmStatusOperational(0),
                msmStatusFailed(2),
                msmStatusResetting(3)
                }

        AsxEbsMsmHardwareType ::= TEXTUAL-CONVENTION
            STATUS current
            DESCRIPTION 
                "The variant of MSM hardware"
            SYNTAX INTEGER
                {
                asxEbsMsmHardwareTypeNone(0),
                asxEbsMsmHardwareTypeJapan(1),
                asxEbsMsmHardwareTypeGeneric(2),
                asxEbsMsmHardwareTypeCommon(3)
                }

        AsxEbsMsmPortOverallStatus ::= TEXTUAL-CONVENTION
            STATUS current
            DESCRIPTION 
                "Identifies the status of the RF Path channel"
            SYNTAX BITS
                {
                msmPortOverallStatusSector1PortError(0),
                msmPortOverallStatusSector2PortError(1),
                msmPortOverallStatusSector3PortError(2),
                msmPortOverallStatusSdrPortError(3),
                msmPortOverallStatus100BaseFxPortError(4),
                msmPortOverallStatus1000BaseSxPortError(5)
                }

        AsxEbsMsmPortAdminStatus ::= TEXTUAL-CONVENTION
            STATUS current
            DESCRIPTION 
                "The status of the MSM as a whole."
            SYNTAX INTEGER
                {
                asxEbsMsmPortAdminStatusUp(1),
                asxEbsMsmPortAdminStatusDown(2),
                asxEbsMsmPortAdminStatusTesting(3)
                }

        AsxEbsMsmPortOperationalStatus ::= TEXTUAL-CONVENTION
            STATUS current
            DESCRIPTION 
                "The status of the MSM as a whole."
            SYNTAX INTEGER
                {
                asxEbsMsmPortOperationalStatusUp(1),
                asxEbsMsmPortOperationalStatusDown(2),
                asxEbsMsmPortOperationalStatusTesting(3)
                }

        AsxEbsMsmPortStatusSpeed ::= TEXTUAL-CONVENTION
            STATUS current
            DESCRIPTION 
                "The status of the MSM as a whole."
            SYNTAX INTEGER
                {
                asxEbsMsmPortStatusSpeed10Mbps(0),
                asxEbsMsmPortStatusSpeed100Mbps(1),
                asxEbsMsmPortStatusSpeed1000Mbps(2)
                }

        EthernetDuplexMode ::= TEXTUAL-CONVENTION
            STATUS current
            DESCRIPTION 
                "The status of the MSM as a whole."
            SYNTAX INTEGER
                {
                ethernetDuplexModeFull(0),
                ethernetDuplexModeHalf(1)
                }

    
--
-- Node definitions
--
    
        -- 1.3.6.1.4.1.989.1.16.2.7.1
        asxEbsConformance OBJECT IDENTIFIER ::= { asMaxEbs 1 }

        
        -- 1.3.6.1.4.1.989.1.16.2.7.1.1
        asxEbsCompliance MODULE-COMPLIANCE
            STATUS current
            DESCRIPTION 
                "Description."
            MODULE -- this module
                MANDATORY-GROUPS { asxEbsObjectGroup }
            ::= { asxEbsConformance 1 }

        
        -- 1.3.6.1.4.1.989.1.16.2.7.1.2
        asxEbsObjectGroup OBJECT-GROUP
            OBJECTS { asxEbsBsOperationalStatusChangedTrapEnabled, asxEbsRfPathStatusChangedTrapEnabled, asxEbsMsmStatusChangedTrapEnabled, asxEbsObsaiLinkTrapEnabled, asxEbs1ppsFrameLockTrapEnabled, 
                asxEbsObsaiLinkStatus, asxEbsObsaiLinkStatusInfo, asxEbs1ppsFrameLockStatus, asxEbs1ppsClockDetected, asxEbsSectorCfgUsedSubchannelGroupMap, 
                asxEbsSectorCfgInitialBurstDiuc, asxEbsSectorCfgInitialRangingUiuc, asxEbsSectorCfgBwRequestUiuc, asxEbsSectorCfgSignonDiuc, asxEbsSectorCfgSignonUiuc, 
                asxEbsSectorCfgPhyType, asxEbsSectorCfgFrameDuplex, asxEbsSectorCfgTddSplit, asxEbsSectorCfgBandwidth, asxEbsSectorCfgRxLevelSetpoint, 
                asxEbsSectorCfgRfGain, asxEbsSectorCfgLicenseExempt, asxEbsSectorCfgT42MobHoIndTimeout, asxEbsSectorCfgResourceRetainTimeout, asxEbsSectorCfgT46IdleModeInitiateTimeout, 
                asxEbsSectorCfgBsMgmtResourceHoldTimeout, asxEbsSectorCfgRssiAlphaLow, asxEbsSectorCfgRssiAlphaHigh, asxEbsSectorCfgMaxUlAllocation, asxEbsSectorCfgMaxDlAllocation, 
                asxEbsSectorCfgTtg, asxEbsSectorCfgRtg, asxEbsSectorCfgSignonUlZoneIndex, asxEbsSectorCfgSignonDlZoneIndex, asxEbsSectorCfgInitialRangingAllocSize, 
                asxEbsSectorCfgRxLevelSpread, asxEbsSectorCfgRxLevelInitialRangingSpread, asxEbsSectorCfgTimingSetpoint, asxEbsSectorCfgTimingSpread, asxEbsSectorCfgUplinkFrequencyErrorSetpoint, 
                asxEbsSectorCfgUplinkFrequencyErrorSpread, asxEbsSectorCfgStrictConformance, asxEbsSectorCfgNumRangingRetries, asxEbsSectorCfgFastPeriodicRangingUpdate, asxEbsSectorCfgNumNoSignalIndsForSignoff, 
                asxEbsSectorCfgInvitedRangingRetryPeriod, asxEbsSectorCfgInitialRangingTosPerSec, asxEbsSectorCfgNumExpectedSss, asxEbsSectorCfgRegistrationTimeout, asxEbsSectorCfgDcdUcdPeriod, 
                asxEbsSectorCfgInitialRangingBurstSize, asxEbsSectorCfgBandwidthRequestTosPerSec, asxEbsSectorCfgBwReqAllocSize, asxEbsSectorCfgFastFeedbackSlotsPerSec, asxEbsSectorCfgBwReqGrantSize, 
                asxEbsSectorCfgNeighbourAdvertisementPeriod, asxEbsSectorCfgIdlePeriodicRangingInterval, asxEbsSectorCfgActivePeriodicRangingInterval, asxEbsSectorCfgT13TftpCompleteTimeout, asxEbsSectorCfgInService, 
                asxEbsSectorCfgForceSpecialUlAllocs, asxEbsSectorCfgReportRequestInterval, asxEbsSectorCfgNumNoReportsForSignoff, asxEbsSectorCfgDefaultSsClass, asxEbsSectorCfgDefaultServiceProduct, 
                asxEbsSectorCfgDefaultPortClass, asxEbsSectorCfgTxPower, asxEbsSectorCfgMsCinrAlpha, asxEbsSectorCfgDefaultAsnGwUplkServiceClass, asxEbsSectorCfgDefaultAsnGwDnlkServiceClass, 
                asxEbsSectorCfgPreambleIndex, asxEbsSectorCfgSignonMaxUlSubchannels, asxEbsBsCfgPagingMacHashLifetime, asxEbsBsCfgPagingMacHashTransmissions, asxEbsSectorCfgFirstCidToPartition, 
                asxEbsSectorCfgNumCidsToPartition, asxEbsSectorCfgControlledHoWaitPeriod, asxEbsSectorCfgAutoGenerateHoCnf, asxEbsSectorCfgT42HoRngRspTimeout, asxEbsSectorCfgHoHysteresisMargin, 
                asxEbsSectorCfgHoTimeToTriggerDuration, asxEbsSectorCfgIncludeMsTxPowerLimit, asxEbsSectorCfgMsTxPowerLimit, asxEbsSectorStatusAchievedTransmitPower, asxEbsSectorStatusAchievedRfGain, 
                asxEbsIpCfgIpAddressType, asxEbsIpCfgIpAddress, asxEbsSectorNeighbourIpAddressType, asxEbsSectorNeighbourIpAddress, asxEbsSectorNeighbourRowStatus, 
                asxEbsSectorNeighbourPreambleSubchannelIndex, asxEbsSectorNeighbourColocated, asxEbsSecuritySaChallengeTimer, asxEbsSecuritySaChallengeMaxResends, asxEbsSecurityTekLifetime, 
                asxEbsSecurityPmkChangeOverTime, asxEbsSecurityAllowInsecureSs, asxEbsSecurityAllowPkmv1Authentication, asxEbsSecurityAllowPkmv2Authentication, asxEbsAsnCfgId, 
                asxEbsAsnCfgUseAsnGateway, asxEbsAsnCfgInetAddressType, asxEbsAsnCfgInetAddress, asxEbsAsnCfgResponseTimeout, asxEbsAsnCfgRequestRetries, 
                asxEbsAsnCfgSfDsxTransactionTime, asxEbsAsnCfgBsInetAddress, asxEbsAsnCfgGreIpAddressType, asxEbsAsnCfgGreIpAddress, asxEbsAsnCfgAuthenticatorId, 
                asxEbsAsnCfgPcId, asxEbsArqT22Duration, asxEbsArqTransmitterDelay, asxEbsArqReceiverDelay, asxEbsArqMinSsReceiverDelay, 
                asxEbsArqT22RetryCount, asxEbsHoTriggerType, asxEbsHoTriggerFn, asxEbsHoTriggerMsAction, asxEbsHoTriggerTypeVal, 
                asxEbsHoTriggerAveragingDuration, asxEbsHoTriggerRowStatus, asxEbsPagingGroupInterval, asxEbsPagingGroupRowStatus, asxEbsPagingCycleNumber, 
                asxEbsPagingCycleRowStatus, asxEbsPagingOpportunityOffset, asxEbsPagingOpportunityRowStatus, asxEbsBsFramePeriodOfdma, asxEbsBsCfgAAAServerIpAddressType, 
                asxEbsBsCfgAAAServerIpAddress, asxEbsBsCfgAAAServerTimerPeriod, asxEbsBsCfgAAAServerToSsTimerPeriod, asxEbsBsCfgAAAServerSharedSecret, asxEbsBsCfgResetPhy, 
                asxEbsBsCfgMgmtPortIfIndex, asxEbsBsCfgResetRequest, asxEbsBsCfgAsnGatewayProtocolFamily, asxEbsBsCfgAsnGatewayProtocolVersion, asxEbsBsCfgClockSourceForSync, 
                asxEbsBsCfgOperationalStatus, asxEbsBsStatusOperationalStatus, asxEbsBsStatusOperationalStatusInfo, asxEbsStdOfdmaUlBurstRepetitionCoding, asxEbsStdOfdmaUlBurstProfRowStatus, 
                asxEbsStdOfdmaUlBurstMinEntryThresh, asxEbsStdOfdmaUlBurstMandatExitThresh, asxEbsStdOfdmaDlBurstRepetitionCoding, asxEbsStdOfdmaDlBurstProfRowStatus, asxEbsStdOfdmaDlBurstMinEntryThresh, 
                asxEbsStdOfdmaDlBurstMandatExitThresh, asxEbsStdReservedObject, asxEbsStdZoneType, asxEbsStdZoneUseAllSubchannels, asxEbsStdZoneMaxProportion, 
                asxEbsStdZonePermutationBase, asxEbsStdZonePrbsId, asxEbsStdZoneStcMode, asxEbsStdZoneStcMatrix, asxEbsStdZoneAmcType, 
                asxEbsStdZoneMidambles, asxEbsStdZoneMidambleBoost, asxEbsStdZoneDedicatedPilots, asxEbsStdZoneRowStatus, asxEbsStdZoneMinProportion, 
                asxEbsStdZoneStartProportion, asxEbsStdZoneHarqEnabled, asxEbsSsProvInService, asxEbsSsProvDlZoneIndex, asxEbsSsProvDlZoneSelStyle, 
                asxEbsSsProvUlZoneIndex, asxEbsSsProvUlZoneSelStyle, asxEbsSsProvDiuc, asxEbsSsProvDiucSelStyle, asxEbsSsProvUiuc, 
                asxEbsSsProvUiucSelStyle, asxEbsSsProvCSType, asxEbsSsProvRowStatus, asxEbsSsStatRequestedOptions, asxEbsSsStatGrantedOptions, 
                asxEbsSsClassInService, asxEbsSsClassDlZoneIndex, asxEbsSsClassDlZoneSelStyle, asxEbsSsClassUlZoneIndex, asxEbsSsClassUlZoneSelStyle, 
                asxEbsSsClassDiuc, asxEbsSsClassDiucSelStyle, asxEbsSsClassUiuc, asxEbsSsClassUiucSelStyle, asxEbsSsClassCSType, 
                asxEbsSsClassRowStatus, asxEbsRfPathId, asxEbsRfPaInService, asxEbsRfReset, asxEbsRfPathStatus, 
                asxEbsRfStatusAchievedTxPower, asxEbsRfStatusAchievedRxGain, asxEbsMsmPresent, asxEbsMsmStatus, asxEbsMsmStatusInfo, 
                asxEbsGpsCw25Mode, asxEbsGpsCw25LedStatus, asxEbsGpsCw25HoldoverGuaranteedStatus, asxEbsGpsCw25HoldoverDegradedStatus, asxEbsGpsCw25ModeMU, 
                asxEbsGpsCw25HoldoverGuaranteedPeriod, asxEbsGpsCw25HoldoverDegradedPeriod, asxEbsGpsCw25DegradedBehaviour, asxEbsGpsCw25ExpiredBehaviour, asxEbsSectorCfgDeadPeriodicRangingInterval, 
                asxEbsSectorCfgRadioConfigReportPeriod, asxEbsSectorCfgMissingRadioConfigReportPeriod, asxEbsSsClassMaxUlSubchannels, asxEbsSsProvMaxUlSubchannels, asxEbsSectorCfgNoiseMeasurementBandwidth, 
                asxEbsSectorCfgNoiseMeasurementTime, asxEbsSectorCfgNoiseMeasurementRate, asxEbsGpsCw25ResetGps, asxEbsSecurityAllowCcmAesKeyWrapEncryption, asxEbsSecurityAllowNoEncryption, 
                asxEbsSectorCfgEnableNormalizedCnOverride, asxEbsSectorCfgNormalizedCnOverride, asxEbsSsProvDlMatrixStyle, asxEbsSsClassDlMatrixStyle, asxEbsSsProvFixedDlMatrix, 
                asxEbsSsClassFixedDlMatrix, asxEbsRfStatusMeasuredTxPower, asxEbsRfStatusMeasuredVswr, asxEbsRrmCfgCinrAlphaLow, asxEbsRrmCfgCinrAlphaHigh, 
                asxEbsRrmCfgClpcDeadband, asxEbsRrmCfgDlCinrAlpha, asxEbsRrmCfgDlMimoMcsDown, asxEbsRrmCfgDlMimoMcsUp, asxEbsRrmCfgDlReuseMcsDown, 
                asxEbsRrmCfgDlReuseMcsUp, asxEbsRrmCfgRepReqInterval, asxEbsRrmCfgDlMcsThreshStartReuse1CinrReport, asxEbsRrmCfgDlMcsThreshStopReuse1CinrReport, asxEbsRrmCfgDlThreshHighMcsNumInReuse3, 
                asxEbsRrmCfgDlThreshLowMcsNumInReuse3, asxEbsRrmCfgDlPcinrThreshToReuse1, asxEbsRrmCfgDlMcsThreshToReuse3, asxEbsRrmCfgDlThreshLowMcsNumInReuse1, asxEbsRrmCfgDlDefaultMcs, 
                asxEbsRrmCfgDlDefaultRepetition, asxEbsRrmCfgDlPcinrMargin, asxEbsRrmCfgDlPcinrHysteresis, asxEbsRrmCfgDisableFastDlDynamicSelection, asxEbsRrmCfgDlMcsMargin, 
                asxEbsRrmCfgPreferDlPcinrReport, asxEbsArqCfgHarqAckDelay, asxEbsSectorCfgMsPeriodicRangingTimeout, asxEbsSectorCfgDregCmdWaitTime, asxEbsSectorCfgDregCmdNumRetries, 
                asxEbsSectorCfgTimingOffsetAdjustment, asxEbsRfTrapPathStatusInfo, asxEbsRfTrapPathStatus, asxEbsMsmStatusFirmwareError, asxEbsMsmStatus25HzClockError, 
                asxEbsMsmStatus50HzClockError, asxEbsMsmStatusFirmwareUpgradeRequired, asxEbsMsmStatusFpgaVersion, asxEbsMsmStatusFirmwareVersion, asxEbsMsmStatusHardwareType, 
                asxEbsMsmStatus100BaseFxTxFault, asxEbsMsmStatus100BaseFxLosError, asxEbsMsmStatus1000BaseSxLosError, asxEbsMsmStatus1000BaseSxTxFault, asxEbsMsmCfgReset, 
                asxEbsMsmCfgShutdownOpticalModule, asxEbsMsmPortAdminStatus, asxEbsMsmPortStatusPortDesc, asxEbsMsmPortStatusLinkStatus, asxEbsMsmPortStatusSpeed, 
                asxEbsMsmPortStatusDuplexMode, asxEbsMsmStatus100BaseFxOpticalModuleError, asxEbsMsmStatusOverallPortStatusInfo, asxEbsMsmPortStatusChangedTrapEnabled, asxEbsMsmStatusOverallPortStatus, 
                asxEbsRrmCfgIncludeTxPowerReport, asxEbsRrmCfgTxPowerReportThreshold, asxEbsRrmCfgTxPowerReportInterval, asxEbsRrmCfgTxPowerReportAlpha, asxEbsRrmCfgTxPowerReportCqichThreshold, 
                asxEbsRrmCfgTxPowerReportCqichInterval, asxEbsRrmCfgTxPowerReportCqichAlpha, asxEbsSectorCfgUlPermutationBase, asxEbsSectorCfgDlPermutationBase, asxEbsSectorCfgPermutationBaseSource, 
                asxEbsBsCfgNoSignalCinrThreshold, asxEbsBsCfgRfDlPropagationDelay, asxEbsBsCfgRfUlPropagationDelay, asxEbsBsCfgAlarmThresholdLowGain, asxEbsBsCfgAlarmThresholdHighGain, 
                asxEbsBsCfgAlarmThresholdVswr, asxEbsBsCfgPhyFrameIndAdvance, asxEbsBsCfgFrameBuildTimeLimit, asxEbsBsCfgFrameBuildPduLimit, asxEbsBsCfgDiversityMode, 
                asxEbsBsCfgDegradedTxPowerReduction, asxEbsBsCfgPhyApiErrorThreshold, asxEbsBsCfgArpRetryPeriod, asxEbsBsCfgArpRefreshPeriod, asxEbsSectorNeighbourUlPermutationBase, 
                asxEbsSectorCfgAsnGwCommsPingFailsMax, asxEbsSectorCfgAsnGwCommsPingTimeout, asxEbsSectorCfgAsnGwCommsR6Timeout, asxEbsMsmStatus1000BaseSxOpticalModuleError, asxEbsAsnCfgBsNetMask, 
                asxEbsAsnCfgPcIpAddress, asxEbsAsnCfgPcIpAddressType, asxEbsSectorCfgSnReportingBase, asxEbsRrmCfgExcessBwBetaVal, asxEbsSectorCfgInitialRangingThrottleTime, 
                asxEbsSectorCfgPagingAdvertAdvance, asxEbsSectorCfgAccuratePagingAdverts, asxEbsBsCfgPhyActivityMonitorPeriod, asxEbsSectorCfgUlAdaptationEfficiencyMode, asxEbsSectorCfgSizeOfCqichIdFieldUcd, 
                asxEbsRrmCfgDlCinrAlphaHigh, asxEbsRrmCfgDlCinrAlphaLow, asxEbsSectorCfgForceAsnUncontrolledHandover, asxEbsRrmCfgMatrixBThresholdCinr, asxEbsSectorCfgCqichReallocationPeriod, 
                asxEbsSsStatusNotificationTrapEnabled, asxEbsBsSsRegisterTrapEnabled, asxEbsSectorCfgIndefiniteCqichDuration, asxEbsRrmCfgMatrixBExtraMargin, asxEbsRrmCfgMatrixBMinMcs, 
                asxEbsRrmCfgUlCinrMargin, asxEbsAsnGwR6CommsTrapEnabled, asxEbsAsnGwR6CommsStatus, asxEbsBsStatusActiveEncryptionMode, asxEbsBsStatusEncryptionLicenceCertCapabilities, 
                asxEbsBsStatusEncryptionLicenceCertInvalid, asxEbsSectorCfgMsHoRetransmissionTimer, asxEbsSectorCfgPowerControlMode, asxEbsSectorCfgNiIePeriod, asxEbsArqCfgHarqNumAckChannels, 
                asxEbsBsCfgRequestedMobilityMode, asxEbsBsCfgFeatureLicenceCertificate, asxEbsBsStatusOperationalMobilityMode, asxEbsBsStatusFeatureLicenceCertCapabilities, asxEbsSsStatDeregisterCmd, 
                asxEbsSsStatDeregisterAction, asxEbsSsStatResetCmd, asxEbsBsCfgEncryptionLicenceCertificate, asxEbsBsEncryptionLicenceCertTrapEnabled, asxEbsBsIndex, 
                asxEbsBsStaticIpRouteDestIpAddress, asxEbsBsStaticIpRouteNetMask, asxEbsBsStaticIpRouteNextHop, asxEbsBsStaticIpRouteRowStatus, asxEbsBsFeatureLicenceCertTrapEnabled, 
                asxEbsBsStatusFeatureLicenceCertInvalid, asxEbsBsStatusFeatureLicenceCertInvalidInfo, asxEbsBsStatusFeatureLicenceExpiryStatus, asxEbsBsStatusFeatureLicenceExpiryDaysRemaining, asxEbsBsNtpServerIpAddressType, 
                asxEbsBsNtpServerIpAddress, asxEbsBsNtpServerRowStatus, asxEbsSectorCfgCarrierSenseThreshold, asxEbsSectorCfgCarrierSenseBackoffTime, asxEbsSectorCfgDisableDlMgmtHarq, 
                asxEbsSectorCfgMsMaxTxPowerBackoff, asxEbsBsCfgUseNtp, asxEbsTenMhzClockDetected, asxEbsTenMhzClockTrapEnabled, asxEbsRrmCfgMatrixBMaxMcs, 
                asxEbsSsProvDlMatrixBMaxMcs, asxEbsSsClassDlMatrixBMaxMcs, asxEbsBsStatusFeatureLicenceExpiryStatusInfo, asxEbsBsFeatureLicenceExpiringTrapEnabled, asxEbsSectorCfgCarrierSenseEnabled, 
                asxEbsBsStatusLicensedFeatures2, asxEbsBsStatusImplementedFeatures, asxEbsSectorCfgRequestedLicensedFeatures, asxEbsSectorStatusOperationalLicensedFeatures, asxEbsSectorStatusUnimplementedLicensedFeatures, 
                asxEbsSectorStatusUnlicensedLicensedFeatures, asxEbsBsFeatureNotImplementedTrapEnabled, asxEbsBsFeatureNotLicensedTrapEnabled, asxEbsSectorStatusUnimplementedLicensedFeaturesInfo, asxEbsSectorStatusUnlicensedLicensedFeaturesInfo, 
                asxEbsSectorCfgCarrierSenseMonitorPeriod, asxEbsSectorCfgCarrierSenseHysteresis, asxEbsSectorCfgCarrierSenseContentionTime, asxEbsSectorCfgCarrierSenseMeasurePeriod, asxEbsRrmCfgDlR3PcinrThreshold, 
                asxEbsRrmCfgDlMngPcinrMargin, asxEbsRrmCfgDlHarqErrWindowSize, asxEbsRrmCfgDlHarqErrFastWindowSize, asxEbsRrmCfgDlHarqErrLow, asxEbsRrmCfgDlHarqErrHigh, 
                asxEbsRrmCfgDlHarqErrFastHigh, asxEbsRrmCfgDlHarqPurgeTimeout, asxEbsBsCfgAAAServerPort, asxEbsBsCfgAAAServerMyIpAddressType, asxEbsBsCfgAAAServerMyIpAddress, 
                asxEbsBsCfgAAAServerAccountingPort, asxEbsSsProvControlMode, asxEbsSsClassControlMode, asxEbsBsStaticArp2RowStatus, asxEbsBsStaticArp2Mac, 
                asxEbsSectorCfgCarrierSenseHighThresholdPercentageMuting, asxEbsNtpStatusChangedTrapEnabled, asxEbsBsStatusNtpStatus, asxEbsBsCfgRelayAgentCircuitId, asxEbsVoipCfgServerAddressType, 
                asxEbsVoipCfgServerAddress, asxEbsVoipCfgMaxBandwidth, asxEbsVoipCfgMaxCalls, asxEbsVoipCfgMaxMsCalls, asxEbsVoipCfgMaxSfCalls, 
                asxEbsVoipCfgLocalTcpPort, asxEbsVoipCfgDiscoveryPort, asxEbsVoipCfgUplinkServiceClassId, asxEbsVoipCfgDownlinkServiceClassId, asxEbsVoipCfgGainPerPacket, 
                asxEbsVoipStatusUsedBandwidth, asxEbsVoipStatusUsedCalls, asxEbsVoipCfgEnabled, asxEbsBsCfgNumberOfAntennas, asxEbsSsClassForceCsFromMib, 
                asxEbsBsCfgNumberOfSectors, asxEbsBsCfgRtFileLogLevel, asxEbsAsnCfgSecondaryAsnGatewayIpAddress, asxEbsAsnCfgSecondaryPagingControllerIpAddress, asxEbsAsnCfgActiveAsnGateway, 
                asxEbsAsnCfgActiveAsnGatewayAction, asxEbsBsCfgGpsAdjustHoldoff, asxEbsBsCfgPaCurrentAlarmMinThresh, asxEbsBsCfgPaCurrentAlarmMaxThresh, asxEbsBsCfgAntMismatchAlarmThresh, 
                asxEbsBsCfgLowFwdPwrAlarmThresh, asxEbsGpsCw25StatusSvSnr, asxEbsRfStatusScrtFwdPower, asxEbsMcastMemberTransState, asxEbsMcastMemberState, 
                asxEbsMcastMemberCurAdmissionState, asxEbsMcastMemberDeleteCmd, asxEbsSectorStatusCurrentPagingAdvertInterval, asxEbsSectorCfgStaticPagingAdvertInterval, asxEbsSectorCfgPagingAdvertMode, 
                asxEbsBsCfgAaaCompatibilityMode, asxEbsSsClassUlMatrixStyle, asxEbsSsClassFixedUlMatrix, asxEbsSsProvUlMatrixStyle, asxEbsSsProvFixedUlMatrix, 
                asxEbsSectorCfgScanDuration, asxEbsSectorCfgScanInterleavingInterval, asxEbsSectorCfgScanScheduleTriggerTime, asxEbsSectorCfgScanScheduleEnable, asxEbsBsCfgAaaAcctInterimPeriod, 
                asxEbsBsCfgAsnGatewayRedundancyAutoResume, asxEbsBsCfgAsnGatewayKeepaliveMethod, asxEbsBsStatusNtpStatusInfo, asxEbsSectorCfgPrivateMapMode, asxEbsRfStatusScrtRevPower
                 }
            STATUS current
            DESCRIPTION 
                "Description."
            ::= { asxEbsConformance 2 }

        
        -- 1.3.6.1.4.1.989.1.16.2.7.1.3
        asxEbsNotificationGroup NOTIFICATION-GROUP
            NOTIFICATIONS { asxEbsBsOperationalStatusChangedTrap, asxEbsRfPathStatusChangedTrap, asxEbsMsmStatusChangedTrap, asxEbsObsaiLinkTrap, asxEbs1ppsFrameLockTrap, 
                asxEbsMsmPortStatusChangedTrap, asxEbsAsnGwR6CommsChangedTrap, asxEbsBsLicenceCertInvalidTrap, asxEbsBsFeatureLicenceCertInvalidTrap, asxEbsBsFeatureLicenceExpiringTrap, 
                asxEbsTenMhzClockTrap, asxEbsBsFeatureNotImplementedTrap, asxEbsBsFeatureNotLicensedTrap, asxEbsNtpStatusChangedTrap, asxEbsActiveAsnGwTrap
                 }
            STATUS current
            DESCRIPTION 
                "Description."
            ::= { asxEbsConformance 3 }

        
        -- 1.3.6.1.4.1.989.1.16.2.7.1.4
        asxEbsDeprecatedObjectGroup OBJECT-GROUP
            OBJECTS { asxEbsBsCfgNumAntennas, asxEbsAsnCfgAsnGatewayRedundancyAutoResume, asxEbsAsnCfgAsnGatewayKeepaliveMethod, asxEbsRfPathStatusInfo, asxEbsBsStatusLicencedFeatures
                 }
            STATUS deprecated
            DESCRIPTION 
                "Description."
            ::= { asxEbsConformance 4 }

        
        -- 1.3.6.1.4.1.989.1.16.2.7.1.5
        asxEbsObsoleteGroup OBJECT-GROUP
            OBJECTS { asxEbsBsCfgAAAServerPassword, asxEbsBsStaticArpMac, asxEbsBsStaticArpRowStatus }
            STATUS obsolete
            DESCRIPTION 
                "Description."
            ::= { asxEbsConformance 5 }

        
        -- 1.3.6.1.4.1.989.1.16.2.7.2
        asxEbsNotifications OBJECT IDENTIFIER ::= { asMaxEbs 2 }

        
        -- 1.3.6.1.4.1.989.1.16.2.7.2.0
        asxEbsTrapPrefix OBJECT IDENTIFIER ::= { asxEbsNotifications 0 }

        
        -- 1.3.6.1.4.1.989.1.16.2.7.2.0.1
        asxEbsBsOperationalStatusChangedTrap NOTIFICATION-TYPE
            OBJECTS { asxEbsBsStatusOperationalStatus, asxEbsBsStatusOperationalStatusInfo }
            STATUS current
            DESCRIPTION 
                "Signifies that BS operational status has changed."
            ::= { asxEbsTrapPrefix 1 }

        
        -- 1.3.6.1.4.1.989.1.16.2.7.2.0.2
        asxEbsRfPathStatusChangedTrap NOTIFICATION-TYPE
            OBJECTS { asxEbsRfPathId, asxEbsRfTrapPathStatus, asxEbsRfTrapPathStatusInfo }
            STATUS current
            DESCRIPTION 
                "Signifies that status of the RF path has changed due to detection of a fault or as a result of management action."
            ::= { asxEbsTrapPrefix 2 }

        
        -- 1.3.6.1.4.1.989.1.16.2.7.2.0.3
        asxEbsMsmStatusChangedTrap NOTIFICATION-TYPE
            OBJECTS { asxEbsMsmStatus, asxEbsMsmStatusInfo }
            STATUS current
            DESCRIPTION 
                "Signifies that MSM status has changed."
            ::= { asxEbsTrapPrefix 3 }

        
        -- 1.3.6.1.4.1.989.1.16.2.7.2.0.4
        asxEbsObsaiLinkTrap NOTIFICATION-TYPE
            OBJECTS { ifIndex, asxEbsObsaiLinkStatus, asxEbsObsaiLinkStatusInfo }
            STATUS current
            DESCRIPTION 
                "OBSAI link between SDR and SCRT link carry signalling and data traffic 
                has failed. If problem persists check optical cable connection.
                Default severity: Critical."
            ::= { asxEbsTrapPrefix 4 }

        
        -- 1.3.6.1.4.1.989.1.16.2.7.2.0.5
        asxEbs1ppsFrameLockTrap NOTIFICATION-TYPE
            OBJECTS { ifIndex, asxEbs1ppsFrameLockStatus, asxEbs1ppsClockDetected }
            STATUS current
            DESCRIPTION 
                "Trap Signifies that BS has lost/recovered timing lock with external (GPS) timing source. 
                "
            ::= { asxEbsTrapPrefix 5 }

        
        -- 1.3.6.1.4.1.989.1.16.2.7.2.0.6
        asxEbsMsmPortStatusChangedTrap NOTIFICATION-TYPE
            OBJECTS { asxEbsMsmStatusOverallPortStatus, asxEbsMsmStatusOverallPortStatusInfo }
            STATUS current
            DESCRIPTION 
                "Signifies that MSM port status has changed."
            ::= { asxEbsTrapPrefix 6 }

        
        -- 1.3.6.1.4.1.989.1.16.2.7.2.0.7
        asxEbsAsnGwR6CommsChangedTrap NOTIFICATION-TYPE
            OBJECTS { ifIndex, asxEbsAsnGwR6CommsStatus }
            STATUS current
            DESCRIPTION 
                "Trap Signifies that BS has lost/recovered comms with ASN-GW over R6. 
                "
            ::= { asxEbsTrapPrefix 7 }

        
        -- 1.3.6.1.4.1.989.1.16.2.7.2.0.8
        asxEbsBsLicenceCertInvalidTrap NOTIFICATION-TYPE
            OBJECTS { asxEbsBsIndex, asxEbsBsStatusEncryptionLicenceCertInvalid }
            STATUS current
            DESCRIPTION 
                "Trap sent to indicate a change of the BS licence certification validity state.
                i.e. sent when the invalid certificate was first decoded (alarm raised)
                and when valid certificate replaced invalid one (clear).
                The licence here is used for encryption features only."
            ::= { asxEbsTrapPrefix 8 }

        
        -- 1.3.6.1.4.1.989.1.16.2.7.2.0.9
        asxEbsBsFeatureLicenceCertInvalidTrap NOTIFICATION-TYPE
            OBJECTS { asxEbsBsIndex, asxEbsBsStatusFeatureLicenceCertInvalid, asxEbsBsStatusFeatureLicenceCertInvalidInfo }
            STATUS current
            DESCRIPTION 
                "Trap sent to indicate a change of the BS feature licence certification validity state.
                i.e. sent when the invalid certificate was first decoded (alarm raised)
                and when valid certificate replaced invalid one (clear).
                The licence here is used for all general BS features subject to licensing with the exception of encryption."
            ::= { asxEbsTrapPrefix 9 }

        
        -- 1.3.6.1.4.1.989.1.16.2.7.2.0.10
        asxEbsBsFeatureLicenceExpiringTrap NOTIFICATION-TYPE
            OBJECTS { asxEbsBsIndex, asxEbsBsStatusFeatureLicenceExpiryStatus, asxEbsBsStatusFeatureLicenceExpiryDaysRemaining, asxEbsBsStatusFeatureLicenceExpiryStatusInfo }
            STATUS current
            DESCRIPTION 
                "Trap sent to indicate that the BS feature licence certificate is starting to expire or has expired.
                The supplied objects specify the status of the expiry trap - NoError, Warning or Error and the number of 
                days remaining until expiry.
                The BS must send a trap with status NoError on the successful application of a new valid Feature Licence"
            ::= { asxEbsTrapPrefix 10 }

        
        -- 1.3.6.1.4.1.989.1.16.2.7.2.0.11
        asxEbsTenMhzClockTrap NOTIFICATION-TYPE
            OBJECTS { ifIndex, asxEbsTenMhzClockDetected }
            STATUS current
            DESCRIPTION 
                "Trap signifying that BS has detected/not detected 10MHz signal
                from external (GPS) timing source. 
                "
            ::= { asxEbsTrapPrefix 11 }

        
        -- 1.3.6.1.4.1.989.1.16.2.7.2.0.12
        asxEbsBsFeatureNotImplementedTrap NOTIFICATION-TYPE
            OBJECTS { ifIndex, asxEbsSectorStatusUnimplementedLicensedFeatures, asxEbsSectorStatusUnimplementedLicensedFeaturesInfo }
            STATUS current
            DESCRIPTION 
                "Trap signifying that BS has detected a request for a feature subject to licensing on this BS TRx that is not
                implemented on the BS."
            ::= { asxEbsTrapPrefix 12 }

        
        -- 1.3.6.1.4.1.989.1.16.2.7.2.0.13
        asxEbsBsFeatureNotLicensedTrap NOTIFICATION-TYPE
            OBJECTS { ifIndex, asxEbsSectorStatusUnlicensedLicensedFeatures, asxEbsSectorStatusUnlicensedLicensedFeaturesInfo }
            STATUS current
            DESCRIPTION 
                "Trap signifying that BS has detected a request for a feature subject to licensing on this BS TRx that is not
                licensed on the BS."
            ::= { asxEbsTrapPrefix 13 }

        
        -- 1.3.6.1.4.1.989.1.16.2.7.2.0.14
        asxEbsNtpStatusChangedTrap NOTIFICATION-TYPE
            OBJECTS { asxEbsBsStatusNtpStatus, asxEbsBsStatusNtpStatusInfo }
            STATUS current
            DESCRIPTION 
                "Trap signifying a change in the status of the BS clock deduced from NTP responses."
            ::= { asxEbsTrapPrefix 14 }

        
        -- 1.3.6.1.4.1.989.1.16.2.7.2.0.15
        asxEbsActiveAsnGwTrap NOTIFICATION-TYPE
            OBJECTS { ifIndex, asxEbsAsnCfgActiveAsnGateway, asxEbsAsnCfgActiveAsnGatewayAction }
            STATUS current
            DESCRIPTION 
                "Description."
            ::= { asxEbsTrapPrefix 15 }

        
        -- 1.3.6.1.4.1.989.1.16.2.7.2.1
        asxEbsTrapControlTable OBJECT-TYPE
            SYNTAX SEQUENCE OF AsxEbsTrapControlEntry
            MAX-ACCESS not-accessible
            STATUS current
            DESCRIPTION
                "Defines enabled/disabled controls for each traps independently. 
                The traps are enabled/disabled simulanously across the whole all sectors of BS."
            ::= { asxEbsNotifications 1 }

        
        -- 1.3.6.1.4.1.989.1.16.2.7.2.1.1
        asxEbsTrapControlEntry OBJECT-TYPE
            SYNTAX AsxEbsTrapControlEntry
            MAX-ACCESS not-accessible
            STATUS current
            DESCRIPTION
                "Single row."
            INDEX { asxEbsTrapControlIndex }
            ::= { asxEbsTrapControlTable 1 }

        
        AsxEbsTrapControlEntry ::=
            SEQUENCE { 
                asxEbsTrapControlIndex
                    INTEGER,
                asxEbsBsOperationalStatusChangedTrapEnabled
                    AsmaxBooleanSwitch,
                asxEbsRfPathStatusChangedTrapEnabled
                    AsmaxBooleanSwitch,
                asxEbsMsmStatusChangedTrapEnabled
                    AsmaxBooleanSwitch,
                asxEbsObsaiLinkTrapEnabled
                    AsmaxBooleanSwitch,
                asxEbs1ppsFrameLockTrapEnabled
                    AsmaxBooleanSwitch,
                asxEbsMsmPortStatusChangedTrapEnabled
                    AsmaxBooleanSwitch,
                asxEbsAsnGwR6CommsTrapEnabled
                    AsmaxBooleanSwitch,
                asxEbsSsStatusNotificationTrapEnabled
                    AsmaxBooleanSwitch,
                asxEbsBsSsRegisterTrapEnabled
                    AsmaxBooleanSwitch,
                asxEbsBsEncryptionLicenceCertTrapEnabled
                    AsmaxBooleanSwitch,
                asxEbsBsFeatureLicenceCertTrapEnabled
                    AsmaxBooleanSwitch,
                asxEbsBsFeatureLicenceExpiringTrapEnabled
                    AsmaxBooleanSwitch,
                asxEbsTenMhzClockTrapEnabled
                    AsmaxBooleanSwitch,
                asxEbsBsFeatureNotImplementedTrapEnabled
                    AsmaxBooleanSwitch,
                asxEbsBsFeatureNotLicensedTrapEnabled
                    AsmaxBooleanSwitch,
                asxEbsNtpStatusChangedTrapEnabled
                    AsmaxBooleanSwitch
             }

        -- 1.3.6.1.4.1.989.1.16.2.7.2.1.1.1
        asxEbsTrapControlIndex OBJECT-TYPE
            SYNTAX INTEGER (1)
            MAX-ACCESS not-accessible
            STATUS current
            DESCRIPTION
                "Arbitrary index - one row only."
            ::= { asxEbsTrapControlEntry 1 }

        
        -- 1.3.6.1.4.1.989.1.16.2.7.2.1.1.2
        asxEbsBsOperationalStatusChangedTrapEnabled OBJECT-TYPE
            SYNTAX AsmaxBooleanSwitch
            MAX-ACCESS read-write
            STATUS current
            DESCRIPTION
                "Enables/disables RfPathFaultTrap"
            DEFVAL { booleanTrue }
            ::= { asxEbsTrapControlEntry 2 }

        
        -- 1.3.6.1.4.1.989.1.16.2.7.2.1.1.3
        asxEbsRfPathStatusChangedTrapEnabled OBJECT-TYPE
            SYNTAX AsmaxBooleanSwitch
            MAX-ACCESS read-write
            STATUS current
            DESCRIPTION
                "Enables/disables RfPathFaultTrap"
            DEFVAL { booleanTrue }
            ::= { asxEbsTrapControlEntry 3 }

        
        -- 1.3.6.1.4.1.989.1.16.2.7.2.1.1.4
        asxEbsMsmStatusChangedTrapEnabled OBJECT-TYPE
            SYNTAX AsmaxBooleanSwitch
            MAX-ACCESS read-write
            STATUS current
            DESCRIPTION
                "Enables/disables MsmStatusChanngedTrap"
            DEFVAL { booleanTrue }
            ::= { asxEbsTrapControlEntry 4 }

        
        -- 1.3.6.1.4.1.989.1.16.2.7.2.1.1.5
        asxEbsObsaiLinkTrapEnabled OBJECT-TYPE
            SYNTAX AsmaxBooleanSwitch
            MAX-ACCESS read-write
            STATUS current
            DESCRIPTION
                "Enables/disables ObsaiLinkTrap"
            DEFVAL { booleanTrue }
            ::= { asxEbsTrapControlEntry 5 }

        
        -- 1.3.6.1.4.1.989.1.16.2.7.2.1.1.6
        asxEbs1ppsFrameLockTrapEnabled OBJECT-TYPE
            SYNTAX AsmaxBooleanSwitch
            MAX-ACCESS read-write
            STATUS current
            DESCRIPTION
                "Enables/disables 1ppsFrameLockTrap"
            DEFVAL { booleanTrue }
            ::= { asxEbsTrapControlEntry 6 }

        
        -- 1.3.6.1.4.1.989.1.16.2.7.2.1.1.7
        asxEbsMsmPortStatusChangedTrapEnabled OBJECT-TYPE
            SYNTAX AsmaxBooleanSwitch
            MAX-ACCESS read-write
            STATUS current
            DESCRIPTION
                "Enables/disables MsmPortStatusChangedTrap"
            DEFVAL { booleanTrue }
            ::= { asxEbsTrapControlEntry 7 }

        
        -- 1.3.6.1.4.1.989.1.16.2.7.2.1.1.8
        asxEbsAsnGwR6CommsTrapEnabled OBJECT-TYPE
            SYNTAX AsmaxBooleanSwitch
            MAX-ACCESS read-write
            STATUS current
            DESCRIPTION
                "ASN GW PING RF inhibit trap control."
            DEFVAL { booleanTrue }
            ::= { asxEbsTrapControlEntry 8 }

        
        -- 1.3.6.1.4.1.989.1.16.2.7.2.1.1.9
        asxEbsSsStatusNotificationTrapEnabled OBJECT-TYPE
            SYNTAX AsmaxBooleanSwitch
            MAX-ACCESS read-write
            STATUS current
            DESCRIPTION
                "Trap control for ssStatusNotificationTrap trap."
            DEFVAL { booleanFalse }
            ::= { asxEbsTrapControlEntry 9 }

        
        -- 1.3.6.1.4.1.989.1.16.2.7.2.1.1.10
        asxEbsBsSsRegisterTrapEnabled OBJECT-TYPE
            SYNTAX AsmaxBooleanSwitch
            MAX-ACCESS read-write
            STATUS current
            DESCRIPTION
                "Trap control for bsSsRegisterTrap trap."
            DEFVAL { booleanFalse }
            ::= { asxEbsTrapControlEntry 10 }

        
        -- 1.3.6.1.4.1.989.1.16.2.7.2.1.1.11
        asxEbsBsEncryptionLicenceCertTrapEnabled OBJECT-TYPE
            SYNTAX AsmaxBooleanSwitch
            MAX-ACCESS read-write
            STATUS current
            DESCRIPTION
                "Trap control for asxEbsBsLicenceCertInvalidTrap trap."
            DEFVAL { booleanTrue }
            ::= { asxEbsTrapControlEntry 11 }

        
        -- 1.3.6.1.4.1.989.1.16.2.7.2.1.1.12
        asxEbsBsFeatureLicenceCertTrapEnabled OBJECT-TYPE
            SYNTAX AsmaxBooleanSwitch
            MAX-ACCESS read-write
            STATUS current
            DESCRIPTION
                "Trap control for asxEbsBsFeatureLicenceCertInvalidTrap trap."
            DEFVAL { booleanTrue }
            ::= { asxEbsTrapControlEntry 12 }

        
        -- 1.3.6.1.4.1.989.1.16.2.7.2.1.1.13
        asxEbsBsFeatureLicenceExpiringTrapEnabled OBJECT-TYPE
            SYNTAX AsmaxBooleanSwitch
            MAX-ACCESS read-write
            STATUS current
            DESCRIPTION
                "Trap control for asxEbsBsFeatureLicenceExpiringTrap trap."
            DEFVAL { booleanTrue }
            ::= { asxEbsTrapControlEntry 13 }

        
        -- 1.3.6.1.4.1.989.1.16.2.7.2.1.1.14
        asxEbsTenMhzClockTrapEnabled OBJECT-TYPE
            SYNTAX AsmaxBooleanSwitch
            MAX-ACCESS read-write
            STATUS current
            DESCRIPTION
                "Enables/disables GpsTenMhzClockTrap"
            DEFVAL { booleanTrue }
            ::= { asxEbsTrapControlEntry 14 }

        
        -- 1.3.6.1.4.1.989.1.16.2.7.2.1.1.15
        asxEbsBsFeatureNotImplementedTrapEnabled OBJECT-TYPE
            SYNTAX AsmaxBooleanSwitch
            MAX-ACCESS read-write
            STATUS current
            DESCRIPTION
                "Enables/disables asxEbsFeatureNotImplemented Trap"
            DEFVAL { booleanTrue }
            ::= { asxEbsTrapControlEntry 15 }

        
        -- 1.3.6.1.4.1.989.1.16.2.7.2.1.1.16
        asxEbsBsFeatureNotLicensedTrapEnabled OBJECT-TYPE
            SYNTAX AsmaxBooleanSwitch
            MAX-ACCESS read-write
            STATUS current
            DESCRIPTION
                "Enables/disables asxEbsFeatureNotLicensed Trap"
            DEFVAL { booleanTrue }
            ::= { asxEbsTrapControlEntry 16 }

        
        -- 1.3.6.1.4.1.989.1.16.2.7.2.1.1.17
        asxEbsNtpStatusChangedTrapEnabled OBJECT-TYPE
            SYNTAX AsmaxBooleanSwitch
            MAX-ACCESS read-write
            STATUS current
            DESCRIPTION
                "Enables/disables asxEbsNtpStatusChanged Trap"
            DEFVAL { booleanTrue }
            ::= { asxEbsTrapControlEntry 17 }

        
        -- 1.3.6.1.4.1.989.1.16.2.7.2.2
        asxEbsIfTrapStatusTable OBJECT-TYPE
            SYNTAX SEQUENCE OF AsxEbsIfTrapStatusEntry
            MAX-ACCESS not-accessible
            STATUS current
            DESCRIPTION
                "Reports current status of objects associated with traps that are per ifIndex."
            ::= { asxEbsNotifications 2 }

        
        -- 1.3.6.1.4.1.989.1.16.2.7.2.2.1
        asxEbsIfTrapStatusEntry OBJECT-TYPE
            SYNTAX AsxEbsIfTrapStatusEntry
            MAX-ACCESS not-accessible
            STATUS current
            DESCRIPTION
                "One row per BS sector."
            INDEX { ifIndex }
            ::= { asxEbsIfTrapStatusTable 1 }

        
        AsxEbsIfTrapStatusEntry ::=
            SEQUENCE { 
                asxEbsObsaiLinkStatus
                    INTEGER,
                asxEbsObsaiLinkStatusInfo
                    DisplayString,
                asxEbs1ppsFrameLockStatus
                    INTEGER,
                asxEbs1ppsClockDetected
                    INTEGER,
                asxEbsAsnGwR6CommsStatus
                    INTEGER,
                asxEbsTenMhzClockDetected
                    INTEGER
             }

        -- 1.3.6.1.4.1.989.1.16.2.7.2.2.1.1
        asxEbsObsaiLinkStatus OBJECT-TYPE
            SYNTAX INTEGER
                {
                obsaiAllLinksOk(0),
                obsaiPartialFailure(1),
                obsaiAllLinksFailed(2)
                }
            MAX-ACCESS read-only
            STATUS current
            DESCRIPTION
                "Indicates the current state of the OBSAI links to the SCRTS as
                seen by the SDR.
                The trap can only be raised after a time of 60 seconds has elapsed after 
                power up/reset of BS to allow for startup process."
            ::= { asxEbsIfTrapStatusEntry 1 }

        
        -- 1.3.6.1.4.1.989.1.16.2.7.2.2.1.2
        asxEbsObsaiLinkStatusInfo OBJECT-TYPE
            SYNTAX DisplayString
            MAX-ACCESS read-only
            STATUS current
            DESCRIPTION
                "Provide additional textual information as in following examples:
                'OBSAI links Failed=None'
                'OBSAI links Failed=Link0'
                'OBSAI links Failed=Link0,Link1'"
            ::= { asxEbsIfTrapStatusEntry 2 }

        
        -- 1.3.6.1.4.1.989.1.16.2.7.2.2.1.3
        asxEbs1ppsFrameLockStatus OBJECT-TYPE
            SYNTAX INTEGER
                {
                lockedToGps1pps(0),
                notLockedToGps1pps(1)
                }
            MAX-ACCESS read-only
            STATUS current
            DESCRIPTION
                "Indicates current status of timing frame lock."
            ::= { asxEbsIfTrapStatusEntry 3 }

        
        -- 1.3.6.1.4.1.989.1.16.2.7.2.2.1.4
        asxEbs1ppsClockDetected OBJECT-TYPE
            SYNTAX INTEGER
                {
                notDetected1ppsClock(0),
                detected1ppsClock(1)
                }
            MAX-ACCESS read-only
            STATUS current
            DESCRIPTION
                "Indicates presence of external 1pps clock."
            ::= { asxEbsIfTrapStatusEntry 4 }

        
        -- 1.3.6.1.4.1.989.1.16.2.7.2.2.1.5
        asxEbsAsnGwR6CommsStatus OBJECT-TYPE
            SYNTAX INTEGER
                {
                asnR6CommsOk(0),
                asnR6CommsFailure(1),
                asnR6CommsSecondryFailure(2),
                asnR6CommsPrimaryFailure(3),
                asnR6CommsUndefined(4)
                }
            MAX-ACCESS read-only
            STATUS current
            DESCRIPTION
                "ASN GW PING RF inhibit status."
            DEFVAL { asnR6CommsOk }
            ::= { asxEbsIfTrapStatusEntry 5 }

        
        -- 1.3.6.1.4.1.989.1.16.2.7.2.2.1.6
        asxEbsTenMhzClockDetected OBJECT-TYPE
            SYNTAX INTEGER
                {
                notDetectedTenMhzClock(0),
                detectedTenMhzClock(1)
                }
            MAX-ACCESS read-only
            STATUS current
            DESCRIPTION
                "Indicates presence of external 10MHz clock."
            ::= { asxEbsIfTrapStatusEntry 6 }

        
        -- 1.3.6.1.4.1.989.1.16.2.7.2.3
        asxEbsRfTrapStatusTable OBJECT-TYPE
            SYNTAX SEQUENCE OF AsxEbsRfTrapStatusEntry
            MAX-ACCESS not-accessible
            STATUS current
            DESCRIPTION
                "Reports current status of objects associated with traps that are per RfPath."
            ::= { asxEbsNotifications 3 }

        
        -- 1.3.6.1.4.1.989.1.16.2.7.2.3.1
        asxEbsRfTrapStatusEntry OBJECT-TYPE
            SYNTAX AsxEbsRfTrapStatusEntry
            MAX-ACCESS not-accessible
            STATUS current
            DESCRIPTION
                "One row per BS RF Path."
            INDEX { asxEbsRfPathId }
            ::= { asxEbsRfTrapStatusTable 1 }

        
        AsxEbsRfTrapStatusEntry ::=
            SEQUENCE { 
                asxEbsRfTrapPathStatus
                    AsxEbsRfPathStatus,
                asxEbsRfTrapPathStatusInfo
                    DisplayString
             }

        -- 1.3.6.1.4.1.989.1.16.2.7.2.3.1.1
        asxEbsRfTrapPathStatus OBJECT-TYPE
            SYNTAX AsxEbsRfPathStatus
            MAX-ACCESS read-only
            STATUS current
            DESCRIPTION
                "Reports current status of RF Path."
            ::= { asxEbsRfTrapStatusEntry 1 }

        
        -- 1.3.6.1.4.1.989.1.16.2.7.2.3.1.2
        asxEbsRfTrapPathStatusInfo OBJECT-TYPE
            SYNTAX DisplayString
            MAX-ACCESS read-only
            STATUS current
            DESCRIPTION
                "Indicates any problem in text. Where practical multiple faults 
                can be indicated by a comma separated list"
            ::= { asxEbsRfTrapStatusEntry 2 }

        
        -- 1.3.6.1.4.1.989.1.16.2.7.3
        asxEbsIf OBJECT IDENTIFIER ::= { asMaxEbs 3 }

        
        -- 1.3.6.1.4.1.989.1.16.2.7.3.1
        asxEbsSectorCfgTable OBJECT-TYPE
            SYNTAX SEQUENCE OF AsxEbsSectorCfgEntry
            MAX-ACCESS not-accessible
            STATUS current
            DESCRIPTION
                "Description."
            ::= { asxEbsIf 1 }

        
        -- 1.3.6.1.4.1.989.1.16.2.7.3.1.1
        asxEbsSectorCfgEntry OBJECT-TYPE
            SYNTAX AsxEbsSectorCfgEntry
            MAX-ACCESS not-accessible
            STATUS current
            DESCRIPTION
                "Description."
            INDEX { ifIndex }
            ::= { asxEbsSectorCfgTable 1 }

        
        AsxEbsSectorCfgEntry ::=
            SEQUENCE { 
                asxEbsSectorCfgUsedSubchannelGroupMap
                    AsxEbsSubchannelGroupMap,
                asxEbsSectorCfgInitialBurstDiuc
                    Integer32,
                asxEbsSectorCfgInitialRangingUiuc
                    Integer32,
                asxEbsSectorCfgBwRequestUiuc
                    Integer32,
                asxEbsSectorCfgSignonDiuc
                    Integer32,
                asxEbsSectorCfgSignonUiuc
                    Integer32,
                asxEbsSectorCfgPhyType
                    INTEGER,
                asxEbsSectorCfgFrameDuplex
                    INTEGER,
                asxEbsSectorCfgTddSplit
                    Integer32,
                asxEbsSectorCfgBandwidth
                    AsmaxBandwidthCode,
                asxEbsSectorCfgRxLevelSetpoint
                    Integer32,
                asxEbsSectorCfgRfGain
                    Integer32,
                asxEbsSectorCfgLicenseExempt
                    AsmaxBooleanSwitch,
                asxEbsSectorCfgT42MobHoIndTimeout
                    Integer32,
                asxEbsSectorCfgResourceRetainTimeout
                    Integer32,
                asxEbsSectorCfgT46IdleModeInitiateTimeout
                    Integer32,
                asxEbsSectorCfgBsMgmtResourceHoldTimeout
                    Integer32,
                asxEbsSectorCfgRssiAlphaLow
                    Integer32,
                asxEbsSectorCfgRssiAlphaHigh
                    Integer32,
                asxEbsSectorCfgMaxUlAllocation
                    Integer32,
                asxEbsSectorCfgMaxDlAllocation
                    Integer32,
                asxEbsSectorCfgTtg
                    Integer32,
                asxEbsSectorCfgRtg
                    Integer32,
                asxEbsSectorCfgSignonUlZoneIndex
                    Integer32,
                asxEbsSectorCfgSignonDlZoneIndex
                    Integer32,
                asxEbsSectorCfgInitialRangingAllocSize
                    Integer32,
                asxEbsSectorCfgRxLevelSpread
                    Integer32,
                asxEbsSectorCfgRxLevelInitialRangingSpread
                    Integer32,
                asxEbsSectorCfgTimingSetpoint
                    Integer32,
                asxEbsSectorCfgTimingSpread
                    Integer32,
                asxEbsSectorCfgUplinkFrequencyErrorSetpoint
                    Integer32,
                asxEbsSectorCfgUplinkFrequencyErrorSpread
                    Integer32,
                asxEbsSectorCfgStrictConformance
                    AsmaxBooleanSwitch,
                asxEbsSectorCfgNumRangingRetries
                    Integer32,
                asxEbsSectorCfgFastPeriodicRangingUpdate
                    AsmaxBooleanSwitch,
                asxEbsSectorCfgNumNoSignalIndsForSignoff
                    Integer32,
                asxEbsSectorCfgInvitedRangingRetryPeriod
                    Integer32,
                asxEbsSectorCfgInitialRangingTosPerSec
                    Integer32,
                asxEbsSectorCfgNumExpectedSss
                    Integer32,
                asxEbsSectorCfgRegistrationTimeout
                    Integer32,
                asxEbsSectorCfgDcdUcdPeriod
                    Integer32,
                asxEbsSectorCfgInitialRangingBurstSize
                    Integer32,
                asxEbsSectorCfgBandwidthRequestTosPerSec
                    Integer32,
                asxEbsSectorCfgBwReqAllocSize
                    Integer32,
                asxEbsSectorCfgFastFeedbackSlotsPerSec
                    Integer32,
                asxEbsSectorCfgBwReqGrantSize
                    Integer32,
                asxEbsSectorCfgNeighbourAdvertisementPeriod
                    Integer32,
                asxEbsSectorCfgIdlePeriodicRangingInterval
                    Integer32,
                asxEbsSectorCfgActivePeriodicRangingInterval
                    Integer32,
                asxEbsSectorCfgT13TftpCompleteTimeout
                    Integer32,
                asxEbsSectorCfgInService
                    AsmaxBooleanSwitch,
                asxEbsSectorCfgForceSpecialUlAllocs
                    AsmaxBooleanSwitch,
                asxEbsSectorCfgReportRequestInterval
                    Integer32,
                asxEbsSectorCfgNumNoReportsForSignoff
                    Integer32,
                asxEbsSectorCfgDefaultSsClass
                    AsxEbsClassName,
                asxEbsSectorCfgDefaultServiceProduct
                    AsxEbsClassName,
                asxEbsSectorCfgDefaultPortClass
                    AsxEbsClassName,
                asxEbsSectorCfgTxPower
                    Integer32,
                asxEbsSectorCfgMsCinrAlpha
                    Integer32,
                asxEbsSectorCfgDefaultAsnGwUplkServiceClass
                    Integer32,
                asxEbsSectorCfgDefaultAsnGwDnlkServiceClass
                    Integer32,
                asxEbsSectorCfgPreambleIndex
                    Integer32,
                asxEbsSectorCfgSignonMaxUlSubchannels
                    Integer32,
                asxEbsSectorCfgFirstCidToPartition
                    Integer32,
                asxEbsSectorCfgNumCidsToPartition
                    Integer32,
                asxEbsSectorCfgControlledHoWaitPeriod
                    Integer32,
                asxEbsSectorCfgAutoGenerateHoCnf
                    AsmaxBooleanSwitch,
                asxEbsSectorCfgT42HoRngRspTimeout
                    Integer32,
                asxEbsSectorCfgHoHysteresisMargin
                    Integer32,
                asxEbsSectorCfgHoTimeToTriggerDuration
                    Integer32,
                asxEbsSectorCfgIncludeMsTxPowerLimit
                    AsmaxBooleanSwitch,
                asxEbsSectorCfgMsTxPowerLimit
                    Integer32,
                asxEbsSectorCfgDeadPeriodicRangingInterval
                    Integer32,
                asxEbsSectorCfgRadioConfigReportPeriod
                    Integer32,
                asxEbsSectorCfgMissingRadioConfigReportPeriod
                    Integer32,
                asxEbsSectorCfgNoiseMeasurementRate
                    Integer32,
                asxEbsSectorCfgNoiseMeasurementTime
                    Integer32,
                asxEbsSectorCfgNoiseMeasurementBandwidth
                    Integer32,
                asxEbsSectorCfgEnableNormalizedCnOverride
                    AsmaxBooleanSwitch,
                asxEbsSectorCfgNormalizedCnOverride
                    OCTET STRING,
                asxEbsSectorCfgMsPeriodicRangingTimeout
                    Integer32,
                asxEbsSectorCfgTimingOffsetAdjustment
                    Integer32,
                asxEbsSectorCfgDregCmdWaitTime
                    Integer32,
                asxEbsSectorCfgDregCmdNumRetries
                    Integer32,
                asxEbsSectorCfgUlPermutationBase
                    Integer32,
                asxEbsSectorCfgDlPermutationBase
                    Integer32,
                asxEbsSectorCfgPermutationBaseSource
                    INTEGER,
                asxEbsSectorCfgAsnGwCommsR6Timeout
                    Integer32,
                asxEbsSectorCfgAsnGwCommsPingTimeout
                    Integer32,
                asxEbsSectorCfgAsnGwCommsPingFailsMax
                    Integer32,
                asxEbsSectorCfgSnReportingBase
                    Integer32,
                asxEbsSectorCfgInitialRangingThrottleTime
                    Integer32,
                asxEbsSectorCfgPagingAdvertAdvance
                    Integer32,
                asxEbsSectorCfgAccuratePagingAdverts
                    AsmaxBooleanSwitch,
                asxEbsSectorCfgSizeOfCqichIdFieldUcd
                    INTEGER,
                asxEbsSectorCfgUlAdaptationEfficiencyMode
                    INTEGER,
                asxEbsSectorCfgForceAsnUncontrolledHandover
                    AsmaxBooleanSwitch,
                asxEbsSectorCfgCqichReallocationPeriod
                    Integer32,
                asxEbsSectorCfgIndefiniteCqichDuration
                    Integer32,
                asxEbsSectorCfgMsHoRetransmissionTimer
                    Integer32,
                asxEbsSectorCfgPowerControlMode
                    INTEGER,
                asxEbsSectorCfgNiIePeriod
                    Integer32,
                asxEbsSectorCfgCarrierSenseThreshold
                    Integer32,
                asxEbsSectorCfgCarrierSenseBackoffTime
                    Integer32,
                asxEbsSectorCfgDisableDlMgmtHarq
                    AsmaxBooleanSwitch,
                asxEbsSectorCfgMsMaxTxPowerBackoff
                    Integer32,
                asxEbsSectorCfgCarrierSenseEnabled
                    AsmaxBooleanSwitch,
                asxEbsSectorCfgRequestedLicensedFeatures
                    AsxEbsBsLicensedFeatures,
                asxEbsSectorCfgCarrierSenseMonitorPeriod
                    Integer32,
                asxEbsSectorCfgCarrierSenseHighThresholdPercentageMuting
                    Integer32,
                asxEbsSectorCfgCarrierSenseHysteresis
                    Integer32,
                asxEbsSectorCfgCarrierSenseContentionTime
                    Integer32,
                asxEbsSectorCfgCarrierSenseMeasurePeriod
                    Integer32,
                asxEbsSectorCfgPrivateMapMode
                    AsxEbsSectorPrivateMapMode,
                asxEbsSectorCfgPagingAdvertMode
                    INTEGER,
                asxEbsSectorCfgStaticPagingAdvertInterval
                    Integer32,
                asxEbsSectorCfgScanScheduleEnable
                    AsmaxBooleanSwitch,
                asxEbsSectorCfgScanScheduleTriggerTime
                    Integer32,
                asxEbsSectorCfgScanInterleavingInterval
                    Integer32,
                asxEbsSectorCfgScanDuration
                    Integer32
             }

        -- 1.3.6.1.4.1.989.1.16.2.7.3.1.1.1
        asxEbsSectorCfgUsedSubchannelGroupMap OBJECT-TYPE
            SYNTAX AsxEbsSubchannelGroupMap
            MAX-ACCESS read-write
            STATUS current
            DESCRIPTION
                "In OFDMA, a 6-bit bitmap representing the subchannel groups used for the 
                downlink zones. 
                Only groups 0, 2 and 4 can be used with 128 and 512(?) FFT sizes.
                Not used for OFDM sectors. "
            ::= { asxEbsSectorCfgEntry 1 }

        
        -- 1.3.6.1.4.1.989.1.16.2.7.3.1.1.2
        asxEbsSectorCfgInitialBurstDiuc OBJECT-TYPE
            SYNTAX Integer32 (0..12)
            MAX-ACCESS read-write
            STATUS current
            DESCRIPTION
                "For OFDM: the DIUC of the burst profile to be used for transmission 
                of the first downlink burst containing the maps, DCD and UCD. 
                For OFDMA: the DIUC of the burst profile to be used for transmission 
                of the downlink burst containing the ULMAP. "
            ::= { asxEbsSectorCfgEntry 2 }

        
        -- 1.3.6.1.4.1.989.1.16.2.7.3.1.1.3
        asxEbsSectorCfgInitialRangingUiuc OBJECT-TYPE
            SYNTAX Integer32 (1..10)
            MAX-ACCESS read-write
            STATUS current
            DESCRIPTION
                "The UIUC of the burst profile to be used for uplink initial ranging."
            ::= { asxEbsSectorCfgEntry 3 }

        
        -- 1.3.6.1.4.1.989.1.16.2.7.3.1.1.4
        asxEbsSectorCfgBwRequestUiuc OBJECT-TYPE
            SYNTAX Integer32 (1..10)
            MAX-ACCESS read-write
            STATUS current
            DESCRIPTION
                "The UIUC of the burst profile to be used 
                in the contention bandwidth request interval (for OFDM) 
                or the allocation made in response to a CDMA bandwidth request (OFDMA). "
            ::= { asxEbsSectorCfgEntry 4 }

        
        -- 1.3.6.1.4.1.989.1.16.2.7.3.1.1.5
        asxEbsSectorCfgSignonDiuc OBJECT-TYPE
            SYNTAX Integer32 (0..12)
            MAX-ACCESS read-write
            STATUS current
            DESCRIPTION
                "Specifies the burst profile to be used for downlink transmissions 
                to an SS during the signon process before provisioning is active. "
            ::= { asxEbsSectorCfgEntry 5 }

        
        -- 1.3.6.1.4.1.989.1.16.2.7.3.1.1.6
        asxEbsSectorCfgSignonUiuc OBJECT-TYPE
            SYNTAX Integer32 (1..10)
            MAX-ACCESS read-write
            STATUS current
            DESCRIPTION
                "Specifies the burst profile to be used for uplink transmissions by an SS 
                during the signon process before the provisioning is active. "
            ::= { asxEbsSectorCfgEntry 6 }

        
        -- 1.3.6.1.4.1.989.1.16.2.7.3.1.1.7
        asxEbsSectorCfgPhyType OBJECT-TYPE
            SYNTAX INTEGER
                {
                phyTypeOfdm(0),
                phyTypeOfdma(1)
                }
            MAX-ACCESS read-write
            STATUS current
            DESCRIPTION
                "Description."
            DEFVAL { phyTypeOfdma }
            ::= { asxEbsSectorCfgEntry 7 }

        
        -- 1.3.6.1.4.1.989.1.16.2.7.3.1.1.8
        asxEbsSectorCfgFrameDuplex OBJECT-TYPE
            SYNTAX INTEGER
                {
                frameDuplexFdd(0),
                frameDuplexTdd(1)
                }
            MAX-ACCESS read-write
            STATUS current
            DESCRIPTION
                "Description."
            DEFVAL { frameDuplexTdd }
            ::= { asxEbsSectorCfgEntry 8 }

        
        -- 1.3.6.1.4.1.989.1.16.2.7.3.1.1.9
        asxEbsSectorCfgTddSplit OBJECT-TYPE
            SYNTAX Integer32 (0..100)
            UNITS "%"
            MAX-ACCESS read-write
            STATUS current
            DESCRIPTION
                "Description."
            DEFVAL { 50 }
            ::= { asxEbsSectorCfgEntry 9 }

        
        -- 1.3.6.1.4.1.989.1.16.2.7.3.1.1.10
        asxEbsSectorCfgBandwidth OBJECT-TYPE
            SYNTAX AsmaxBandwidthCode
            MAX-ACCESS read-write
            STATUS current
            DESCRIPTION
                "Description."
            DEFVAL { bandwidth3dot5MHz }
            ::= { asxEbsSectorCfgEntry 10 }

        
        -- 1.3.6.1.4.1.989.1.16.2.7.3.1.1.11
        asxEbsSectorCfgRxLevelSetpoint OBJECT-TYPE
            SYNTAX Integer32 (-32768..32767)
            UNITS "1/4 dBm"
            MAX-ACCESS read-write
            STATUS current
            DESCRIPTION
                "The uplink receive level set point in 1/4 dBm units"
            DEFVAL { -380 }
            ::= { asxEbsSectorCfgEntry 11 }

        
        -- 1.3.6.1.4.1.989.1.16.2.7.3.1.1.12
        asxEbsSectorCfgRfGain OBJECT-TYPE
            SYNTAX Integer32 (0..65000)
            MAX-ACCESS read-write
            STATUS current
            DESCRIPTION
                "Indicates the gain of the RF stages of the sector. 
                This value is used in the RSSI calculations."
            DEFVAL { 13800 }
            ::= { asxEbsSectorCfgEntry 12 }

        
        -- 1.3.6.1.4.1.989.1.16.2.7.3.1.1.13
        asxEbsSectorCfgLicenseExempt OBJECT-TYPE
            SYNTAX AsmaxBooleanSwitch
            MAX-ACCESS read-write
            STATUS current
            DESCRIPTION
                "Set to licenseExempTrue if required to operate in license exempt mode,
                in which case the channel to use is indicated by the License Exempt channel
                defined in WMAN-IF2-MIB mib table wmanIf2BsCmnPhyDownlinkChannelTable"
            DEFVAL { booleanFalse }
            ::= { asxEbsSectorCfgEntry 13 }

        
        -- 1.3.6.1.4.1.989.1.16.2.7.3.1.1.14
        asxEbsSectorCfgT42MobHoIndTimeout OBJECT-TYPE
            SYNTAX Integer32 (0..2147483647)
            UNITS "ms"
            MAX-ACCESS read-write
            STATUS current
            DESCRIPTION
                "Length of time the BS waits for a MOB_HO-IND message before assuming one was sent. in ms."
            DEFVAL { 10000 }
            ::= { asxEbsSectorCfgEntry 14 }

        
        -- 1.3.6.1.4.1.989.1.16.2.7.3.1.1.15
        asxEbsSectorCfgResourceRetainTimeout OBJECT-TYPE
            SYNTAX Integer32 (0..2147483647)
            UNITS "ms"
            MAX-ACCESS read-write
            STATUS current
            DESCRIPTION
                "Length of time the BS retains an MS's state information after reception of a MOB_HO-IND message. in ms."
            DEFVAL { 2000 }
            ::= { asxEbsSectorCfgEntry 15 }

        
        -- 1.3.6.1.4.1.989.1.16.2.7.3.1.1.16
        asxEbsSectorCfgT46IdleModeInitiateTimeout OBJECT-TYPE
            SYNTAX Integer32 (0..2147483647)
            UNITS "ms"
            MAX-ACCESS read-write
            STATUS current
            DESCRIPTION
                "Time the BS waits for a DREG-REQ after sending a DREG-CMD in case of un-solicited idle mode initiation. in ms."
            DEFVAL { 200 }
            ::= { asxEbsSectorCfgEntry 16 }

        
        -- 1.3.6.1.4.1.989.1.16.2.7.3.1.1.17
        asxEbsSectorCfgBsMgmtResourceHoldTimeout OBJECT-TYPE
            SYNTAX Integer32 (0..1000)
            UNITS "ms"
            MAX-ACCESS read-write
            STATUS current
            DESCRIPTION
                "Time duration for which BS maintains MS connection information after sending the DREG-CMD. in ms."
            DEFVAL { 500 }
            ::= { asxEbsSectorCfgEntry 17 }

        
        -- 1.3.6.1.4.1.989.1.16.2.7.3.1.1.18
        asxEbsSectorCfgRssiAlphaLow OBJECT-TYPE
            SYNTAX Integer32 (0..100)
            UNITS "%"
            MAX-ACCESS read-write
            STATUS current
            DESCRIPTION
                "The alpha factor used by the RSSI filter when the input falls below the previous output. in percentage."
            DEFVAL { 100 }
            ::= { asxEbsSectorCfgEntry 18 }

        
        -- 1.3.6.1.4.1.989.1.16.2.7.3.1.1.19
        asxEbsSectorCfgRssiAlphaHigh OBJECT-TYPE
            SYNTAX Integer32 (0..100)
            UNITS "%"
            MAX-ACCESS read-write
            STATUS current
            DESCRIPTION
                "The alpha factor used by the RSSI filter when the input falls above the previous output. in percentage."
            DEFVAL { 100 }
            ::= { asxEbsSectorCfgEntry 19 }

        
        -- 1.3.6.1.4.1.989.1.16.2.7.3.1.1.20
        asxEbsSectorCfgMaxUlAllocation OBJECT-TYPE
            SYNTAX Integer32 (0..2147483647)
            UNITS "bytes"
            MAX-ACCESS read-write
            STATUS current
            DESCRIPTION
                "Maximum size of a single uplink allocation."
            DEFVAL { 32000 }
            ::= { asxEbsSectorCfgEntry 20 }

        
        -- 1.3.6.1.4.1.989.1.16.2.7.3.1.1.21
        asxEbsSectorCfgMaxDlAllocation OBJECT-TYPE
            SYNTAX Integer32 (0..2147483647)
            UNITS "bytes"
            MAX-ACCESS read-write
            STATUS current
            DESCRIPTION
                "Maximum size of a single downlink allocation."
            DEFVAL { 32000 }
            ::= { asxEbsSectorCfgEntry 21 }

        
        -- 1.3.6.1.4.1.989.1.16.2.7.3.1.1.22
        asxEbsSectorCfgTtg OBJECT-TYPE
            SYNTAX Integer32 (0..2147483647)
            UNITS "1/10 us"
            MAX-ACCESS read-write
            STATUS current
            DESCRIPTION
                "The minimum gap between the last symbol of the downlink subframe and the 
                beginning of the first uplink grant. Only applicable for TDD."
            DEFVAL { 0 }
            ::= { asxEbsSectorCfgEntry 22 }

        
        -- 1.3.6.1.4.1.989.1.16.2.7.3.1.1.23
        asxEbsSectorCfgRtg OBJECT-TYPE
            SYNTAX Integer32 (0..2147483647)
            UNITS "1/10 us"
            MAX-ACCESS read-write
            STATUS current
            DESCRIPTION
                "The minimum gap between the end of the last uplink grant, including contention intervals, 
                and the downlink preamble of the next frame."
            DEFVAL { 0 }
            ::= { asxEbsSectorCfgEntry 23 }

        
        -- 1.3.6.1.4.1.989.1.16.2.7.3.1.1.24
        asxEbsSectorCfgSignonUlZoneIndex OBJECT-TYPE
            SYNTAX Integer32
            MAX-ACCESS read-write
            STATUS current
            DESCRIPTION
                "Specifies the zone to be used for uplink transmissions by an SS during the signon process before the provisioning is active."
            DEFVAL { 0 }
            ::= { asxEbsSectorCfgEntry 24 }

        
        -- 1.3.6.1.4.1.989.1.16.2.7.3.1.1.25
        asxEbsSectorCfgSignonDlZoneIndex OBJECT-TYPE
            SYNTAX Integer32
            MAX-ACCESS read-write
            STATUS current
            DESCRIPTION
                "Specifies the zone to be used for downlink transmissions to an SS during the signon process before provisioning is active. "
            DEFVAL { 0 }
            ::= { asxEbsSectorCfgEntry 25 }

        
        -- 1.3.6.1.4.1.989.1.16.2.7.3.1.1.26
        asxEbsSectorCfgInitialRangingAllocSize OBJECT-TYPE
            SYNTAX Integer32 (0..2147483647)
            UNITS "symbols"
            MAX-ACCESS read-write
            STATUS current
            DESCRIPTION
                "The size of an initial ranging opportunity allocation.
                In OFDM, this is typically 1 or 2 symbols more than the initialRangingBurstSize field.
                In OFDMA, valid values are 2 and 4 symbols only."
            DEFVAL { 2 }
            ::= { asxEbsSectorCfgEntry 26 }

        
        -- 1.3.6.1.4.1.989.1.16.2.7.3.1.1.28
        asxEbsSectorCfgRxLevelSpread OBJECT-TYPE
            SYNTAX Integer32 (0..2147483647)
            UNITS "1/4 dBm"
            MAX-ACCESS read-write
            STATUS current
            DESCRIPTION
                "The spread around the receive level set point allowed before ranging is performed.
                Value must always be positive.
                The measured value is allowed to be in the range set point +/- the spread."
            DEFVAL { 24 }
            ::= { asxEbsSectorCfgEntry 28 }

        
        -- 1.3.6.1.4.1.989.1.16.2.7.3.1.1.29
        asxEbsSectorCfgRxLevelInitialRangingSpread OBJECT-TYPE
            SYNTAX Integer32 (0..2147483647)
            UNITS "1/4 dBm"
            MAX-ACCESS read-write
            STATUS current
            DESCRIPTION
                "The spread around the receive level set point allowed during initial ranging."
            DEFVAL { 48 }
            ::= { asxEbsSectorCfgEntry 29 }

        
        -- 1.3.6.1.4.1.989.1.16.2.7.3.1.1.30
        asxEbsSectorCfgTimingSetpoint OBJECT-TYPE
            SYNTAX Integer32
            UNITS "PS"
            MAX-ACCESS read-write
            STATUS current
            DESCRIPTION
                "The target timing offset for SSs."
            DEFVAL { 0 }
            ::= { asxEbsSectorCfgEntry 30 }

        
        -- 1.3.6.1.4.1.989.1.16.2.7.3.1.1.31
        asxEbsSectorCfgTimingSpread OBJECT-TYPE
            SYNTAX Integer32 (0..2147483647)
            UNITS "PS"
            MAX-ACCESS read-write
            STATUS current
            DESCRIPTION
                "The spread around the timing set point allowed.
                Values must always be positive.
                The measured value is allowed to be in the range set point +/- the spread."
            DEFVAL { 5 }
            ::= { asxEbsSectorCfgEntry 31 }

        
        -- 1.3.6.1.4.1.989.1.16.2.7.3.1.1.32
        asxEbsSectorCfgUplinkFrequencyErrorSetpoint OBJECT-TYPE
            SYNTAX Integer32
            UNITS "Hz"
            MAX-ACCESS read-write
            STATUS current
            DESCRIPTION
                "The target frequency error from the uplink center frequency."
            DEFVAL { 0 }
            ::= { asxEbsSectorCfgEntry 32 }

        
        -- 1.3.6.1.4.1.989.1.16.2.7.3.1.1.33
        asxEbsSectorCfgUplinkFrequencyErrorSpread OBJECT-TYPE
            SYNTAX Integer32 (0..2147483647)
            UNITS "Hz"
            MAX-ACCESS read-write
            STATUS current
            DESCRIPTION
                "The spread around the frequency error set point allowed.
                Values must always be positive.
                The measured value is allowed to be in the range set point +/ the spread."
            DEFVAL { 100 }
            ::= { asxEbsSectorCfgEntry 33 }

        
        -- 1.3.6.1.4.1.989.1.16.2.7.3.1.1.34
        asxEbsSectorCfgStrictConformance OBJECT-TYPE
            SYNTAX AsmaxBooleanSwitch
            MAX-ACCESS read-write
            STATUS current
            DESCRIPTION
                "When TRUE, strictly conforms to the 802.16-2004 and 802.16e-2005 standards."
            DEFVAL { booleanFalse }
            ::= { asxEbsSectorCfgEntry 34 }

        
        -- 1.3.6.1.4.1.989.1.16.2.7.3.1.1.35
        asxEbsSectorCfgNumRangingRetries OBJECT-TYPE
            SYNTAX Integer32 (0..2147483647)
            MAX-ACCESS read-write
            STATUS current
            DESCRIPTION
                "The number of ranging attempts before the BS gives up trying to align the SS."
            DEFVAL { 16 }
            ::= { asxEbsSectorCfgEntry 35 }

        
        -- 1.3.6.1.4.1.989.1.16.2.7.3.1.1.36
        asxEbsSectorCfgFastPeriodicRangingUpdate OBJECT-TYPE
            SYNTAX AsmaxBooleanSwitch
            MAX-ACCESS read-write
            STATUS current
            DESCRIPTION
                "Set to true to allow RNG-RSP messages sent by the BS during periodic ranging 
                to always contain the 'success' code."
            DEFVAL { booleanFalse }
            ::= { asxEbsSectorCfgEntry 36 }

        
        -- 1.3.6.1.4.1.989.1.16.2.7.3.1.1.37
        asxEbsSectorCfgNumNoSignalIndsForSignoff OBJECT-TYPE
            SYNTAX Integer32 (0..2147483647)
            MAX-ACCESS read-write
            STATUS current
            DESCRIPTION
                "The number of consecutive uplink allocations that the SS fails to fill before 
                the BS deems the SS to have signed off. Set to 0 to disable sign-off detection."
            DEFVAL { 16 }
            ::= { asxEbsSectorCfgEntry 37 }

        
        -- 1.3.6.1.4.1.989.1.16.2.7.3.1.1.38
        asxEbsSectorCfgInvitedRangingRetryPeriod OBJECT-TYPE
            SYNTAX Integer32 (0..2147483647)
            UNITS "ms"
            MAX-ACCESS read-write
            STATUS current
            DESCRIPTION
                "The time between repeats of an invited ranging allocation."
            DEFVAL { 100 }
            ::= { asxEbsSectorCfgEntry 38 }

        
        -- 1.3.6.1.4.1.989.1.16.2.7.3.1.1.39
        asxEbsSectorCfgInitialRangingTosPerSec OBJECT-TYPE
            SYNTAX Integer32 (0..2147483647)
            UNITS "per sec"
            MAX-ACCESS read-write
            STATUS current
            DESCRIPTION
                "The number of contention initial ranging transmit opportunities to be planted per second.
                For OFDM these are contended initial ranging opportunities.
                For OFDMA they are CDMA initial ranging regions."
            DEFVAL { 10 }
            ::= { asxEbsSectorCfgEntry 39 }

        
        -- 1.3.6.1.4.1.989.1.16.2.7.3.1.1.40
        asxEbsSectorCfgNumExpectedSss OBJECT-TYPE
            SYNTAX Integer32 (0..2147483647)
            MAX-ACCESS read-write
            STATUS current
            DESCRIPTION
                "The number of expected SSs the sector is to support.
                This number is used to partition the CID space into basic, primary and traffic regions.
                It does not limit the number of SSs that may be supported."
            DEFVAL { 1000 }
            ::= { asxEbsSectorCfgEntry 40 }

        
        -- 1.3.6.1.4.1.989.1.16.2.7.3.1.1.41
        asxEbsSectorCfgRegistrationTimeout OBJECT-TYPE
            SYNTAX Integer32 (0..2147483647)
            UNITS "ms"
            MAX-ACCESS read-write
            STATUS current
            DESCRIPTION
                "Time that the BS waits for registration to occur after authorization before aborting the sign-on."
            DEFVAL { 300 }
            ::= { asxEbsSectorCfgEntry 41 }

        
        -- 1.3.6.1.4.1.989.1.16.2.7.3.1.1.42
        asxEbsSectorCfgDcdUcdPeriod OBJECT-TYPE
            SYNTAX Integer32 (1..3600000)
            UNITS "ms"
            MAX-ACCESS read-write
            STATUS current
            DESCRIPTION
                "The repetition period of the transmission of the DCD and UCD messages."
            DEFVAL { 5000 }
            ::= { asxEbsSectorCfgEntry 42 }

        
        -- 1.3.6.1.4.1.989.1.16.2.7.3.1.1.43
        asxEbsSectorCfgInitialRangingBurstSize OBJECT-TYPE
            SYNTAX Integer32 (0..255)
            UNITS "symbols"
            MAX-ACCESS read-write
            STATUS current
            DESCRIPTION
                "In OFDM, the number of symbols that an SS shall use to transmit a RNG-REQ message
                in a full bandwidth initial ranging opportunity.
                In OFDMA, the size of the allocation made for a RNG-REQ message once CDMA ranging is complete."
            DEFVAL { 4 }
            ::= { asxEbsSectorCfgEntry 43 }

        
        -- 1.3.6.1.4.1.989.1.16.2.7.3.1.1.44
        asxEbsSectorCfgBandwidthRequestTosPerSec OBJECT-TYPE
            SYNTAX Integer32 (0..2147483647)
            UNITS "per sec"
            MAX-ACCESS read-write
            STATUS current
            DESCRIPTION
                "The number of contention bandwidth request transmit opportunities to be planted per second.
                For OFDM these are contended bandwidth request opportunities.
                For OFDMA they are CDMA bandwidth request regions."
            DEFVAL { 100 }
            ::= { asxEbsSectorCfgEntry 44 }

        
        -- 1.3.6.1.4.1.989.1.16.2.7.3.1.1.45
        asxEbsSectorCfgBwReqAllocSize OBJECT-TYPE
            SYNTAX Integer32 (0..2147483647)
            UNITS "symbols"
            MAX-ACCESS read-write
            STATUS current
            DESCRIPTION
                "The size of a bandwidth request opportunity allocation.
                In OFDM, this value is normally 2.
                In OFDMA, valid values are 1 and 3 symbols only."
            DEFVAL { 1 }
            ::= { asxEbsSectorCfgEntry 45 }

        
        -- 1.3.6.1.4.1.989.1.16.2.7.3.1.1.46
        asxEbsSectorCfgFastFeedbackSlotsPerSec OBJECT-TYPE
            SYNTAX Integer32 (0..2147483647)
            UNITS "per sec"
            MAX-ACCESS read-write
            STATUS current
            DESCRIPTION
                "The number of fast feedback slots per second that are allocated in the uplink frame.
                Used by OFDMA only."
            DEFVAL { 100 }
            ::= { asxEbsSectorCfgEntry 46 }

        
        -- 1.3.6.1.4.1.989.1.16.2.7.3.1.1.47
        asxEbsSectorCfgBwReqGrantSize OBJECT-TYPE
            SYNTAX Integer32 (0..2147483647)
            UNITS "bytes"
            MAX-ACCESS read-write
            STATUS current
            DESCRIPTION
                "The size of the grant indicated by a CDMA allocation made in OFDMA mode
                in response to the reception of a bandwidth request CDMA code."
            DEFVAL { 6 }
            ::= { asxEbsSectorCfgEntry 47 }

        
        -- 1.3.6.1.4.1.989.1.16.2.7.3.1.1.48
        asxEbsSectorCfgNeighbourAdvertisementPeriod OBJECT-TYPE
            SYNTAX Integer32 (0..2147483647)
            UNITS "ms"
            MAX-ACCESS read-write
            STATUS current
            DESCRIPTION
                "The period at which the neighbour advertisement broadcast message is sent 
                by the BS. Set to 0 to disable."
            DEFVAL { 10000 }
            ::= { asxEbsSectorCfgEntry 48 }

        
        -- 1.3.6.1.4.1.989.1.16.2.7.3.1.1.49
        asxEbsSectorCfgIdlePeriodicRangingInterval OBJECT-TYPE
            SYNTAX Integer32 (0..2147483647)
            UNITS "ms"
            MAX-ACCESS read-write
            STATUS current
            DESCRIPTION
                "The time between periodic ranging grants when the BS thinks the SS is aligned. 
                Known as T27 idle in 802.16-2004."
            DEFVAL { 5000 }
            ::= { asxEbsSectorCfgEntry 49 }

        
        -- 1.3.6.1.4.1.989.1.16.2.7.3.1.1.50
        asxEbsSectorCfgActivePeriodicRangingInterval OBJECT-TYPE
            SYNTAX Integer32 (0..2147483647)
            UNITS "ms"
            MAX-ACCESS read-write
            STATUS current
            DESCRIPTION
                "The time between periodic ranging grants when the BS thinks the SS is not aligned. 
                Known as T27 active in 802.16-2004. 
                Also controls the time between a RNG-RSP and the allocation of an invited ranging interval."
            DEFVAL { 50 }
            ::= { asxEbsSectorCfgEntry 50 }

        
        -- 1.3.6.1.4.1.989.1.16.2.7.3.1.1.51
        asxEbsSectorCfgT13TftpCompleteTimeout OBJECT-TYPE
            SYNTAX Integer32 (0..2147483647)
            UNITS "ms"
            MAX-ACCESS read-write
            STATUS current
            DESCRIPTION
                "Time that the BS waits for the TFTP complete indication after registration 
                before aborting the sign-on."
            DEFVAL { 900000 }
            ::= { asxEbsSectorCfgEntry 51 }

        
        -- 1.3.6.1.4.1.989.1.16.2.7.3.1.1.52
        asxEbsSectorCfgInService OBJECT-TYPE
            SYNTAX AsmaxBooleanSwitch
            MAX-ACCESS read-write
            STATUS current
            DESCRIPTION
                "Set to TRUE to enable PHY operation of this sector."
            DEFVAL { booleanFalse }
            ::= { asxEbsSectorCfgEntry 52 }

        
        -- 1.3.6.1.4.1.989.1.16.2.7.3.1.1.53
        asxEbsSectorCfgForceSpecialUlAllocs OBJECT-TYPE
            SYNTAX AsmaxBooleanSwitch
            MAX-ACCESS read-write
            STATUS current
            DESCRIPTION
                "Forces the allocation of the uplink special regions (CDMA bandwidth request, CDMA initial ranging and fast feedback) to be exactly one per frame. Use this if it is essential to have this allocation in every frame, something that is not guaranteed by the normal timer driven mode. "
            DEFVAL { booleanFalse }
            ::= { asxEbsSectorCfgEntry 53 }

        
        -- 1.3.6.1.4.1.989.1.16.2.7.3.1.1.54
        asxEbsSectorCfgReportRequestInterval OBJECT-TYPE
            SYNTAX Integer32 (0..2147483647)
            UNITS "ms"
            MAX-ACCESS read-write
            STATUS current
            DESCRIPTION
                "The time between individual requests to an MS to report its signal quality information. Setting this to 0 will disable the transmission of report request messages to all MSs. in ms."
            DEFVAL { 1000 }
            ::= { asxEbsSectorCfgEntry 54 }

        
        -- 1.3.6.1.4.1.989.1.16.2.7.3.1.1.55
        asxEbsSectorCfgNumNoReportsForSignoff OBJECT-TYPE
            SYNTAX Integer32 (0..2147483647)
            MAX-ACCESS read-write
            STATUS current
            DESCRIPTION
                "The number of consecutive times that the MS can fail to send a REP-RSP message in reply to a REP-REQ from the basestation before the MS is signed off. "
            DEFVAL { 5 }
            ::= { asxEbsSectorCfgEntry 55 }

        
        -- 1.3.6.1.4.1.989.1.16.2.7.3.1.1.56
        asxEbsSectorCfgDefaultSsClass OBJECT-TYPE
            SYNTAX AsxEbsClassName
            MAX-ACCESS read-write
            STATUS current
            DESCRIPTION
                "Description."
            ::= { asxEbsSectorCfgEntry 56 }

        
        -- 1.3.6.1.4.1.989.1.16.2.7.3.1.1.57
        asxEbsSectorCfgDefaultServiceProduct OBJECT-TYPE
            SYNTAX AsxEbsClassName
            MAX-ACCESS read-write
            STATUS current
            DESCRIPTION
                "Description."
            ::= { asxEbsSectorCfgEntry 57 }

        
        -- 1.3.6.1.4.1.989.1.16.2.7.3.1.1.58
        asxEbsSectorCfgDefaultPortClass OBJECT-TYPE
            SYNTAX AsxEbsClassName
            MAX-ACCESS read-write
            STATUS current
            DESCRIPTION
                "Description."
            ::= { asxEbsSectorCfgEntry 58 }

        
        -- 1.3.6.1.4.1.989.1.16.2.7.3.1.1.59
        asxEbsSectorCfgTxPower OBJECT-TYPE
            SYNTAX Integer32 (0..7500)
            UNITS "0.01dBm"
            MAX-ACCESS read-write
            STATUS current
            DESCRIPTION
                "The transmit power required by the basestation."
            DEFVAL { 0 }
            ::= { asxEbsSectorCfgEntry 59 }

        
        -- 1.3.6.1.4.1.989.1.16.2.7.3.1.1.60
        asxEbsSectorCfgMsCinrAlpha OBJECT-TYPE
            SYNTAX Integer32 (0..100)
            UNITS "%"
            MAX-ACCESS read-write
            STATUS current
            DESCRIPTION
                "Specifies the alpha value to be sent to the MS when requesting a CINR report. in percentage.
                "
            DEFVAL { 25 }
            ::= { asxEbsSectorCfgEntry 60 }

        
        -- 1.3.6.1.4.1.989.1.16.2.7.3.1.1.61
        asxEbsSectorCfgDefaultAsnGwUplkServiceClass OBJECT-TYPE
            SYNTAX Integer32 (0..2147483647)
            MAX-ACCESS read-write
            STATUS current
            DESCRIPTION
                "The index to service class that is used to supply the service flow configuration 
                for uplink service flows created by the ASN-Gateway that is not supplied 
                by the ASN-Gateway. This primarily includes ARQ and HARQ parameters.  "
            ::= { asxEbsSectorCfgEntry 61 }

        
        -- 1.3.6.1.4.1.989.1.16.2.7.3.1.1.62
        asxEbsSectorCfgDefaultAsnGwDnlkServiceClass OBJECT-TYPE
            SYNTAX Integer32 (0..2147483647)
            MAX-ACCESS read-write
            STATUS current
            DESCRIPTION
                "The index to service class that is used to supply the service flow configuration 
                for downlink service flows created by the ASN-Gateway that is not supplied 
                by the ASN-Gateway. This primarily includes ARQ and HARQ parameters. "
            ::= { asxEbsSectorCfgEntry 62 }

        
        -- 1.3.6.1.4.1.989.1.16.2.7.3.1.1.63
        asxEbsSectorCfgPreambleIndex OBJECT-TYPE
            SYNTAX Integer32 (0..127)
            MAX-ACCESS read-write
            STATUS current
            DESCRIPTION
                "The preamble randomisation seed."
            DEFVAL { '1'b }
            ::= { asxEbsSectorCfgEntry 63 }

        
        -- 1.3.6.1.4.1.989.1.16.2.7.3.1.1.64
        asxEbsSectorCfgSignonMaxUlSubchannels OBJECT-TYPE
            SYNTAX Integer32 (0..2147483647)
            MAX-ACCESS read-write
            STATUS current
            DESCRIPTION
                "The maximum number of subchannels that an MS my use for an uplink transmission 
                during the signon phase. A value of 0 indicates that the number of subchannels is not limited. "
            DEFVAL { 0 }
            ::= { asxEbsSectorCfgEntry 64 }

        
        -- 1.3.6.1.4.1.989.1.16.2.7.3.1.1.65
        asxEbsSectorCfgFirstCidToPartition OBJECT-TYPE
            SYNTAX Integer32 (0..2147483647)
            MAX-ACCESS read-write
            STATUS current
            DESCRIPTION
                "The first CID number that the BS is to use when partitioning the CID space. 
                A value of 0 indicates that the first available CID should be used. "
            DEFVAL { 0 }
            ::= { asxEbsSectorCfgEntry 65 }

        
        -- 1.3.6.1.4.1.989.1.16.2.7.3.1.1.66
        asxEbsSectorCfgNumCidsToPartition OBJECT-TYPE
            SYNTAX Integer32 (0..2147483647)
            MAX-ACCESS read-write
            STATUS current
            DESCRIPTION
                "The number of CID numbers that the BS is to use when partitioning the CID space. 
                A value of 0 indicates that all available CIDs should be used. "
            DEFVAL { 0 }
            ::= { asxEbsSectorCfgEntry 66 }

        
        -- 1.3.6.1.4.1.989.1.16.2.7.3.1.1.67
        asxEbsSectorCfgControlledHoWaitPeriod OBJECT-TYPE
            SYNTAX Integer32 (0..2147483647)
            UNITS "ms"
            MAX-ACCESS read-write
            STATUS current
            DESCRIPTION
                "During controlled handover, if the RNG-REQ arrives before the handover confirm 
                from the ASN-Gateway, the BS waits this amount of time for the handover confirm 
                before dropping into the uncontrolled handover mode. A value of zero disables this wait. "
            DEFVAL { 200 }
            ::= { asxEbsSectorCfgEntry 67 }

        
        -- 1.3.6.1.4.1.989.1.16.2.7.3.1.1.68
        asxEbsSectorCfgAutoGenerateHoCnf OBJECT-TYPE
            SYNTAX AsmaxBooleanSwitch
            MAX-ACCESS read-write
            STATUS current
            DESCRIPTION
                "In the handover preparation phase, if the MOB_HO-IND is not received, 
                this flag controls the transmission of a handover confirm to the ASN-Gateway. 
                The normal (and correct) behaviour is not to send one. When this flag is set to true, 
                a confirm is sent if there was a single recommended BS. "
            DEFVAL { booleanFalse }
            ::= { asxEbsSectorCfgEntry 68 }

        
        -- 1.3.6.1.4.1.989.1.16.2.7.3.1.1.69
        asxEbsSectorCfgT42HoRngRspTimeout OBJECT-TYPE
            SYNTAX Integer32 (0..2147483647)
            UNITS "ms"
            MAX-ACCESS read-write
            STATUS current
            DESCRIPTION
                "Length of time the target BS waits for a RNG-REQ message after the preparation phase 
                before abandoning the handover. "
            DEFVAL { 10000 }
            ::= { asxEbsSectorCfgEntry 69 }

        
        -- 1.3.6.1.4.1.989.1.16.2.7.3.1.1.70
        asxEbsSectorCfgHoHysteresisMargin OBJECT-TYPE
            SYNTAX Integer32 (0..255)
            UNITS "dB"
            MAX-ACCESS read-write
            STATUS current
            DESCRIPTION
                "Hysteresis margin is used by the MS to include a neighbor BS to a list of possible target BSs. 
                When the CINR of a neighbor BS is larger than the sum of the CINR of the current serving BS 
                and the hysteresis margin for the time-to-trigger duration, then the neighbor BS is included 
                in the list of possible target BSs in MOB_MSHO-REQ. "
            DEFVAL { 0 }
            ::= { asxEbsSectorCfgEntry 70 }

        
        -- 1.3.6.1.4.1.989.1.16.2.7.3.1.1.71
        asxEbsSectorCfgHoTimeToTriggerDuration OBJECT-TYPE
            SYNTAX Integer32 (0..255)
            UNITS "ms"
            MAX-ACCESS read-write
            STATUS current
            DESCRIPTION
                "Time-to-Trigger duration is the time duration for MS decides 
                to select a neighbor BS as a possible target BS. "
            DEFVAL { 0 }
            ::= { asxEbsSectorCfgEntry 71 }

        
        -- 1.3.6.1.4.1.989.1.16.2.7.3.1.1.72
        asxEbsSectorCfgIncludeMsTxPowerLimit OBJECT-TYPE
            SYNTAX AsmaxBooleanSwitch
            MAX-ACCESS read-write
            STATUS current
            DESCRIPTION
                "Set to true to include the MS transmit power limitation TLV in the UCD. 
                For user it means MS tx power limit enabled."
            DEFVAL { booleanFalse }
            ::= { asxEbsSectorCfgEntry 72 }

        
        -- 1.3.6.1.4.1.989.1.16.2.7.3.1.1.73
        asxEbsSectorCfgMsTxPowerLimit OBJECT-TYPE
            SYNTAX Integer32 (0..255)
            UNITS "dBm"
            MAX-ACCESS read-write
            STATUS current
            DESCRIPTION
                "The MS transmit power limitation to be included in the UCD 
                if the asxEbsSectorCfgIncludeMsTxPowerLimit field is true. "
            DEFVAL { 0 }
            ::= { asxEbsSectorCfgEntry 73 }

        
        -- 1.3.6.1.4.1.989.1.16.2.7.3.1.1.74
        asxEbsSectorCfgDeadPeriodicRangingInterval OBJECT-TYPE
            SYNTAX Integer32 (0..2147483647)
            UNITS "ms"
            MAX-ACCESS read-write
            STATUS current
            DESCRIPTION
                "The period during which the BS does not calculate any further adjustments for an SS after it has made an adjustment. 
                This gives the SS time to respond. "
            DEFVAL { 50 }
            ::= { asxEbsSectorCfgEntry 74 }

        
        -- 1.3.6.1.4.1.989.1.16.2.7.3.1.1.75
        asxEbsSectorCfgRadioConfigReportPeriod OBJECT-TYPE
            SYNTAX Integer32 (0..2147483647)
            UNITS "ms"
            MAX-ACCESS read-write
            STATUS current
            DESCRIPTION
                "Period at which radio configuration reports are expected to be received from neighbour sectors. "
            DEFVAL { 600000 }
            ::= { asxEbsSectorCfgEntry 75 }

        
        -- 1.3.6.1.4.1.989.1.16.2.7.3.1.1.76
        asxEbsSectorCfgMissingRadioConfigReportPeriod OBJECT-TYPE
            SYNTAX Integer32 (0..2147483647)
            UNITS "ms"
            MAX-ACCESS read-write
            STATUS current
            DESCRIPTION
                "Period at which radio configuration reports are requested from a neighbour sector 
                that has not sent one within the last radioConfigReportPeriod. "
            DEFVAL { 5000 }
            ::= { asxEbsSectorCfgEntry 76 }

        
        -- 1.3.6.1.4.1.989.1.16.2.7.3.1.1.77
        asxEbsSectorCfgNoiseMeasurementRate OBJECT-TYPE
            SYNTAX Integer32
            UNITS "per sec"
            MAX-ACCESS read-write
            STATUS current
            DESCRIPTION
                "The rate at which allocations are made to allow the PHY to measure the uplink noise floor. Can be overridden by the 'forceSpecialUlAllocs' flag. "
            ::= { asxEbsSectorCfgEntry 77 }

        
        -- 1.3.6.1.4.1.989.1.16.2.7.3.1.1.78
        asxEbsSectorCfgNoiseMeasurementTime OBJECT-TYPE
            SYNTAX Integer32
            UNITS "symbols"
            MAX-ACCESS read-write
            STATUS current
            DESCRIPTION
                "The duration of each allocation made to allow the PHY to measure the uplink noise floor."
            ::= { asxEbsSectorCfgEntry 78 }

        
        -- 1.3.6.1.4.1.989.1.16.2.7.3.1.1.79
        asxEbsSectorCfgNoiseMeasurementBandwidth OBJECT-TYPE
            SYNTAX Integer32
            UNITS "subchannels"
            MAX-ACCESS read-write
            STATUS current
            DESCRIPTION
                "The bandwidth of each allocation made to allow the PHY to measure the uplink noise floor."
            ::= { asxEbsSectorCfgEntry 79 }

        
        -- 1.3.6.1.4.1.989.1.16.2.7.3.1.1.80
        asxEbsSectorCfgEnableNormalizedCnOverride OBJECT-TYPE
            SYNTAX AsmaxBooleanSwitch
            MAX-ACCESS read-write
            STATUS current
            DESCRIPTION
                "Enables the transmission of the normalized CN override table in the UCD. 
                The normalizedCnOverride column provides the values."
            DEFVAL { booleanFalse }
            ::= { asxEbsSectorCfgEntry 80 }

        
        -- 1.3.6.1.4.1.989.1.16.2.7.3.1.1.81
        asxEbsSectorCfgNormalizedCnOverride OBJECT-TYPE
            SYNTAX OCTET STRING (SIZE (15))
            MAX-ACCESS read-write
            STATUS current
            DESCRIPTION
                "The normalized CN override values for the UCD, 1 byte per value. "
            DEFVAL { '000000000000000000000000000000'h }
            ::= { asxEbsSectorCfgEntry 81 }

        
        -- 1.3.6.1.4.1.989.1.16.2.7.3.1.1.82
        asxEbsSectorCfgMsPeriodicRangingTimeout OBJECT-TYPE
            SYNTAX Integer32 (0..255000)
            UNITS "ms"
            MAX-ACCESS read-write
            STATUS current
            DESCRIPTION
                "The time (in milliseconds) sent to the MS as the Periodic Ranging timeout (T4)."
            DEFVAL { 10000 }
            ::= { asxEbsSectorCfgEntry 82 }

        
        -- 1.3.6.1.4.1.989.1.16.2.7.3.1.1.83
        asxEbsSectorCfgTimingOffsetAdjustment OBJECT-TYPE
            SYNTAX Integer32 (0..2147483647)
            UNITS "PS"
            MAX-ACCESS read-write
            STATUS current
            DESCRIPTION
                "The offset value used to convert the 10-bit unsigned timing value reported 
                by the PHY into a signed range. The algorithm is: 
                if (reported PHY value >= timing offset adjustment) 
                then timing = reported PHY value - 1024; else timing = reported PHY value."
            DEFVAL { 512 }
            ::= { asxEbsSectorCfgEntry 83 }

        
        -- 1.3.6.1.4.1.989.1.16.2.7.3.1.1.84
        asxEbsSectorCfgDregCmdWaitTime OBJECT-TYPE
            SYNTAX Integer32 (0..2147483647)
            UNITS "ms"
            MAX-ACCESS read-write
            STATUS current
            DESCRIPTION
                "The length of time the BS waits for a response to a DREG-CMD."
            DEFVAL { 500 }
            ::= { asxEbsSectorCfgEntry 84 }

        
        -- 1.3.6.1.4.1.989.1.16.2.7.3.1.1.85
        asxEbsSectorCfgDregCmdNumRetries OBJECT-TYPE
            SYNTAX Integer32 (0..2147483647)
            MAX-ACCESS read-write
            STATUS current
            DESCRIPTION
                "The number of times a DREG-CMD is sent to an MS before the BS gives up waiting for a response."
            DEFVAL { 5 }
            ::= { asxEbsSectorCfgEntry 85 }

        
        -- 1.3.6.1.4.1.989.1.16.2.7.3.1.1.86
        asxEbsSectorCfgUlPermutationBase OBJECT-TYPE
            SYNTAX Integer32 (0..31)
            MAX-ACCESS read-write
            STATUS current
            DESCRIPTION
                "The base used for the sub-carrier permutation in uplink PUSC zones."
            DEFVAL { 0 }
            ::= { asxEbsSectorCfgEntry 86 }

        
        -- 1.3.6.1.4.1.989.1.16.2.7.3.1.1.87
        asxEbsSectorCfgDlPermutationBase OBJECT-TYPE
            SYNTAX Integer32 (0..31)
            MAX-ACCESS read-write
            STATUS current
            DESCRIPTION
                "The base used for the sub-carrier permutation in downlink PUSC zones."
            DEFVAL { 0 }
            ::= { asxEbsSectorCfgEntry 87 }

        
        -- 1.3.6.1.4.1.989.1.16.2.7.3.1.1.88
        asxEbsSectorCfgPermutationBaseSource OBJECT-TYPE
            SYNTAX INTEGER
                {
                permBaseSourceZone(0),
                permBaseSourceSector(1)
                }
            MAX-ACCESS read-write
            STATUS current
            DESCRIPTION
                "The source of the sub-carrier permutation value for PUSC zones.
                NMS should set the value to permBaseSourceSector, to configured permutation base per sector."
            DEFVAL { permBaseSourceZone }
            ::= { asxEbsSectorCfgEntry 88 }

        
        -- 1.3.6.1.4.1.989.1.16.2.7.3.1.1.89
        asxEbsSectorCfgAsnGwCommsR6Timeout OBJECT-TYPE
            SYNTAX Integer32 (0..2147483647)
            UNITS "ms"
            MAX-ACCESS read-write
            STATUS current
            DESCRIPTION
                "ASN GW PING R6 message waiting timeout."
            DEFVAL { 30000 }
            ::= { asxEbsSectorCfgEntry 89 }

        
        -- 1.3.6.1.4.1.989.1.16.2.7.3.1.1.90
        asxEbsSectorCfgAsnGwCommsPingTimeout OBJECT-TYPE
            SYNTAX Integer32 (0..2147483647)
            UNITS "ms"
            MAX-ACCESS read-write
            STATUS current
            DESCRIPTION
                "ASN GW PING time between PING requests."
            DEFVAL { 2000 }
            ::= { asxEbsSectorCfgEntry 90 }

        
        -- 1.3.6.1.4.1.989.1.16.2.7.3.1.1.91
        asxEbsSectorCfgAsnGwCommsPingFailsMax OBJECT-TYPE
            SYNTAX Integer32 (0..2147483647)
            MAX-ACCESS read-write
            STATUS current
            DESCRIPTION
                "ASN GW PING maximum number of PING failures."
            DEFVAL { 5 }
            ::= { asxEbsSectorCfgEntry 91 }

        
        -- 1.3.6.1.4.1.989.1.16.2.7.3.1.1.92
        asxEbsSectorCfgSnReportingBase OBJECT-TYPE
            SYNTAX Integer32 (0..255)
            UNITS "dB"
            MAX-ACCESS read-write
            STATUS current
            DESCRIPTION
                "The base for SN reports from an MS. This value is sent to the MS 
                in the REG-RSP message, for values other than 3 (the default value in the standard)."
            DEFVAL { 3 }
            ::= { asxEbsSectorCfgEntry 92 }

        
        -- 1.3.6.1.4.1.989.1.16.2.7.3.1.1.93
        asxEbsSectorCfgInitialRangingThrottleTime OBJECT-TYPE
            SYNTAX Integer32 (0..2147483647)
            UNITS "ms"
            MAX-ACCESS read-write
            STATUS current
            DESCRIPTION
                "The minimum period between recognition of individual initial ranging CDMA codes.
                A value of zero disables the throttle."
            DEFVAL { 100 }
            ::= { asxEbsSectorCfgEntry 93 }

        
        -- 1.3.6.1.4.1.989.1.16.2.7.3.1.1.94
        asxEbsSectorCfgPagingAdvertAdvance OBJECT-TYPE
            SYNTAX Integer32 (0..2147483647)
            UNITS "frames"
            MAX-ACCESS read-write
            STATUS current
            DESCRIPTION
                "The number of frames in advance that a MOB_PAG-ADV message is generated 
                so that the real time part can transmit it in a timely manner. "
            DEFVAL { 30 }
            ::= { asxEbsSectorCfgEntry 94 }

        
        -- 1.3.6.1.4.1.989.1.16.2.7.3.1.1.95
        asxEbsSectorCfgAccuratePagingAdverts OBJECT-TYPE
            SYNTAX AsmaxBooleanSwitch
            MAX-ACCESS read-write
            STATUS current
            DESCRIPTION
                "Set to true (the normal state) causes the non-real time to use 
                the real time MAC's facility to transmit a message on a specific frame. 
                Set to false, and messages are sent to the radio as they are generated. "
            DEFVAL { booleanTrue }
            ::= { asxEbsSectorCfgEntry 95 }

        
        -- 1.3.6.1.4.1.989.1.16.2.7.3.1.1.96
        asxEbsSectorCfgSizeOfCqichIdFieldUcd OBJECT-TYPE
            SYNTAX INTEGER
                {
                bits0(0),
                bits3(1),
                bits4(2),
                bits5(3),
                bits6(4),
                bits7(5),
                bits8(6),
                bits9(7)
                }
            UNITS "bits"
            MAX-ACCESS read-write
            STATUS current
            DESCRIPTION
                "Size of the CQICH Id field (UCD PHY-specific channel encoding TLV 176).
                0 = 0 bits
                1 = 3 bits
                2 = 4 bits
                3 = 5 bits
                4 = 6 bits
                5 = 7 bits
                6 = 8 bits
                7 = 9 bits
                8...255 = Reserved"
            DEFVAL { bits9 }
            ::= { asxEbsSectorCfgEntry 96 }

        
        -- 1.3.6.1.4.1.989.1.16.2.7.3.1.1.97
        asxEbsSectorCfgUlAdaptationEfficiencyMode OBJECT-TYPE
            SYNTAX INTEGER
                {
                spectral(0),
                ms(1)
                }
            MAX-ACCESS read-write
            STATUS current
            DESCRIPTION
                "The uplink adaptation preferencial efficiency mode."
            DEFVAL { spectral }
            ::= { asxEbsSectorCfgEntry 97 }

        
        -- 1.3.6.1.4.1.989.1.16.2.7.3.1.1.98
        asxEbsSectorCfgForceAsnUncontrolledHandover OBJECT-TYPE
            SYNTAX AsmaxBooleanSwitch
            MAX-ACCESS read-write
            STATUS current
            DESCRIPTION
                "Forces handovers in the sector to be uncontrolled from the ASN-Gateway's point of view 
                by suppressing the R6 protocol during the handover preparation phase when set to TRUE.
                Typically used for development and test purposes. Normally set to FALSE."
            DEFVAL { booleanFalse }
            ::= { asxEbsSectorCfgEntry 98 }

        
        -- 1.3.6.1.4.1.989.1.16.2.7.3.1.1.99
        asxEbsSectorCfgCqichReallocationPeriod OBJECT-TYPE
            SYNTAX Integer32 (0..2147483647)
            UNITS "frames"
            MAX-ACCESS read-write
            STATUS current
            DESCRIPTION
                "The period between retransmissions of the CQICH Allocation IE for a CQICH that
                has an indefinite duration (duration = 7).  If this is set to zero then there is
                no retransmission of CQICH allocation IEs; only one allocation IE will be sent
                when the CQICH is created."
            DEFVAL { 200 }
            ::= { asxEbsSectorCfgEntry 99 }

        
        -- 1.3.6.1.4.1.989.1.16.2.7.3.1.1.100
        asxEbsSectorCfgIndefiniteCqichDuration OBJECT-TYPE
            SYNTAX Integer32 (0..7)
            MAX-ACCESS read-write
            STATUS current
            DESCRIPTION
                "The duration of the individual, repeated, CQICH allocations used 
                when a CQICH allocation of an indefinite duration (duration = 7) is required. 
                The duration is calculated as 10*2^n frames where n is configured value of this object."
            DEFVAL { 4 }
            ::= { asxEbsSectorCfgEntry 100 }

        
        -- 1.3.6.1.4.1.989.1.16.2.7.3.1.1.101
        asxEbsSectorCfgMsHoRetransmissionTimer OBJECT-TYPE
            SYNTAX Integer32 (0..255)
            MAX-ACCESS read-write
            STATUS current
            DESCRIPTION
                "The MS HandoverRetransmssion Timer in frames on MOB_MSH_REQ, 
                value sent in TLV30 in a REG-RSP. "
            DEFVAL { 60 }
            ::= { asxEbsSectorCfgEntry 101 }

        
        -- 1.3.6.1.4.1.989.1.16.2.7.3.1.1.102
        asxEbsSectorCfgPowerControlMode OBJECT-TYPE
            SYNTAX INTEGER
                {
                powerCtrlModeCloseLoop(0),
                powerCtrlModeOpenLoopPassiveOffsetSsRetention(1),
                powerCtrlModeOpenLoopPassiveOffsetSsReset(2),
                powerCtrlModeOpenLoopActive(3)
                }
            MAX-ACCESS read-write
            STATUS current
            DESCRIPTION
                "Power control mode for the sector as per PMC-REQ/RSP. Modes currently supported: 
                Macromaxe: closedLoop and openLoopPassiveWithOffsetSsRetention. 
                Others: closedLoop. "
            DEFVAL { powerCtrlModeCloseLoop }
            ::= { asxEbsSectorCfgEntry 102 }

        
        -- 1.3.6.1.4.1.989.1.16.2.7.3.1.1.103
        asxEbsSectorCfgNiIePeriod OBJECT-TYPE
            SYNTAX Integer32 (0..2147483647)
            UNITS "Frames"
            MAX-ACCESS read-write
            STATUS current
            DESCRIPTION
                "NI-IE (Uplink noise and interference level) period in frame numbers. For power control. "
            DEFVAL { 32 }
            ::= { asxEbsSectorCfgEntry 103 }

        
        -- 1.3.6.1.4.1.989.1.16.2.7.3.1.1.104
        asxEbsSectorCfgCarrierSenseThreshold OBJECT-TYPE
            SYNTAX Integer32 (-9600..-6500)
            UNITS "1/100 dBm"
            MAX-ACCESS read-write
            STATUS current
            DESCRIPTION
                "Sets the threshold above which a detection is made. Value is specified in 1/100 dBm in 10 MHz channel.
                NOTE: this feature is enabled or disabled using property asxEbsSectorCfgCarrierSenseEnabled
                If the value is in range  -9600 to -6500 it will be accepted. 
                Any other value will be rejected. Netspan does all the frequency v country checking."
            DEFVAL { -6500 }
            ::= { asxEbsSectorCfgEntry 104 }

        
        -- 1.3.6.1.4.1.989.1.16.2.7.3.1.1.105
        asxEbsSectorCfgCarrierSenseBackoffTime OBJECT-TYPE
            SYNTAX Integer32 (2..2147483647)
            MAX-ACCESS read-write
            STATUS current
            DESCRIPTION
                "Sets the number of frames for which the transmitter is inhibited. 
                Presumably after this time the detector is re-enabled and may disabled the transmitter again."
            DEFVAL { 2 }
            ::= { asxEbsSectorCfgEntry 105 }

        
        -- 1.3.6.1.4.1.989.1.16.2.7.3.1.1.106
        asxEbsSectorCfgDisableDlMgmtHarq OBJECT-TYPE
            SYNTAX AsmaxBooleanSwitch
            MAX-ACCESS read-write
            STATUS current
            DESCRIPTION
                "If 1(booleanTrue), always create DL management connections with HARQ disabled.
                Note inverted boolean logic for this parameter!"
            DEFVAL { booleanFalse }
            ::= { asxEbsSectorCfgEntry 106 }

        
        -- 1.3.6.1.4.1.989.1.16.2.7.3.1.1.107
        asxEbsSectorCfgMsMaxTxPowerBackoff OBJECT-TYPE
            SYNTAX Integer32
            UNITS "1/4 dBm"
            MAX-ACCESS read-write
            STATUS current
            DESCRIPTION
                "A backoff applied to the reported max transmit power of an MS, 
                used to limit MS transmit powers and alter ULM behaviour."
            DEFVAL { 0 }
            ::= { asxEbsSectorCfgEntry 107 }

        
        -- 1.3.6.1.4.1.989.1.16.2.7.3.1.1.108
        asxEbsSectorCfgCarrierSenseEnabled OBJECT-TYPE
            SYNTAX AsmaxBooleanSwitch
            MAX-ACCESS read-write
            STATUS current
            DESCRIPTION
                "Determines whether or not the Carrier Sense feature is enabled"
            DEFVAL { booleanFalse }
            ::= { asxEbsSectorCfgEntry 108 }

        
        -- 1.3.6.1.4.1.989.1.16.2.7.3.1.1.109
        asxEbsSectorCfgRequestedLicensedFeatures OBJECT-TYPE
            SYNTAX AsxEbsBsLicensedFeatures
            MAX-ACCESS read-write
            STATUS current
            DESCRIPTION
                "A set of bits indicating which of the features subject to licensing are currently being configured on this BS TRx.
                Features are configured here irrespective of whether they are currently licensed or not. "
            ::= { asxEbsSectorCfgEntry 109 }

        
        -- 1.3.6.1.4.1.989.1.16.2.7.3.1.1.110
        asxEbsSectorCfgCarrierSenseMonitorPeriod OBJECT-TYPE
            SYNTAX Integer32 (5..300)
            UNITS "s"
            MAX-ACCESS read-write
            STATUS current
            DESCRIPTION
                "The period in secs over which the FCC carrier sense activation count is monitored before a new trap is generated."
            DEFVAL { 30 }
            ::= { asxEbsSectorCfgEntry 110 }

        
        -- 1.3.6.1.4.1.989.1.16.2.7.3.1.1.111
        asxEbsSectorCfgCarrierSenseHighThresholdPercentageMuting OBJECT-TYPE
            SYNTAX Integer32 (1..100)
            UNITS "%"
            MAX-ACCESS read-write
            STATUS current
            DESCRIPTION
                "The percentage muting at which the high level trap is raised."
            DEFVAL { 50 }
            ::= { asxEbsSectorCfgEntry 111 }

        
        -- 1.3.6.1.4.1.989.1.16.2.7.3.1.1.112
        asxEbsSectorCfgCarrierSenseHysteresis OBJECT-TYPE
            SYNTAX Integer32 (-1000..-100)
            UNITS "1/100 dB"
            MAX-ACCESS read-write
            STATUS current
            DESCRIPTION
                "The carrier sense detection hysteresis, relatively to the high detection threshold, 
                defines the lower RSSI detection threshold."
            DEFVAL { -500 }
            ::= { asxEbsSectorCfgEntry 112 }

        
        -- 1.3.6.1.4.1.989.1.16.2.7.3.1.1.113
        asxEbsSectorCfgCarrierSenseContentionTime OBJECT-TYPE
            SYNTAX Integer32 (0..2147483647)
            UNITS "frame"
            MAX-ACCESS read-write
            STATUS current
            DESCRIPTION
                "Sets the number of consecutive frames in which an interference was detected, 
                before shutting down the Tx."
            DEFVAL { 4 }
            ::= { asxEbsSectorCfgEntry 113 }

        
        -- 1.3.6.1.4.1.989.1.16.2.7.3.1.1.114
        asxEbsSectorCfgCarrierSenseMeasurePeriod OBJECT-TYPE
            SYNTAX Integer32 (0..2147483647)
            UNITS "1/10 us"
            MAX-ACCESS read-write
            STATUS current
            DESCRIPTION
                "Duration of each measurement period."
            DEFVAL { 229 }
            ::= { asxEbsSectorCfgEntry 114 }

        
        -- 1.3.6.1.4.1.989.1.16.2.7.3.1.1.115
        asxEbsSectorCfgPrivateMapMode OBJECT-TYPE
            SYNTAX AsxEbsSectorPrivateMapMode
            MAX-ACCESS read-write
            STATUS current
            DESCRIPTION
                "The type of compression to use on the private maps."
            ::= { asxEbsSectorCfgEntry 115 }

        
        -- 1.3.6.1.4.1.989.1.16.2.7.3.1.1.116
        asxEbsSectorCfgPagingAdvertMode OBJECT-TYPE
            SYNTAX INTEGER
                {
                noPeriodic(0),
                staticPeriodic(1),
                dymanicPeriodic(2)
                }
            MAX-ACCESS read-write
            STATUS current
            DESCRIPTION
                "The method of periodic Paging Advertisement."
            DEFVAL { noPeriodic }
            ::= { asxEbsSectorCfgEntry 116 }

        
        -- 1.3.6.1.4.1.989.1.16.2.7.3.1.1.117
        asxEbsSectorCfgStaticPagingAdvertInterval OBJECT-TYPE
            SYNTAX Integer32 (0..2147483647)
            MAX-ACCESS read-write
            STATUS current
            DESCRIPTION
                "Period of static paging advertisement in frames. Valid only when pagingAdvertMode set to static."
            DEFVAL { 5 }
            ::= { asxEbsSectorCfgEntry 117 }

        
        -- 1.3.6.1.4.1.989.1.16.2.7.3.1.1.118
        asxEbsSectorCfgScanScheduleEnable OBJECT-TYPE
            SYNTAX AsmaxBooleanSwitch
            MAX-ACCESS read-write
            STATUS current
            DESCRIPTION
                "Allow the FB to intiate a scheduled scan."
            DEFVAL { booleanFalse }
            ::= { asxEbsSectorCfgEntry 118 }

        
        -- 1.3.6.1.4.1.989.1.16.2.7.3.1.1.119
        asxEbsSectorCfgScanScheduleTriggerTime OBJECT-TYPE
            SYNTAX Integer32
            MAX-ACCESS read-write
            STATUS current
            DESCRIPTION
                "The time at which to intiate a scheduled scan. (Defined as seconds after midnight)"
            DEFVAL { 10800 }
            ::= { asxEbsSectorCfgEntry 119 }

        
        -- 1.3.6.1.4.1.989.1.16.2.7.3.1.1.120
        asxEbsSectorCfgScanInterleavingInterval OBJECT-TYPE
            SYNTAX Integer32
            MAX-ACCESS read-write
            STATUS current
            DESCRIPTION
                "The length, in frames, of the scan interleaving interval."
            DEFVAL { 20 }
            ::= { asxEbsSectorCfgEntry 120 }

        
        -- 1.3.6.1.4.1.989.1.16.2.7.3.1.1.121
        asxEbsSectorCfgScanDuration OBJECT-TYPE
            SYNTAX Integer32
            MAX-ACCESS read-write
            STATUS current
            DESCRIPTION
                "The length, in frames, of the scan duration."
            DEFVAL { 6 }
            ::= { asxEbsSectorCfgEntry 121 }

        
        -- 1.3.6.1.4.1.989.1.16.2.7.3.2
        asxEbsSectorStatusTable OBJECT-TYPE
            SYNTAX SEQUENCE OF AsxEbsSectorStatusEntry
            MAX-ACCESS not-accessible
            STATUS current
            DESCRIPTION
                "Description."
            ::= { asxEbsIf 2 }

        
        -- 1.3.6.1.4.1.989.1.16.2.7.3.2.1
        asxEbsSectorStatusEntry OBJECT-TYPE
            SYNTAX AsxEbsSectorStatusEntry
            MAX-ACCESS not-accessible
            STATUS current
            DESCRIPTION
                "Description."
            INDEX { ifIndex }
            ::= { asxEbsSectorStatusTable 1 }

        
        AsxEbsSectorStatusEntry ::=
            SEQUENCE { 
                asxEbsSectorStatusAchievedTransmitPower
                    Integer32,
                asxEbsSectorStatusAchievedRfGain
                    Integer32,
                asxEbsSectorStatusOperationalLicensedFeatures
                    AsxEbsBsLicensedFeatures,
                asxEbsSectorStatusUnimplementedLicensedFeatures
                    AsxEbsBsLicensedFeatures,
                asxEbsSectorStatusUnimplementedLicensedFeaturesInfo
                    DisplayString,
                asxEbsSectorStatusUnlicensedLicensedFeatures
                    AsxEbsBsLicensedFeatures,
                asxEbsSectorStatusUnlicensedLicensedFeaturesInfo
                    DisplayString,
                asxEbsSectorStatusCurrentPagingAdvertInterval
                    Integer32
             }

        -- 1.3.6.1.4.1.989.1.16.2.7.3.2.1.1
        asxEbsSectorStatusAchievedTransmitPower OBJECT-TYPE
            SYNTAX Integer32 (0..3200)
            UNITS "1/100 dBm"
            MAX-ACCESS read-only
            STATUS current
            DESCRIPTION
                "The transmit power achieved by the basestation. "
            ::= { asxEbsSectorStatusEntry 1 }

        
        -- 1.3.6.1.4.1.989.1.16.2.7.3.2.1.2
        asxEbsSectorStatusAchievedRfGain OBJECT-TYPE
            SYNTAX Integer32 (0..2147483647)
            UNITS "1/100 dB"
            MAX-ACCESS read-only
            STATUS current
            DESCRIPTION
                "The RF gain achieved by the basestation. "
            ::= { asxEbsSectorStatusEntry 2 }

        
        -- 1.3.6.1.4.1.989.1.16.2.7.3.2.1.3
        asxEbsSectorStatusOperationalLicensedFeatures OBJECT-TYPE
            SYNTAX AsxEbsBsLicensedFeatures
            MAX-ACCESS read-only
            STATUS current
            DESCRIPTION
                "A set of bits indicating which of the features subject to licensing are currently operational on this BS TRx.
                They have been both requested and licensed."
            ::= { asxEbsSectorStatusEntry 3 }

        
        -- 1.3.6.1.4.1.989.1.16.2.7.3.2.1.4
        asxEbsSectorStatusUnimplementedLicensedFeatures OBJECT-TYPE
            SYNTAX AsxEbsBsLicensedFeatures
            MAX-ACCESS read-only
            STATUS current
            DESCRIPTION
                "A set of bits indicating which of the features subject to licensing are currently unimplemented on this BS TRx.
                They have been requested but are not implemented on the BS.  Features are reported here irrespective of the state of the licensing."
            ::= { asxEbsSectorStatusEntry 4 }

        
        -- 1.3.6.1.4.1.989.1.16.2.7.3.2.1.5
        asxEbsSectorStatusUnimplementedLicensedFeaturesInfo OBJECT-TYPE
            SYNTAX DisplayString
            MAX-ACCESS read-only
            STATUS current
            DESCRIPTION
                "Provides additional textual information on the unimplemented licensed features"
            ::= { asxEbsSectorStatusEntry 5 }

        
        -- 1.3.6.1.4.1.989.1.16.2.7.3.2.1.6
        asxEbsSectorStatusUnlicensedLicensedFeatures OBJECT-TYPE
            SYNTAX AsxEbsBsLicensedFeatures
            MAX-ACCESS read-only
            STATUS current
            DESCRIPTION
                "A set of bits indicating which of the features subject to licensing are currently unlicensed on this BS TRx.
                They have been requested and are implemented on the BS, but are not currently licensed."
            ::= { asxEbsSectorStatusEntry 6 }

        
        -- 1.3.6.1.4.1.989.1.16.2.7.3.2.1.7
        asxEbsSectorStatusUnlicensedLicensedFeaturesInfo OBJECT-TYPE
            SYNTAX DisplayString
            MAX-ACCESS read-only
            STATUS current
            DESCRIPTION
                "Provides additional textual information on the unlicensed licensed features."
            ::= { asxEbsSectorStatusEntry 7 }

        
        -- 1.3.6.1.4.1.989.1.16.2.7.3.2.1.8
        asxEbsSectorStatusCurrentPagingAdvertInterval OBJECT-TYPE
            SYNTAX Integer32 (0..2147483647)
            MAX-ACCESS read-only
            STATUS current
            DESCRIPTION
                "Period of current paging advertisement in frames"
            DEFVAL { 0 }
            ::= { asxEbsSectorStatusEntry 8 }

        
        -- 1.3.6.1.4.1.989.1.16.2.7.3.3
        asxEbsIpCfgTable OBJECT-TYPE
            SYNTAX SEQUENCE OF AsxEbsIpCfgEntry
            MAX-ACCESS not-accessible
            STATUS current
            DESCRIPTION
                "Allows ethernet port configuration. This is purely used for read-only purpose in Netspan to identify ethernet ports at this moment."
            ::= { asxEbsIf 3 }

        
        -- 1.3.6.1.4.1.989.1.16.2.7.3.3.1
        asxEbsIpCfgEntry OBJECT-TYPE
            SYNTAX AsxEbsIpCfgEntry
            MAX-ACCESS not-accessible
            STATUS current
            DESCRIPTION
                "Description."
            INDEX { ifIndex }
            ::= { asxEbsIpCfgTable 1 }

        
        AsxEbsIpCfgEntry ::=
            SEQUENCE { 
                asxEbsIpCfgIpAddressType
                    InetAddressType,
                asxEbsIpCfgIpAddress
                    InetAddress
             }

        -- 1.3.6.1.4.1.989.1.16.2.7.3.3.1.1
        asxEbsIpCfgIpAddressType OBJECT-TYPE
            SYNTAX InetAddressType
            MAX-ACCESS read-write
            STATUS current
            DESCRIPTION
                "Indicates the type of the IP address assigned to this port. "
            DEFVAL { ipv4 }
            ::= { asxEbsIpCfgEntry 1 }

        
        -- 1.3.6.1.4.1.989.1.16.2.7.3.3.1.2
        asxEbsIpCfgIpAddress OBJECT-TYPE
            SYNTAX InetAddress
            MAX-ACCESS read-write
            STATUS current
            DESCRIPTION
                "The IP address assigned to this port. If there is no address, should take the NULL value. "
            ::= { asxEbsIpCfgEntry 2 }

        
        -- 1.3.6.1.4.1.989.1.16.2.7.3.4
        asxEbsSectorNeighbourTable OBJECT-TYPE
            SYNTAX SEQUENCE OF AsxEbsSectorNeighbourEntry
            MAX-ACCESS not-accessible
            STATUS current
            DESCRIPTION
                "Defines the neighbour sectors."
            ::= { asxEbsIf 4 }

        
        -- 1.3.6.1.4.1.989.1.16.2.7.3.4.1
        asxEbsSectorNeighbourEntry OBJECT-TYPE
            SYNTAX AsxEbsSectorNeighbourEntry
            MAX-ACCESS not-accessible
            STATUS current
            DESCRIPTION
                "Defines the neighbour sectors.
                The ifIndex is the ifIndex of the local sector.
                The asxEbsSectorNeighbourBsId is the BsId of the neighbour sector."
            INDEX { ifIndex, asxEbsSectorNeighbourBsId }
            ::= { asxEbsSectorNeighbourTable 1 }

        
        AsxEbsSectorNeighbourEntry ::=
            SEQUENCE { 
                asxEbsSectorNeighbourBsId
                    AsxEbsBsIdType,
                asxEbsSectorNeighbourIpAddressType
                    InetAddressType,
                asxEbsSectorNeighbourIpAddress
                    InetAddress,
                asxEbsSectorNeighbourRowStatus
                    RowStatus,
                asxEbsSectorNeighbourPreambleSubchannelIndex
                    Integer32,
                asxEbsSectorNeighbourColocated
                    AsmaxBooleanSwitch,
                asxEbsSectorNeighbourUlPermutationBase
                    Integer32
             }

        -- 1.3.6.1.4.1.989.1.16.2.7.3.4.1.1
        asxEbsSectorNeighbourBsId OBJECT-TYPE
            SYNTAX AsxEbsBsIdType
            MAX-ACCESS not-accessible
            STATUS current
            DESCRIPTION
                "The BSID of the neighbour sector."
            ::= { asxEbsSectorNeighbourEntry 1 }

        
        -- 1.3.6.1.4.1.989.1.16.2.7.3.4.1.2
        asxEbsSectorNeighbourIpAddressType OBJECT-TYPE
            SYNTAX InetAddressType
            MAX-ACCESS read-create
            STATUS current
            DESCRIPTION
                "Indicates the type of the IP address assigned to the sector."
            DEFVAL { ipv4 }
            ::= { asxEbsSectorNeighbourEntry 2 }

        
        -- 1.3.6.1.4.1.989.1.16.2.7.3.4.1.3
        asxEbsSectorNeighbourIpAddress OBJECT-TYPE
            SYNTAX InetAddress
            MAX-ACCESS read-create
            STATUS current
            DESCRIPTION
                "The IP address assigned to the neighbour sector."
            DEFVAL { "0.0.0.0" }
            ::= { asxEbsSectorNeighbourEntry 3 }

        
        -- 1.3.6.1.4.1.989.1.16.2.7.3.4.1.4
        asxEbsSectorNeighbourRowStatus OBJECT-TYPE
            SYNTAX RowStatus
            MAX-ACCESS read-create
            STATUS current
            DESCRIPTION
                "Description."
            ::= { asxEbsSectorNeighbourEntry 4 }

        
        -- 1.3.6.1.4.1.989.1.16.2.7.3.4.1.5
        asxEbsSectorNeighbourPreambleSubchannelIndex OBJECT-TYPE
            SYNTAX Integer32
            MAX-ACCESS read-create
            STATUS current
            DESCRIPTION
                "The preamble index (for OFDMA) or the subchannel index (for OFDM)."
            DEFVAL { '0'b }
            ::= { asxEbsSectorNeighbourEntry 5 }

        
        -- 1.3.6.1.4.1.989.1.16.2.7.3.4.1.6
        asxEbsSectorNeighbourColocated OBJECT-TYPE
            SYNTAX AsmaxBooleanSwitch
            MAX-ACCESS read-create
            STATUS current
            DESCRIPTION
                "Set to TRUE if this neighbour is co-located with the transmitting BS. "
            DEFVAL { booleanFalse }
            ::= { asxEbsSectorNeighbourEntry 6 }

        
        -- 1.3.6.1.4.1.989.1.16.2.7.3.4.1.7
        asxEbsSectorNeighbourUlPermutationBase OBJECT-TYPE
            SYNTAX Integer32 (0..31)
            MAX-ACCESS read-create
            STATUS current
            DESCRIPTION
                "The base used for the sub-carrier permutation in uplink PUSC zones in the neighbour sector."
            DEFVAL { 0 }
            ::= { asxEbsSectorNeighbourEntry 7 }

        
        -- 1.3.6.1.4.1.989.1.16.2.7.3.5
        asxEbsSecurityTable OBJECT-TYPE
            SYNTAX SEQUENCE OF AsxEbsSecurityEntry
            MAX-ACCESS not-accessible
            STATUS current
            DESCRIPTION
                "This table allows setting up security related configuration for each wimax interface.
                "
            ::= { asxEbsIf 5 }

        
        -- 1.3.6.1.4.1.989.1.16.2.7.3.5.1
        asxEbsSecurityEntry OBJECT-TYPE
            SYNTAX AsxEbsSecurityEntry
            MAX-ACCESS not-accessible
            STATUS current
            DESCRIPTION
                "This table allows setting up security related configuration for each wimax interface."
            INDEX { ifIndex }
            ::= { asxEbsSecurityTable 1 }

        
        AsxEbsSecurityEntry ::=
            SEQUENCE { 
                asxEbsSecuritySaChallengeTimer
                    Integer32,
                asxEbsSecuritySaChallengeMaxResends
                    Integer32,
                asxEbsSecurityTekLifetime
                    Integer32,
                asxEbsSecurityPmkChangeOverTime
                    Integer32,
                asxEbsSecurityAllowInsecureSs
                    AsmaxBooleanSwitch,
                asxEbsSecurityAllowPkmv1Authentication
                    AsmaxBooleanSwitch,
                asxEbsSecurityAllowPkmv2Authentication
                    AsmaxBooleanSwitch,
                asxEbsSecurityAllowCcmAesKeyWrapEncryption
                    AsmaxBooleanSwitch,
                asxEbsSecurityAllowNoEncryption
                    AsmaxBooleanSwitch
             }

        -- 1.3.6.1.4.1.989.1.16.2.7.3.5.1.1
        asxEbsSecuritySaChallengeTimer OBJECT-TYPE
            SYNTAX Integer32
            MAX-ACCESS read-write
            STATUS current
            DESCRIPTION
                "The time the BS waits after sending an SA TEK challenge before retrying in ms."
            ::= { asxEbsSecurityEntry 1 }

        
        -- 1.3.6.1.4.1.989.1.16.2.7.3.5.1.2
        asxEbsSecuritySaChallengeMaxResends OBJECT-TYPE
            SYNTAX Integer32
            MAX-ACCESS read-write
            STATUS current
            DESCRIPTION
                "The number of times the BS will retry the SA TEK challenge before the SS is signed off."
            ::= { asxEbsSecurityEntry 2 }

        
        -- 1.3.6.1.4.1.989.1.16.2.7.3.5.1.3
        asxEbsSecurityTekLifetime OBJECT-TYPE
            SYNTAX Integer32
            MAX-ACCESS read-write
            STATUS current
            DESCRIPTION
                "The lifetime of the traffic encryption keys in seconds."
            ::= { asxEbsSecurityEntry 3 }

        
        -- 1.3.6.1.4.1.989.1.16.2.7.3.5.1.4
        asxEbsSecurityPmkChangeOverTime OBJECT-TYPE
            SYNTAX Integer32
            MAX-ACCESS read-write
            STATUS current
            DESCRIPTION
                "The time after the completion of the SA TEK 3 way challenge that the old PMK and association AKs must be discarded in ms."
            ::= { asxEbsSecurityEntry 4 }

        
        -- 1.3.6.1.4.1.989.1.16.2.7.3.5.1.5
        asxEbsSecurityAllowInsecureSs OBJECT-TYPE
            SYNTAX AsmaxBooleanSwitch
            MAX-ACCESS read-write
            STATUS current
            DESCRIPTION
                "A value of TRUE will allow SSs that have negotiated no security to enter the network."
            DEFVAL { booleanFalse }
            ::= { asxEbsSecurityEntry 5 }

        
        -- 1.3.6.1.4.1.989.1.16.2.7.3.5.1.6
        asxEbsSecurityAllowPkmv1Authentication OBJECT-TYPE
            SYNTAX AsmaxBooleanSwitch
            MAX-ACCESS read-write
            STATUS current
            DESCRIPTION
                "The BS is to allow PKM version 1 authentication."
            DEFVAL { booleanTrue }
            ::= { asxEbsSecurityEntry 6 }

        
        -- 1.3.6.1.4.1.989.1.16.2.7.3.5.1.7
        asxEbsSecurityAllowPkmv2Authentication OBJECT-TYPE
            SYNTAX AsmaxBooleanSwitch
            MAX-ACCESS read-write
            STATUS current
            DESCRIPTION
                "The BS is to allow PKM version 2 authentication."
            DEFVAL { booleanTrue }
            ::= { asxEbsSecurityEntry 7 }

        
        -- 1.3.6.1.4.1.989.1.16.2.7.3.5.1.8
        asxEbsSecurityAllowCcmAesKeyWrapEncryption OBJECT-TYPE
            SYNTAX AsmaxBooleanSwitch
            MAX-ACCESS read-write
            STATUS current
            DESCRIPTION
                "Enables the BS to use the CCM AES encryption mode with AES key wrapped key encryption. "
            DEFVAL { booleanFalse }
            ::= { asxEbsSecurityEntry 8 }

        
        -- 1.3.6.1.4.1.989.1.16.2.7.3.5.1.9
        asxEbsSecurityAllowNoEncryption OBJECT-TYPE
            SYNTAX AsmaxBooleanSwitch
            MAX-ACCESS read-write
            STATUS current
            DESCRIPTION
                "Enables the BS to use the CCM AES encryption mode with AES key wrapped key encryption. "
            DEFVAL { booleanTrue }
            ::= { asxEbsSecurityEntry 9 }

        
        -- 1.3.6.1.4.1.989.1.16.2.7.3.6
        asxEbsAsnCfgTable OBJECT-TYPE
            SYNTAX SEQUENCE OF AsxEbsAsnCfgEntry
            MAX-ACCESS not-accessible
            STATUS current
            DESCRIPTION
                "This table allows setting up Asn gateway related configuration for each wimax interface."
            ::= { asxEbsIf 6 }

        
        -- 1.3.6.1.4.1.989.1.16.2.7.3.6.1
        asxEbsAsnCfgEntry OBJECT-TYPE
            SYNTAX AsxEbsAsnCfgEntry
            MAX-ACCESS not-accessible
            STATUS current
            DESCRIPTION
                "This table allows setting up Asn gateway related configuration for each wimax interface."
            INDEX { ifIndex }
            ::= { asxEbsAsnCfgTable 1 }

        
        AsxEbsAsnCfgEntry ::=
            SEQUENCE { 
                asxEbsAsnCfgId
                    MacAddress,
                asxEbsAsnCfgUseAsnGateway
                    AsmaxBooleanSwitch,
                asxEbsAsnCfgInetAddressType
                    InetAddressType,
                asxEbsAsnCfgInetAddress
                    InetAddress,
                asxEbsAsnCfgResponseTimeout
                    Integer32,
                asxEbsAsnCfgRequestRetries
                    Integer32,
                asxEbsAsnCfgSfDsxTransactionTime
                    Integer32,
                asxEbsAsnCfgBsInetAddress
                    InetAddress,
                asxEbsAsnCfgGreIpAddressType
                    InetAddressType,
                asxEbsAsnCfgGreIpAddress
                    InetAddress,
                asxEbsAsnCfgAuthenticatorId
                    MacAddress,
                asxEbsAsnCfgPcId
                    MacAddress,
                asxEbsAsnCfgBsNetMask
                    InetAddress,
                asxEbsAsnCfgPcIpAddressType
                    InetAddressType,
                asxEbsAsnCfgPcIpAddress
                    InetAddress,
                asxEbsAsnCfgSecondaryAsnGatewayIpAddress
                    InetAddress,
                asxEbsAsnCfgSecondaryPagingControllerIpAddress
                    InetAddress,
                asxEbsAsnCfgAsnGatewayRedundancyAutoResume
                    AsmaxBooleanSwitch,
                asxEbsAsnCfgAsnGatewayKeepaliveMethod
                    INTEGER,
                asxEbsAsnCfgActiveAsnGateway
                    INTEGER,
                asxEbsAsnCfgActiveAsnGatewayAction
                    INTEGER
             }

        -- 1.3.6.1.4.1.989.1.16.2.7.3.6.1.1
        asxEbsAsnCfgId OBJECT-TYPE
            SYNTAX MacAddress
            MAX-ACCESS read-write
            STATUS current
            DESCRIPTION
                "The 6 byte identifier of the ASN-Gateway used by the Fujitsu family of R6 protocols. Not required when using the Starent family.
                "
            ::= { asxEbsAsnCfgEntry 1 }

        
        -- 1.3.6.1.4.1.989.1.16.2.7.3.6.1.2
        asxEbsAsnCfgUseAsnGateway OBJECT-TYPE
            SYNTAX AsmaxBooleanSwitch
            MAX-ACCESS read-write
            STATUS current
            DESCRIPTION
                "Set to True if this sector is to use an ASN-Gateway."
            DEFVAL { booleanFalse }
            ::= { asxEbsAsnCfgEntry 2 }

        
        -- 1.3.6.1.4.1.989.1.16.2.7.3.6.1.3
        asxEbsAsnCfgInetAddressType OBJECT-TYPE
            SYNTAX InetAddressType
            MAX-ACCESS read-write
            STATUS current
            DESCRIPTION
                "The type of IP address used by the ASN Gateway, if any."
            DEFVAL { ipv4 }
            ::= { asxEbsAsnCfgEntry 3 }

        
        -- 1.3.6.1.4.1.989.1.16.2.7.3.6.1.4
        asxEbsAsnCfgInetAddress OBJECT-TYPE
            SYNTAX InetAddress
            MAX-ACCESS read-write
            STATUS current
            DESCRIPTION
                "The IPv4 or IPv6 address of the ASN-Gateway, if present."
            DEFVAL { "" }
            ::= { asxEbsAsnCfgEntry 4 }

        
        -- 1.3.6.1.4.1.989.1.16.2.7.3.6.1.5
        asxEbsAsnCfgResponseTimeout OBJECT-TYPE
            SYNTAX Integer32
            UNITS "ms"
            MAX-ACCESS read-write
            STATUS current
            DESCRIPTION
                "The time in milliseconds the BS will wait for a response from an ASN-Gateway 
                to requests it has made. "
            DEFVAL { 500 }
            ::= { asxEbsAsnCfgEntry 5 }

        
        -- 1.3.6.1.4.1.989.1.16.2.7.3.6.1.6
        asxEbsAsnCfgRequestRetries OBJECT-TYPE
            SYNTAX Integer32
            MAX-ACCESS read-write
            STATUS current
            DESCRIPTION
                "The number of retries the BS will make of a message while waiting for a response from the 
                ASN-Gateway. "
            DEFVAL { 5 }
            ::= { asxEbsAsnCfgEntry 6 }

        
        -- 1.3.6.1.4.1.989.1.16.2.7.3.6.1.7
        asxEbsAsnCfgSfDsxTransactionTime OBJECT-TYPE
            SYNTAX Integer32
            UNITS "ms"
            MAX-ACCESS read-write
            STATUS current
            DESCRIPTION
                "The time in milliseconds that the BS waits for all the dynamic service flow transactions of 
                a single ASN-Gateway path registration request to complete."
            DEFVAL { 60000 }
            ::= { asxEbsAsnCfgEntry 7 }

        
        -- 1.3.6.1.4.1.989.1.16.2.7.3.6.1.8
        asxEbsAsnCfgBsInetAddress OBJECT-TYPE
            SYNTAX InetAddress
            MAX-ACCESS read-write
            STATUS current
            DESCRIPTION
                "The IPv4 or IPv6 address used by the BS when talking to this sector's ASN-Gateway"
            DEFVAL { "" }
            ::= { asxEbsAsnCfgEntry 8 }

        
        -- 1.3.6.1.4.1.989.1.16.2.7.3.6.1.9
        asxEbsAsnCfgGreIpAddressType OBJECT-TYPE
            SYNTAX InetAddressType
            MAX-ACCESS read-write
            STATUS current
            DESCRIPTION
                "The typo of address of asxEbsAsnCfgGreIpAddress."
            DEFVAL { ipv4 }
            ::= { asxEbsAsnCfgEntry 9 }

        
        -- 1.3.6.1.4.1.989.1.16.2.7.3.6.1.10
        asxEbsAsnCfgGreIpAddress OBJECT-TYPE
            SYNTAX InetAddress
            MAX-ACCESS read-write
            STATUS current
            DESCRIPTION
                "The destination end point address to be used for uplink GRE tunnels 
                when no end point address is explicitly specified by the R6 protocol. 
                If this field is 0.0.0.0, the asnGatewayIpAddress is used instead. "
            DEFVAL { '00000000'h }
            ::= { asxEbsAsnCfgEntry 10 }

        
        -- 1.3.6.1.4.1.989.1.16.2.7.3.6.1.11
        asxEbsAsnCfgAuthenticatorId OBJECT-TYPE
            SYNTAX MacAddress
            MAX-ACCESS read-write
            STATUS current
            DESCRIPTION
                "The 6 byte identifier of the default authenticator ASN-Gateway used by 
                the Fujitsu family of R6 protocols. Not required when using the Starent family. 
                If this value is 0-0-0-0-0-0, the asnGatewayId will be used instead. "
            DEFVAL { '000000000000'h }
            ::= { asxEbsAsnCfgEntry 11 }

        
        -- 1.3.6.1.4.1.989.1.16.2.7.3.6.1.12
        asxEbsAsnCfgPcId OBJECT-TYPE
            SYNTAX MacAddress
            MAX-ACCESS read-write
            STATUS current
            DESCRIPTION
                "The 6 byte identifier of the paging controller ASN-Gateway used by the Fujitsu family 
                of R6 protocols. Not required when using the Starent family. If this value is 0-0-0-0-0-0, 
                the asnGatewayId will be used instead. "
            DEFVAL { '000000000000'h }
            ::= { asxEbsAsnCfgEntry 12 }

        
        -- 1.3.6.1.4.1.989.1.16.2.7.3.6.1.13
        asxEbsAsnCfgBsNetMask OBJECT-TYPE
            SYNTAX InetAddress
            MAX-ACCESS read-write
            STATUS current
            DESCRIPTION
                "The Netmask used by the BS when talking to this sector's ASN-Gateway"
            DEFVAL { "" }
            ::= { asxEbsAsnCfgEntry 13 }

        
        -- 1.3.6.1.4.1.989.1.16.2.7.3.6.1.14
        asxEbsAsnCfgPcIpAddressType OBJECT-TYPE
            SYNTAX InetAddressType
            MAX-ACCESS read-write
            STATUS current
            DESCRIPTION
                "Paging controller Ip address type used by the the Starent v1.1.2. "
            DEFVAL { 1 }
            ::= { asxEbsAsnCfgEntry 14 }

        
        -- 1.3.6.1.4.1.989.1.16.2.7.3.6.1.15
        asxEbsAsnCfgPcIpAddress OBJECT-TYPE
            SYNTAX InetAddress
            MAX-ACCESS read-write
            STATUS current
            DESCRIPTION
                "Paging controller Ip address used by the the Starent v1.1.2. "
            ::= { asxEbsAsnCfgEntry 15 }

        
        -- 1.3.6.1.4.1.989.1.16.2.7.3.6.1.16
        asxEbsAsnCfgSecondaryAsnGatewayIpAddress OBJECT-TYPE
            SYNTAX InetAddress
            MAX-ACCESS read-write
            STATUS current
            DESCRIPTION
                "The IPv4 or IPv6 address of the Secondary ASN-Gateway, if present."
            DEFVAL { "" }
            ::= { asxEbsAsnCfgEntry 16 }

        
        -- 1.3.6.1.4.1.989.1.16.2.7.3.6.1.17
        asxEbsAsnCfgSecondaryPagingControllerIpAddress OBJECT-TYPE
            SYNTAX InetAddress
            MAX-ACCESS read-write
            STATUS current
            DESCRIPTION
                "The IPv4 or IPv6 address of the Secondary Pagind Controller, if present."
            DEFVAL { "" }
            ::= { asxEbsAsnCfgEntry 17 }

        
        -- 1.3.6.1.4.1.989.1.16.2.7.3.6.1.18
        asxEbsAsnCfgAsnGatewayRedundancyAutoResume OBJECT-TYPE
            SYNTAX AsmaxBooleanSwitch
            MAX-ACCESS read-write
            STATUS deprecated
            DESCRIPTION
                "Redundancy auto resome on/off"
            DEFVAL { booleanFalse }
            ::= { asxEbsAsnCfgEntry 18 }

        
        -- 1.3.6.1.4.1.989.1.16.2.7.3.6.1.19
        asxEbsAsnCfgAsnGatewayKeepaliveMethod OBJECT-TYPE
            SYNTAX INTEGER
                {
                disable(0),
                r6(1),
                ping(2)
                }
            MAX-ACCESS read-write
            STATUS deprecated
            DESCRIPTION
                "Keep Alive Method"
            DEFVAL { disable }
            ::= { asxEbsAsnCfgEntry 19 }

        
        -- 1.3.6.1.4.1.989.1.16.2.7.3.6.1.20
        asxEbsAsnCfgActiveAsnGateway OBJECT-TYPE
            SYNTAX INTEGER
                {
                none(0),
                primary(1),
                secondary(2)
                }
            MAX-ACCESS read-only
            STATUS current
            DESCRIPTION
                "Active AswGateway"
            DEFVAL { primary }
            ::= { asxEbsAsnCfgEntry 20 }

        
        -- 1.3.6.1.4.1.989.1.16.2.7.3.6.1.21
        asxEbsAsnCfgActiveAsnGatewayAction OBJECT-TYPE
            SYNTAX INTEGER
                {
                none(0),
                reconfigured(1),
                switched(2),
                restarted(3),
                lost(4)
                }
            MAX-ACCESS read-only
            STATUS current
            DESCRIPTION
                "Active ASN gateway action"
            DEFVAL { none }
            ::= { asxEbsAsnCfgEntry 21 }

        
        -- 1.3.6.1.4.1.989.1.16.2.7.3.7
        asxEbsArqCfgTable OBJECT-TYPE
            SYNTAX SEQUENCE OF AsxEbsArqCfgEntry
            MAX-ACCESS not-accessible
            STATUS current
            DESCRIPTION
                "This table allows setting up Arq related configuration for each wimax interface."
            ::= { asxEbsIf 7 }

        
        -- 1.3.6.1.4.1.989.1.16.2.7.3.7.1
        asxEbsArqCfgEntry OBJECT-TYPE
            SYNTAX AsxEbsArqCfgEntry
            MAX-ACCESS not-accessible
            STATUS current
            DESCRIPTION
                "This table allows setting up Arq related configuration for each wimax interface."
            INDEX { ifIndex }
            ::= { asxEbsArqCfgTable 1 }

        
        AsxEbsArqCfgEntry ::=
            SEQUENCE { 
                asxEbsArqT22Duration
                    Integer32,
                asxEbsArqTransmitterDelay
                    Integer32,
                asxEbsArqReceiverDelay
                    Integer32,
                asxEbsArqMinSsReceiverDelay
                    Integer32,
                asxEbsArqT22RetryCount
                    Integer32,
                asxEbsArqCfgHarqAckDelay
                    Integer32,
                asxEbsArqCfgHarqNumAckChannels
                    Integer32
             }

        -- 1.3.6.1.4.1.989.1.16.2.7.3.7.1.1
        asxEbsArqT22Duration OBJECT-TYPE
            SYNTAX Integer32 (0..500)
            UNITS "ms"
            MAX-ACCESS read-write
            STATUS current
            DESCRIPTION
                "The length of time that is allowed for the other party to respond to an ARQ Reset control message during an ARQ reset operation. in ms."
            DEFVAL { 500 }
            ::= { asxEbsArqCfgEntry 1 }

        
        -- 1.3.6.1.4.1.989.1.16.2.7.3.7.1.2
        asxEbsArqTransmitterDelay OBJECT-TYPE
            SYNTAX Integer32 (10..6553)
            UNITS "ms"
            MAX-ACCESS read-write
            STATUS current
            DESCRIPTION
                "The total ARQ transmitter delay, including sending data and receiving acknowledgements. The retry timeout for downlink ARQ connections is the sum of this delay and the receiver delay communicated by the subscriber. in ms."
            DEFVAL { 10 }
            ::= { asxEbsArqCfgEntry 2 }

        
        -- 1.3.6.1.4.1.989.1.16.2.7.3.7.1.3
        asxEbsArqReceiverDelay OBJECT-TYPE
            SYNTAX Integer32 (10..6553)
            UNITS "ms"
            MAX-ACCESS read-write
            STATUS current
            DESCRIPTION
                "The total ARQ receiver delay, including receiving data and sending acknowledgements. This timeout is communicated to the subscriber, and the retry timeout for uplink connections is the sum of this delay and the subscriber's own transmitter delay. in ms."
            DEFVAL { 10 }
            ::= { asxEbsArqCfgEntry 3 }

        
        -- 1.3.6.1.4.1.989.1.16.2.7.3.7.1.4
        asxEbsArqMinSsReceiverDelay OBJECT-TYPE
            SYNTAX Integer32 (10..6553)
            UNITS "ms"
            MAX-ACCESS read-write
            STATUS current
            DESCRIPTION
                "The minimum value for the ARQ receiver delay indicated by the SS for a downlink connection. The BS will use this value when calculating the retry timeout if the value indicated by the SS is lower. in ms."
            DEFVAL { 10 }
            ::= { asxEbsArqCfgEntry 4 }

        
        -- 1.3.6.1.4.1.989.1.16.2.7.3.7.1.5
        asxEbsArqT22RetryCount OBJECT-TYPE
            SYNTAX Integer32 (1..20)
            MAX-ACCESS read-write
            STATUS current
            DESCRIPTION
                "The number of times an ARQ reset operation will be reattempted before the operation is abandoned and the connection is taken down. "
            DEFVAL { 3 }
            ::= { asxEbsArqCfgEntry 5 }

        
        -- 1.3.6.1.4.1.989.1.16.2.7.3.7.1.6
        asxEbsArqCfgHarqAckDelay OBJECT-TYPE
            SYNTAX Integer32 (0..2147483647)
            MAX-ACCESS read-write
            STATUS current
            DESCRIPTION
                "The H-ARQ ACK delay advertised in the UCD (TLV 171)."
            DEFVAL { 3 }
            ::= { asxEbsArqCfgEntry 6 }

        
        -- 1.3.6.1.4.1.989.1.16.2.7.3.7.1.7
        asxEbsArqCfgHarqNumAckChannels OBJECT-TYPE
            SYNTAX Integer32 (0..2147483647)
            UNITS "0.5 slot"
            MAX-ACCESS read-write
            STATUS current
            DESCRIPTION
                "The number of HARQ ACK channels that will be allocated in each frame 
                when the HARQ ACK delay parameter is set to 1. 
                If the HARQ ACK delay is set to 2 or 3, this parameter is ignored 
                and the number of HARQ ACK channels is automatically determined for each frame. "
            DEFVAL { 12 }
            ::= { asxEbsArqCfgEntry 7 }

        
        -- 1.3.6.1.4.1.989.1.16.2.7.3.8
        asxEbsHoTriggerTable OBJECT-TYPE
            SYNTAX SEQUENCE OF AsxEbsHoTriggerEntry
            MAX-ACCESS not-accessible
            STATUS current
            DESCRIPTION
                "Description."
            ::= { asxEbsIf 8 }

        
        -- 1.3.6.1.4.1.989.1.16.2.7.3.8.1
        asxEbsHoTriggerEntry OBJECT-TYPE
            SYNTAX AsxEbsHoTriggerEntry
            MAX-ACCESS not-accessible
            STATUS current
            DESCRIPTION
                "Description."
            INDEX { ifIndex, asxEbsHoTriggerId }
            ::= { asxEbsHoTriggerTable 1 }

        
        AsxEbsHoTriggerEntry ::=
            SEQUENCE { 
                asxEbsHoTriggerId
                    Integer32,
                asxEbsHoTriggerType
                    INTEGER,
                asxEbsHoTriggerFn
                    INTEGER,
                asxEbsHoTriggerMsAction
                    INTEGER,
                asxEbsHoTriggerTypeVal
                    Integer32,
                asxEbsHoTriggerAveragingDuration
                    Integer32,
                asxEbsHoTriggerRowStatus
                    RowStatus
             }

        -- 1.3.6.1.4.1.989.1.16.2.7.3.8.1.1
        asxEbsHoTriggerId OBJECT-TYPE
            SYNTAX Integer32 (1..65535)
            MAX-ACCESS not-accessible
            STATUS current
            DESCRIPTION
                "Description."
            ::= { asxEbsHoTriggerEntry 1 }

        
        -- 1.3.6.1.4.1.989.1.16.2.7.3.8.1.2
        asxEbsHoTriggerType OBJECT-TYPE
            SYNTAX INTEGER
                {
                cinr(0),
                rssi(1),
                rtd(2)
                }
            MAX-ACCESS read-create
            STATUS current
            DESCRIPTION
                "Which type of handover trigger metric MSs should employ when signed onto this sector. "
            DEFVAL { cinr }
            ::= { asxEbsHoTriggerEntry 2 }

        
        -- 1.3.6.1.4.1.989.1.16.2.7.3.8.1.3
        asxEbsHoTriggerFn OBJECT-TYPE
            SYNTAX INTEGER
                {
                neighbourGtAbs(1),
                neighbourLtAbs(2),
                neighbourGtRel(3),
                neighbourLtRel(4),
                servingGtAbs(5),
                servingLtAbs(6)
                }
            MAX-ACCESS read-create
            STATUS current
            DESCRIPTION
                "The function an MS should apply to the trigger metric to determine handover"
            DEFVAL { servingLtAbs }
            ::= { asxEbsHoTriggerEntry 3 }

        
        -- 1.3.6.1.4.1.989.1.16.2.7.3.8.1.4
        asxEbsHoTriggerMsAction OBJECT-TYPE
            SYNTAX INTEGER
                {
                scanReport(1),
                msHoReq(2),
                scanReq(3)
                }
            MAX-ACCESS read-create
            STATUS current
            DESCRIPTION
                "What an MS should do when a trigger fires."
            DEFVAL { msHoReq }
            ::= { asxEbsHoTriggerEntry 4 }

        
        -- 1.3.6.1.4.1.989.1.16.2.7.3.8.1.5
        asxEbsHoTriggerTypeVal OBJECT-TYPE
            SYNTAX Integer32
            MAX-ACCESS read-create
            STATUS current
            DESCRIPTION
                "The value against which the trigger metric is compared."
            DEFVAL { 0 }
            ::= { asxEbsHoTriggerEntry 5 }

        
        -- 1.3.6.1.4.1.989.1.16.2.7.3.8.1.6
        asxEbsHoTriggerAveragingDuration OBJECT-TYPE
            SYNTAX Integer32
            MAX-ACCESS read-create
            STATUS current
            DESCRIPTION
                "Trigger metric averaging duration "
            DEFVAL { 10 }
            ::= { asxEbsHoTriggerEntry 6 }

        
        -- 1.3.6.1.4.1.989.1.16.2.7.3.8.1.7
        asxEbsHoTriggerRowStatus OBJECT-TYPE
            SYNTAX RowStatus
            MAX-ACCESS read-create
            STATUS current
            DESCRIPTION
                "Tracks the state of the row"
            ::= { asxEbsHoTriggerEntry 7 }

        
        -- 1.3.6.1.4.1.989.1.16.2.7.3.9
        asxEbsPagingGroupTable OBJECT-TYPE
            SYNTAX SEQUENCE OF AsxEbsPagingGroupEntry
            MAX-ACCESS not-accessible
            STATUS current
            DESCRIPTION
                "Description."
            ::= { asxEbsIf 9 }

        
        -- 1.3.6.1.4.1.989.1.16.2.7.3.9.1
        asxEbsPagingGroupEntry OBJECT-TYPE
            SYNTAX AsxEbsPagingGroupEntry
            MAX-ACCESS not-accessible
            STATUS current
            DESCRIPTION
                "Description."
            INDEX { ifIndex, asxEbsPagingGroupId }
            ::= { asxEbsPagingGroupTable 1 }

        
        AsxEbsPagingGroupEntry ::=
            SEQUENCE { 
                asxEbsPagingGroupId
                    Integer32,
                asxEbsPagingGroupInterval
                    Integer32,
                asxEbsPagingGroupRowStatus
                    RowStatus
             }

        -- 1.3.6.1.4.1.989.1.16.2.7.3.9.1.1
        asxEbsPagingGroupId OBJECT-TYPE
            SYNTAX Integer32 (1..2147483647)
            MAX-ACCESS not-accessible
            STATUS current
            DESCRIPTION
                "Paging group ID. "
            ::= { asxEbsPagingGroupEntry 1 }

        
        -- 1.3.6.1.4.1.989.1.16.2.7.3.9.1.2
        asxEbsPagingGroupInterval OBJECT-TYPE
            SYNTAX Integer32 (1..65535)
            UNITS "frames"
            MAX-ACCESS read-create
            STATUS current
            DESCRIPTION
                "Paging Interval (frames) for the paging group. "
            DEFVAL { 2 }
            ::= { asxEbsPagingGroupEntry 2 }

        
        -- 1.3.6.1.4.1.989.1.16.2.7.3.9.1.3
        asxEbsPagingGroupRowStatus OBJECT-TYPE
            SYNTAX RowStatus
            MAX-ACCESS read-create
            STATUS current
            DESCRIPTION
                "Description."
            ::= { asxEbsPagingGroupEntry 3 }

        
        -- 1.3.6.1.4.1.989.1.16.2.7.3.10
        asxEbsPagingCycleTable OBJECT-TYPE
            SYNTAX SEQUENCE OF AsxEbsPagingCycleEntry
            MAX-ACCESS not-accessible
            STATUS current
            DESCRIPTION
                "Description."
            ::= { asxEbsIf 10 }

        
        -- 1.3.6.1.4.1.989.1.16.2.7.3.10.1
        asxEbsPagingCycleEntry OBJECT-TYPE
            SYNTAX AsxEbsPagingCycleEntry
            MAX-ACCESS not-accessible
            STATUS current
            DESCRIPTION
                "Description."
            INDEX { ifIndex, asxEbsPagingGroupId, asxEbsPagingCycleId }
            ::= { asxEbsPagingCycleTable 1 }

        
        AsxEbsPagingCycleEntry ::=
            SEQUENCE { 
                asxEbsPagingCycleId
                    Integer32,
                asxEbsPagingCycleNumber
                    Integer32,
                asxEbsPagingCycleRowStatus
                    RowStatus
             }

        -- 1.3.6.1.4.1.989.1.16.2.7.3.10.1.1
        asxEbsPagingCycleId OBJECT-TYPE
            SYNTAX Integer32 (1..2147483647)
            MAX-ACCESS not-accessible
            STATUS current
            DESCRIPTION
                "Paging cycle Id. "
            ::= { asxEbsPagingCycleEntry 1 }

        
        -- 1.3.6.1.4.1.989.1.16.2.7.3.10.1.2
        asxEbsPagingCycleNumber OBJECT-TYPE
            SYNTAX Integer32 (1..65535)
            UNITS "frames"
            MAX-ACCESS read-create
            STATUS current
            DESCRIPTION
                "paging cycle (frames)."
            DEFVAL { 1000 }
            ::= { asxEbsPagingCycleEntry 2 }

        
        -- 1.3.6.1.4.1.989.1.16.2.7.3.10.1.4
        asxEbsPagingCycleRowStatus OBJECT-TYPE
            SYNTAX RowStatus
            MAX-ACCESS read-create
            STATUS current
            DESCRIPTION
                "Description."
            ::= { asxEbsPagingCycleEntry 4 }

        
        -- 1.3.6.1.4.1.989.1.16.2.7.3.11
        asxEbsPagingOpportunityTable OBJECT-TYPE
            SYNTAX SEQUENCE OF AsxEbsPagingOpportunityEntry
            MAX-ACCESS not-accessible
            STATUS current
            DESCRIPTION
                "Description."
            ::= { asxEbsIf 11 }

        
        -- 1.3.6.1.4.1.989.1.16.2.7.3.11.1
        asxEbsPagingOpportunityEntry OBJECT-TYPE
            SYNTAX AsxEbsPagingOpportunityEntry
            MAX-ACCESS not-accessible
            STATUS current
            DESCRIPTION
                "Description."
            INDEX { ifIndex, asxEbsPagingGroupId, asxEbsPagingCycleId, asxEbsPagingOpportunityId }
            ::= { asxEbsPagingOpportunityTable 1 }

        
        AsxEbsPagingOpportunityEntry ::=
            SEQUENCE { 
                asxEbsPagingOpportunityId
                    Integer32,
                asxEbsPagingOpportunityOffset
                    Integer32,
                asxEbsPagingOpportunityRowStatus
                    RowStatus
             }

        -- 1.3.6.1.4.1.989.1.16.2.7.3.11.1.1
        asxEbsPagingOpportunityId OBJECT-TYPE
            SYNTAX Integer32 (1..2147483647)
            MAX-ACCESS not-accessible
            STATUS current
            DESCRIPTION
                "paging opportunity Id."
            ::= { asxEbsPagingOpportunityEntry 1 }

        
        -- 1.3.6.1.4.1.989.1.16.2.7.3.11.1.2
        asxEbsPagingOpportunityOffset OBJECT-TYPE
            SYNTAX Integer32 (0..65534)
            UNITS "frames"
            MAX-ACCESS read-create
            STATUS current
            DESCRIPTION
                "Paging offset (frames) per paging cycle. Set as max value of pagingcycle minus paging interval. "
            DEFVAL { 0 }
            ::= { asxEbsPagingOpportunityEntry 2 }

        
        -- 1.3.6.1.4.1.989.1.16.2.7.3.11.1.3
        asxEbsPagingOpportunityRowStatus OBJECT-TYPE
            SYNTAX RowStatus
            MAX-ACCESS read-create
            STATUS current
            DESCRIPTION
                "Description."
            ::= { asxEbsPagingOpportunityEntry 3 }

        
        -- 1.3.6.1.4.1.989.1.16.2.7.3.12
        asxEbsRrmCfgTable OBJECT-TYPE
            SYNTAX SEQUENCE OF AsxEbsRrmCfgEntry
            MAX-ACCESS not-accessible
            STATUS current
            DESCRIPTION
                "Groups all the sector properties relevant to RRM and in particular
                to fast RRM adaptive algorithms."
            ::= { asxEbsIf 12 }

        
        -- 1.3.6.1.4.1.989.1.16.2.7.3.12.1
        asxEbsRrmCfgEntry OBJECT-TYPE
            SYNTAX AsxEbsRrmCfgEntry
            MAX-ACCESS not-accessible
            STATUS current
            DESCRIPTION
                "Description."
            INDEX { ifIndex }
            ::= { asxEbsRrmCfgTable 1 }

        
        AsxEbsRrmCfgEntry ::=
            SEQUENCE { 
                asxEbsRrmCfgCinrAlphaLow
                    Integer32,
                asxEbsRrmCfgCinrAlphaHigh
                    Integer32,
                asxEbsRrmCfgClpcDeadband
                    Integer32,
                asxEbsRrmCfgDlCinrAlpha
                    Integer32,
                asxEbsRrmCfgDlMimoMcsDown
                    Integer32,
                asxEbsRrmCfgDlMimoMcsUp
                    Integer32,
                asxEbsRrmCfgDlReuseMcsDown
                    Integer32,
                asxEbsRrmCfgDlReuseMcsUp
                    Integer32,
                asxEbsRrmCfgRepReqInterval
                    Integer32,
                asxEbsRrmCfgDlMcsThreshStartReuse1CinrReport
                    Integer32,
                asxEbsRrmCfgDlMcsThreshStopReuse1CinrReport
                    Integer32,
                asxEbsRrmCfgDlThreshHighMcsNumInReuse3
                    Integer32,
                asxEbsRrmCfgDlThreshLowMcsNumInReuse3
                    Integer32,
                asxEbsRrmCfgDlPcinrThreshToReuse1
                    Integer32,
                asxEbsRrmCfgDlMcsThreshToReuse3
                    Integer32,
                asxEbsRrmCfgDlThreshLowMcsNumInReuse1
                    Integer32,
                asxEbsRrmCfgDlDefaultMcs
                    Integer32,
                asxEbsRrmCfgDlDefaultRepetition
                    Integer32,
                asxEbsRrmCfgDlPcinrMargin
                    Integer32,
                asxEbsRrmCfgDlPcinrHysteresis
                    Integer32,
                asxEbsRrmCfgDisableFastDlDynamicSelection
                    AsmaxBooleanSwitch,
                asxEbsRrmCfgDlMcsMargin
                    Integer32,
                asxEbsRrmCfgPreferDlPcinrReport
                    AsmaxBooleanSwitch,
                asxEbsRrmCfgIncludeTxPowerReport
                    AsmaxBooleanSwitch,
                asxEbsRrmCfgTxPowerReportThreshold
                    Integer32,
                asxEbsRrmCfgTxPowerReportInterval
                    Integer32,
                asxEbsRrmCfgTxPowerReportAlpha
                    Integer32,
                asxEbsRrmCfgTxPowerReportCqichThreshold
                    Integer32,
                asxEbsRrmCfgTxPowerReportCqichInterval
                    Integer32,
                asxEbsRrmCfgTxPowerReportCqichAlpha
                    Integer32,
                asxEbsRrmCfgUlCinrMargin
                    Integer32,
                asxEbsRrmCfgExcessBwBetaVal
                    Integer32,
                asxEbsRrmCfgDlCinrAlphaLow
                    Integer32,
                asxEbsRrmCfgDlCinrAlphaHigh
                    Integer32,
                asxEbsRrmCfgMatrixBThresholdCinr
                    Integer32,
                asxEbsRrmCfgMatrixBExtraMargin
                    Integer32,
                asxEbsRrmCfgMatrixBMinMcs
                    Integer32,
                asxEbsRrmCfgMatrixBMaxMcs
                    WmanIf2OfdmaDcdFecCode,
                asxEbsRrmCfgDlR3PcinrThreshold
                    Integer32,
                asxEbsRrmCfgDlMngPcinrMargin
                    Integer32,
                asxEbsRrmCfgDlHarqErrWindowSize
                    Integer32,
                asxEbsRrmCfgDlHarqErrFastWindowSize
                    Integer32,
                asxEbsRrmCfgDlHarqErrLow
                    Integer32,
                asxEbsRrmCfgDlHarqErrHigh
                    Integer32,
                asxEbsRrmCfgDlHarqErrFastHigh
                    Integer32,
                asxEbsRrmCfgDlHarqPurgeTimeout
                    Integer32
             }

        -- 1.3.6.1.4.1.989.1.16.2.7.3.12.1.1
        asxEbsRrmCfgCinrAlphaLow OBJECT-TYPE
            SYNTAX Integer32 (0..100)
            UNITS "%"
            MAX-ACCESS read-write
            STATUS current
            DESCRIPTION
                "The alpha factor used by the CINR filter when the input falls below the previous output."
            DEFVAL { 90 }
            ::= { asxEbsRrmCfgEntry 1 }

        
        -- 1.3.6.1.4.1.989.1.16.2.7.3.12.1.2
        asxEbsRrmCfgCinrAlphaHigh OBJECT-TYPE
            SYNTAX Integer32 (0..100)
            UNITS "%"
            MAX-ACCESS read-write
            STATUS current
            DESCRIPTION
                "The alpha factor used by the CINR filter when the input falls above the previous output."
            DEFVAL { 10 }
            ::= { asxEbsRrmCfgEntry 2 }

        
        -- 1.3.6.1.4.1.989.1.16.2.7.3.12.1.3
        asxEbsRrmCfgClpcDeadband OBJECT-TYPE
            SYNTAX Integer32 (0..12)
            UNITS "0.25 dB"
            MAX-ACCESS read-write
            STATUS current
            DESCRIPTION
                "No power offset will be issued if the CINR falls into the deadband."
            DEFVAL { 4 }
            ::= { asxEbsRrmCfgEntry 3 }

        
        -- 1.3.6.1.4.1.989.1.16.2.7.3.12.1.4
        asxEbsRrmCfgDlCinrAlpha OBJECT-TYPE
            SYNTAX Integer32 (0..100)
            UNITS "%"
            MAX-ACCESS read-write
            STATUS current
            DESCRIPTION
                "The alpha factor used by the CINR filter at all MSs of the sector."
            DEFVAL { 50 }
            ::= { asxEbsRrmCfgEntry 4 }

        
        -- 1.3.6.1.4.1.989.1.16.2.7.3.12.1.5
        asxEbsRrmCfgDlMimoMcsDown OBJECT-TYPE
            SYNTAX Integer32 (0..8)
            MAX-ACCESS read-write
            STATUS current
            DESCRIPTION
                "The reduction in MCS level for predicting the MCS of Matrix-B."
            DEFVAL { 5 }
            ::= { asxEbsRrmCfgEntry 5 }

        
        -- 1.3.6.1.4.1.989.1.16.2.7.3.12.1.6
        asxEbsRrmCfgDlMimoMcsUp OBJECT-TYPE
            SYNTAX Integer32 (0..5)
            MAX-ACCESS read-write
            STATUS current
            DESCRIPTION
                "The increase in MCS level for predicting the MCS of Matrix-A."
            DEFVAL { 3 }
            ::= { asxEbsRrmCfgEntry 6 }

        
        -- 1.3.6.1.4.1.989.1.16.2.7.3.12.1.7
        asxEbsRrmCfgDlReuseMcsDown OBJECT-TYPE
            SYNTAX Integer32 (0..8)
            MAX-ACCESS read-write
            STATUS current
            DESCRIPTION
                "The reduction in MCS level for predicting the MCS of Reuse-1."
            DEFVAL { 3 }
            ::= { asxEbsRrmCfgEntry 7 }

        
        -- 1.3.6.1.4.1.989.1.16.2.7.3.12.1.8
        asxEbsRrmCfgDlReuseMcsUp OBJECT-TYPE
            SYNTAX Integer32 (0..5)
            MAX-ACCESS read-write
            STATUS current
            DESCRIPTION
                "The increase in MCS level for predicting the MCS of Reuse-3."
            DEFVAL { 3 }
            ::= { asxEbsRrmCfgEntry 8 }

        
        -- 1.3.6.1.4.1.989.1.16.2.7.3.12.1.9
        asxEbsRrmCfgRepReqInterval OBJECT-TYPE
            SYNTAX Integer32 (0..2147483647)
            UNITS "Frames"
            MAX-ACCESS read-write
            STATUS current
            DESCRIPTION
                "The min interval between two consecutive REP-REQ for Reuse-1 preamble CINR."
            DEFVAL { 200 }
            ::= { asxEbsRrmCfgEntry 9 }

        
        -- 1.3.6.1.4.1.989.1.16.2.7.3.12.1.10
        asxEbsRrmCfgDlMcsThreshStartReuse1CinrReport OBJECT-TYPE
            SYNTAX Integer32 (13..21)
            MAX-ACCESS read-write
            STATUS current
            DESCRIPTION
                "The Reuse-3 MCS at which the Reuse-1 preamble CINR should be polled."
            DEFVAL { 16 }
            ::= { asxEbsRrmCfgEntry 10 }

        
        -- 1.3.6.1.4.1.989.1.16.2.7.3.12.1.11
        asxEbsRrmCfgDlMcsThreshStopReuse1CinrReport OBJECT-TYPE
            SYNTAX Integer32 (13..21)
            MAX-ACCESS read-write
            STATUS current
            DESCRIPTION
                "The Reuse-3 MCS at which should stop polling the Reuse-1 preamble CINR."
            DEFVAL { 15 }
            ::= { asxEbsRrmCfgEntry 11 }

        
        -- 1.3.6.1.4.1.989.1.16.2.7.3.12.1.12
        asxEbsRrmCfgDlThreshHighMcsNumInReuse3 OBJECT-TYPE
            SYNTAX Integer32 (1..2147483647)
            MAX-ACCESS read-write
            STATUS current
            DESCRIPTION
                "The number of consecutive high MCS in Reuse-3 at which enable the Reuse-1 preamble CINR polling. "
            DEFVAL { 1 }
            ::= { asxEbsRrmCfgEntry 12 }

        
        -- 1.3.6.1.4.1.989.1.16.2.7.3.12.1.13
        asxEbsRrmCfgDlThreshLowMcsNumInReuse3 OBJECT-TYPE
            SYNTAX Integer32 (1..2147483647)
            MAX-ACCESS read-write
            STATUS current
            DESCRIPTION
                "The number of consecutive high MCS in Reuse-3 at which enable the Reuse-1 preamble CINR polling. "
            DEFVAL { 1 }
            ::= { asxEbsRrmCfgEntry 13 }

        
        -- 1.3.6.1.4.1.989.1.16.2.7.3.12.1.14
        asxEbsRrmCfgDlPcinrThreshToReuse1 OBJECT-TYPE
            SYNTAX Integer32 (18..120)
            UNITS "0.25 dBm"
            MAX-ACCESS read-write
            STATUS current
            DESCRIPTION
                "The threshold of Reuse-1 preamble CINR at which switching to Reuse-1 (and Matrix-A)."
            DEFVAL { 26 }
            ::= { asxEbsRrmCfgEntry 14 }

        
        -- 1.3.6.1.4.1.989.1.16.2.7.3.12.1.15
        asxEbsRrmCfgDlMcsThreshToReuse3 OBJECT-TYPE
            SYNTAX Integer32 (13..21)
            MAX-ACCESS read-write
            STATUS current
            DESCRIPTION
                "The Reuse-1 MCS at which may switch to Reuse-3 Matrix-A.
                The value configured corresponds to FEC code defined by the textual convention
                WmanIf2OfdmaDcdFecCode as follows:
                qpskCtc1Over2(13),
                reserved14(14),
                qpskCtc3Over4(15),
                sixteenQamCtc1Over2(16),
                sixteenQamCtc3Over4(17),
                sixtyFourQamCtc1Over2(18), etc.
                "
            DEFVAL { 13 }
            ::= { asxEbsRrmCfgEntry 15 }

        
        -- 1.3.6.1.4.1.989.1.16.2.7.3.12.1.16
        asxEbsRrmCfgDlThreshLowMcsNumInReuse1 OBJECT-TYPE
            SYNTAX Integer32 (1..2147483647)
            MAX-ACCESS read-write
            STATUS current
            DESCRIPTION
                "The number of consecutive low MCS in Reuse-1 at which switch to Reuse-3 Matrix-A. "
            DEFVAL { 1 }
            ::= { asxEbsRrmCfgEntry 16 }

        
        -- 1.3.6.1.4.1.989.1.16.2.7.3.12.1.17
        asxEbsRrmCfgDlDefaultMcs OBJECT-TYPE
            SYNTAX Integer32 (13..21)
            MAX-ACCESS read-write
            STATUS current
            DESCRIPTION
                "The default MCS for predicting MCS of different reuse and MIMO mode.
                The value configured corresponds to FEC code defined by the textual convention
                WmanIf2OfdmaDcdFecCode as follows:
                qpskCtc1Over2(13),
                reserved14(14),
                qpskCtc3Over4(15),
                sixteenQamCtc1Over2(16),
                sixteenQamCtc3Over4(17),
                sixtyFourQamCtc1Over2(18), etc.
                "
            DEFVAL { 15 }
            ::= { asxEbsRrmCfgEntry 17 }

        
        -- 1.3.6.1.4.1.989.1.16.2.7.3.12.1.18
        asxEbsRrmCfgDlDefaultRepetition OBJECT-TYPE
            SYNTAX Integer32 (0..3)
            MAX-ACCESS read-write
            STATUS current
            DESCRIPTION
                "The default repetition rate for predicting MCS of different reuse and MIMO mode."
            DEFVAL { 0 }
            ::= { asxEbsRrmCfgEntry 18 }

        
        -- 1.3.6.1.4.1.989.1.16.2.7.3.12.1.19
        asxEbsRrmCfgDlPcinrMargin OBJECT-TYPE
            SYNTAX Integer32 (0..60)
            UNITS "0.25 dB"
            MAX-ACCESS read-write
            STATUS current
            DESCRIPTION
                "The margin applied to the DL PCINR report (through CQICH). "
            DEFVAL { 0 }
            ::= { asxEbsRrmCfgEntry 19 }

        
        -- 1.3.6.1.4.1.989.1.16.2.7.3.12.1.20
        asxEbsRrmCfgDlPcinrHysteresis OBJECT-TYPE
            SYNTAX Integer32 (0..60)
            UNITS "0.25 dBm"
            MAX-ACCESS read-write
            STATUS current
            DESCRIPTION
                "Hysteresis parameter. 0.25dB units. Maybe used to calculate the exit threshold
                from entry threshold if required."
            DEFVAL { 0 }
            ::= { asxEbsRrmCfgEntry 20 }

        
        -- 1.3.6.1.4.1.989.1.16.2.7.3.12.1.21
        asxEbsRrmCfgDisableFastDlDynamicSelection OBJECT-TYPE
            SYNTAX AsmaxBooleanSwitch
            MAX-ACCESS read-write
            STATUS current
            DESCRIPTION
                "Set TRUE to disable fast downlink dynamic control using CQICH and REP-RSP polling."
            DEFVAL { booleanFalse }
            ::= { asxEbsRrmCfgEntry 21 }

        
        -- 1.3.6.1.4.1.989.1.16.2.7.3.12.1.22
        asxEbsRrmCfgDlMcsMargin OBJECT-TYPE
            SYNTAX Integer32 (-5..5)
            MAX-ACCESS read-write
            STATUS current
            DESCRIPTION
                "The margin applied to the DL ECINR report (MCS level through CQICH)."
            DEFVAL { 0 }
            ::= { asxEbsRrmCfgEntry 22 }

        
        -- 1.3.6.1.4.1.989.1.16.2.7.3.12.1.23
        asxEbsRrmCfgPreferDlPcinrReport OBJECT-TYPE
            SYNTAX AsmaxBooleanSwitch
            MAX-ACCESS read-write
            STATUS current
            DESCRIPTION
                "MS sends PCINR report even it supports ECINR report."
            DEFVAL { booleanTrue }
            ::= { asxEbsRrmCfgEntry 23 }

        
        -- 1.3.6.1.4.1.989.1.16.2.7.3.12.1.24
        asxEbsRrmCfgIncludeTxPowerReport OBJECT-TYPE
            SYNTAX AsmaxBooleanSwitch
            MAX-ACCESS read-write
            STATUS current
            DESCRIPTION
                "Set to true to include the transmit power report TLV 196 in the UCD."
            DEFVAL { booleanFalse }
            ::= { asxEbsRrmCfgEntry 24 }

        
        -- 1.3.6.1.4.1.989.1.16.2.7.3.12.1.25
        asxEbsRrmCfgTxPowerReportThreshold OBJECT-TYPE
            SYNTAX Integer32 (0..15)
            UNITS "dBm"
            MAX-ACCESS read-write
            STATUS current
            DESCRIPTION
                "Transmit power report threshold as expected in UCD TLV 196. 
                15=infinite."
            DEFVAL { 0 }
            ::= { asxEbsRrmCfgEntry 25 }

        
        -- 1.3.6.1.4.1.989.1.16.2.7.3.12.1.26
        asxEbsRrmCfgTxPowerReportInterval OBJECT-TYPE
            SYNTAX Integer32 (0..15)
            MAX-ACCESS read-write
            STATUS current
            DESCRIPTION
                "Transmit power report interval (d) as expected in UCD TLV 196 (where actual interval=2^d).
                15=infinite."
            DEFVAL { 0 }
            ::= { asxEbsRrmCfgEntry 26 }

        
        -- 1.3.6.1.4.1.989.1.16.2.7.3.12.1.27
        asxEbsRrmCfgTxPowerReportAlpha OBJECT-TYPE
            SYNTAX Integer32 (1..16)
            UNITS "1/16"
            MAX-ACCESS read-write
            STATUS current
            DESCRIPTION
                "Transmit power report alpha in UCD TLV 196 (1=1/16, 16=16/16)."
            DEFVAL { 1 }
            ::= { asxEbsRrmCfgEntry 27 }

        
        -- 1.3.6.1.4.1.989.1.16.2.7.3.12.1.28
        asxEbsRrmCfgTxPowerReportCqichThreshold OBJECT-TYPE
            SYNTAX Integer32 (0..15)
            UNITS "dBm"
            MAX-ACCESS read-write
            STATUS current
            DESCRIPTION
                "Transmit power report threshold as expected in UCD TLV 196. 
                15=infinite. 
                Used when CQICH is allocated to SS."
            DEFVAL { 0 }
            ::= { asxEbsRrmCfgEntry 28 }

        
        -- 1.3.6.1.4.1.989.1.16.2.7.3.12.1.29
        asxEbsRrmCfgTxPowerReportCqichInterval OBJECT-TYPE
            SYNTAX Integer32 (0..15)
            MAX-ACCESS read-write
            STATUS current
            DESCRIPTION
                "Transmit power report interval (d) as expected in UCD TLV 196 (where actual interval=2^d). 
                15=infinite. 
                Used when CQICH is allocated to SS."
            DEFVAL { 0 }
            ::= { asxEbsRrmCfgEntry 29 }

        
        -- 1.3.6.1.4.1.989.1.16.2.7.3.12.1.30
        asxEbsRrmCfgTxPowerReportCqichAlpha OBJECT-TYPE
            SYNTAX Integer32 (1..16)
            UNITS "1/16"
            MAX-ACCESS read-write
            STATUS current
            DESCRIPTION
                "Transmit power report alpha in UCD TLV 196 (1=1/16, 16=16/16). 
                Used when CQICH is allocated to SS."
            DEFVAL { 1 }
            ::= { asxEbsRrmCfgEntry 30 }

        
        -- 1.3.6.1.4.1.989.1.16.2.7.3.12.1.31
        asxEbsRrmCfgUlCinrMargin OBJECT-TYPE
            SYNTAX Integer32 (0..40)
            UNITS "0.25 dB"
            MAX-ACCESS read-write
            STATUS current
            DESCRIPTION
                "Uplink CINR margin for uplink dynamic modulation RRM algorithm."
            DEFVAL { 16 }
            ::= { asxEbsRrmCfgEntry 31 }

        
        -- 1.3.6.1.4.1.989.1.16.2.7.3.12.1.32
        asxEbsRrmCfgExcessBwBetaVal OBJECT-TYPE
            SYNTAX Integer32 (0..100)
            MAX-ACCESS read-write
            STATUS current
            DESCRIPTION
                "Weight assigned to link conditions in scheduler metric (arbitrary values). 
                Paramater of APFS (Adaptive Proportional Fair Scheduling).
                The weight paramater should be optimised to balance between fairness 
                and aggregated system efficiency. 
                Seting the value to zero implies that channel conditions
                are not considered and the excess bandwidth should be scheduled fairly between users.
                Setting the value to infinity implies that flows with poor channel conditions (low MCS)
                shall starve."
            DEFVAL { 0 }
            ::= { asxEbsRrmCfgEntry 32 }

        
        -- 1.3.6.1.4.1.989.1.16.2.7.3.12.1.33
        asxEbsRrmCfgDlCinrAlphaLow OBJECT-TYPE
            SYNTAX Integer32 (0..100)
            UNITS "%"
            MAX-ACCESS read-write
            STATUS current
            DESCRIPTION
                "The alpha factor used by the DLM CINR filter when the input falls below the previous output"
            DEFVAL { 90 }
            ::= { asxEbsRrmCfgEntry 33 }

        
        -- 1.3.6.1.4.1.989.1.16.2.7.3.12.1.34
        asxEbsRrmCfgDlCinrAlphaHigh OBJECT-TYPE
            SYNTAX Integer32 (0..100)
            UNITS "%"
            MAX-ACCESS read-write
            STATUS current
            DESCRIPTION
                "The alpha factor used by the DLM CINR filter when the input falls above the previous output"
            DEFVAL { 10 }
            ::= { asxEbsRrmCfgEntry 34 }

        
        -- 1.3.6.1.4.1.989.1.16.2.7.3.12.1.35
        asxEbsRrmCfgMatrixBThresholdCinr OBJECT-TYPE
            SYNTAX Integer32
            UNITS "0.25dB"
            MAX-ACCESS read-write
            STATUS current
            DESCRIPTION
                "The threshold CINR value below which Matrix B is NOT selected."
            DEFVAL { 40 }
            ::= { asxEbsRrmCfgEntry 35 }

        
        -- 1.3.6.1.4.1.989.1.16.2.7.3.12.1.36
        asxEbsRrmCfgMatrixBExtraMargin OBJECT-TYPE
            SYNTAX Integer32 (0..62)
            UNITS "0.25 dB"
            MAX-ACCESS read-write
            STATUS current
            DESCRIPTION
                "The additional margin applied to DL PCINR report when using MatrixB. "
            DEFVAL { 16 }
            ::= { asxEbsRrmCfgEntry 36 }

        
        -- 1.3.6.1.4.1.989.1.16.2.7.3.12.1.37
        asxEbsRrmCfgMatrixBMinMcs OBJECT-TYPE
            SYNTAX Integer32 (0..2147483647)
            MAX-ACCESS read-write
            STATUS current
            DESCRIPTION
                "The minimum MCS required for MatrixB allocation. 
                This is the MCS level (index in burst profile table)."
            DEFVAL { 4 }
            ::= { asxEbsRrmCfgEntry 37 }

        
        -- 1.3.6.1.4.1.989.1.16.2.7.3.12.1.38
        asxEbsRrmCfgMatrixBMaxMcs OBJECT-TYPE
            SYNTAX WmanIf2OfdmaDcdFecCode
            MAX-ACCESS read-write
            STATUS current
            DESCRIPTION
                "The maximum modulation/FEC to be used for MatrixB allocations.
                Note that unlike the (sector table) matrixBMinMcs, this is
                in MCS, NOT an index into a table of MCS."
            DEFVAL { sixtyFourQamCtc5Over6 }
            ::= { asxEbsRrmCfgEntry 38 }

        
        -- 1.3.6.1.4.1.989.1.16.2.7.3.12.1.39
        asxEbsRrmCfgDlR3PcinrThreshold OBJECT-TYPE
            SYNTAX Integer32 (0..120)
            UNITS "0.25 dB"
            MAX-ACCESS read-write
            STATUS current
            DESCRIPTION
                "Permutation Zone PCINR to trigger switching from R1 zone to R3 zone."
            DEFVAL { 28 }
            ::= { asxEbsRrmCfgEntry 39 }

        
        -- 1.3.6.1.4.1.989.1.16.2.7.3.12.1.40
        asxEbsRrmCfgDlMngPcinrMargin OBJECT-TYPE
            SYNTAX Integer32 (0..120)
            UNITS "0.25 dB"
            MAX-ACCESS read-write
            STATUS current
            DESCRIPTION
                "Margin subtracted from average PCINR before MCS lookup 
                for selecting MCS for management connections. "
            DEFVAL { 48 }
            ::= { asxEbsRrmCfgEntry 40 }

        
        -- 1.3.6.1.4.1.989.1.16.2.7.3.12.1.41
        asxEbsRrmCfgDlHarqErrWindowSize OBJECT-TYPE
            SYNTAX Integer32 (0..128)
            MAX-ACCESS read-write
            STATUS current
            DESCRIPTION
                "Size of window to monitor HARQ error rate. "
            DEFVAL { 32 }
            ::= { asxEbsRrmCfgEntry 41 }

        
        -- 1.3.6.1.4.1.989.1.16.2.7.3.12.1.42
        asxEbsRrmCfgDlHarqErrFastWindowSize OBJECT-TYPE
            SYNTAX Integer32 (0..128)
            MAX-ACCESS read-write
            STATUS current
            DESCRIPTION
                "Size of window to monitor high HARQ error rate."
            DEFVAL { 8 }
            ::= { asxEbsRrmCfgEntry 42 }

        
        -- 1.3.6.1.4.1.989.1.16.2.7.3.12.1.43
        asxEbsRrmCfgDlHarqErrLow OBJECT-TYPE
            SYNTAX Integer32 (0..40)
            UNITS "%"
            MAX-ACCESS read-write
            STATUS current
            DESCRIPTION
                "Error rate threshold to trigger low HARQ error rate event."
            DEFVAL { 2 }
            ::= { asxEbsRrmCfgEntry 43 }

        
        -- 1.3.6.1.4.1.989.1.16.2.7.3.12.1.44
        asxEbsRrmCfgDlHarqErrHigh OBJECT-TYPE
            SYNTAX Integer32 (0..40)
            UNITS "%"
            MAX-ACCESS read-write
            STATUS current
            DESCRIPTION
                "Description."
            DEFVAL { 10 }
            ::= { asxEbsRrmCfgEntry 44 }

        
        -- 1.3.6.1.4.1.989.1.16.2.7.3.12.1.45
        asxEbsRrmCfgDlHarqErrFastHigh OBJECT-TYPE
            SYNTAX Integer32 (0..40)
            UNITS "%"
            MAX-ACCESS read-write
            STATUS current
            DESCRIPTION
                "Error rate threshold to trigger high HARQ error rate event."
            DEFVAL { 30 }
            ::= { asxEbsRrmCfgEntry 45 }

        
        -- 1.3.6.1.4.1.989.1.16.2.7.3.12.1.46
        asxEbsRrmCfgDlHarqPurgeTimeout OBJECT-TYPE
            SYNTAX Integer32 (1..100)
            UNITS "10 ms"
            MAX-ACCESS read-write
            STATUS current
            DESCRIPTION
                "In case HARQ error window for an MS was not advanced in this time interval, 
                HARQ MCS shall be driven from PCINR."
            DEFVAL { 10 }
            ::= { asxEbsRrmCfgEntry 46 }

        
        -- 1.3.6.1.4.1.989.1.16.2.7.3.13
        asxEbsMcastMemberTable OBJECT-TYPE
            SYNTAX SEQUENCE OF AsxEbsMcastMemberEntry
            MAX-ACCESS not-accessible
            STATUS current
            DESCRIPTION
                "Description."
            ::= { asxEbsIf 13 }

        
        -- 1.3.6.1.4.1.989.1.16.2.7.3.13.1
        asxEbsMcastMemberEntry OBJECT-TYPE
            SYNTAX AsxEbsMcastMemberEntry
            MAX-ACCESS not-accessible
            STATUS current
            DESCRIPTION
                "Description."
            INDEX { ifIndex, wmanIf2fBsSfId, wmanIf2BsSsMacAddress }
            ::= { asxEbsMcastMemberTable 1 }

        
        AsxEbsMcastMemberEntry ::=
            SEQUENCE { 
                asxEbsMcastMemberDeleteCmd
                    INTEGER,
                asxEbsMcastMemberCurAdmissionState
                    INTEGER,
                asxEbsMcastMemberState
                    INTEGER,
                asxEbsMcastMemberTransState
                    INTEGER
             }

        -- 1.3.6.1.4.1.989.1.16.2.7.3.13.1.1
        asxEbsMcastMemberDeleteCmd OBJECT-TYPE
            SYNTAX INTEGER
                {
                idle(0),
                do(1)
                }
            MAX-ACCESS read-write
            STATUS current
            DESCRIPTION
                "Description."
            DEFVAL { idle }
            ::= { asxEbsMcastMemberEntry 1 }

        
        -- 1.3.6.1.4.1.989.1.16.2.7.3.13.1.2
        asxEbsMcastMemberCurAdmissionState OBJECT-TYPE
            SYNTAX INTEGER
                {
                provisioned(1),
                admitted(2),
                active(3)
                }
            MAX-ACCESS read-write
            STATUS current
            DESCRIPTION
                "Description."
            DEFVAL { provisioned }
            ::= { asxEbsMcastMemberEntry 2 }

        
        -- 1.3.6.1.4.1.989.1.16.2.7.3.13.1.3
        asxEbsMcastMemberState OBJECT-TYPE
            SYNTAX INTEGER
                {
                null(0),
                addingLocal(1),
                addingRemote(2),
                nominal(3),
                changingLocal(4),
                changingRemote(5),
                deleting(6),
                addingLocalPending(7),
                addingRemotePending(8),
                changingLocalPending(9),
                changingRemotePending(10),
                deletingPending(11),
                waiting(12),
                errorDeleting(13),
                nominalPending(14),
                handingOver(15),
                greTunnelEndPoint(16),
                greTunnelEndPointHo(17)
                }
            MAX-ACCESS read-write
            STATUS current
            DESCRIPTION
                "Description."
            DEFVAL { null }
            ::= { asxEbsMcastMemberEntry 3 }

        
        -- 1.3.6.1.4.1.989.1.16.2.7.3.13.1.4
        asxEbsMcastMemberTransState OBJECT-TYPE
            SYNTAX INTEGER
                {
                null(0),
                flowControl(1),
                responsePending(2),
                holdingDownOk(3),
                holdingDownFail(4),
                holdingDownError(5)
                }
            MAX-ACCESS read-write
            STATUS current
            DESCRIPTION
                "Description."
            DEFVAL { null }
            ::= { asxEbsMcastMemberEntry 4 }

        
        -- 1.3.6.1.4.1.989.1.16.2.7.4
        asxEbsDevice OBJECT IDENTIFIER ::= { asMaxEbs 4 }

        
        -- 1.3.6.1.4.1.989.1.16.2.7.4.1
        asxEbsBsCfgTable OBJECT-TYPE
            SYNTAX SEQUENCE OF AsxEbsBsCfgEntry
            MAX-ACCESS not-accessible
            STATUS current
            DESCRIPTION
                "Table grouping per BS management properties."
            ::= { asxEbsDevice 1 }

        
        -- 1.3.6.1.4.1.989.1.16.2.7.4.1.1
        asxEbsBsCfgEntry OBJECT-TYPE
            SYNTAX AsxEbsBsCfgEntry
            MAX-ACCESS not-accessible
            STATUS current
            DESCRIPTION
                "Description."
            INDEX { asxEbsBsIndex }
            ::= { asxEbsBsCfgTable 1 }

        
        AsxEbsBsCfgEntry ::=
            SEQUENCE { 
                asxEbsBsIndex
                    Integer32,
                asxEbsBsFramePeriodOfdma
                    INTEGER,
                asxEbsBsCfgAAAServerIpAddressType
                    InetAddressType,
                asxEbsBsCfgAAAServerIpAddress
                    InetAddress,
                asxEbsBsCfgAAAServerTimerPeriod
                    Integer32,
                asxEbsBsCfgAAAServerToSsTimerPeriod
                    Integer32,
                asxEbsBsCfgAAAServerPassword
                    DisplayString,
                asxEbsBsCfgAAAServerSharedSecret
                    DisplayString,
                asxEbsBsCfgResetPhy
                    INTEGER,
                asxEbsBsCfgMgmtPortIfIndex
                    InterfaceIndex,
                asxEbsBsCfgResetRequest
                    INTEGER,
                asxEbsBsCfgAsnGatewayProtocolFamily
                    INTEGER,
                asxEbsBsCfgAsnGatewayProtocolVersion
                    INTEGER,
                asxEbsBsCfgClockSourceForSync
                    INTEGER,
                asxEbsBsCfgNumAntennas
                    Unsigned32,
                asxEbsBsCfgOperationalStatus
                    AsxEbsOperationalStatus,
                asxEbsBsCfgPagingMacHashLifetime
                    Integer32,
                asxEbsBsCfgPagingMacHashTransmissions
                    Integer32,
                asxEbsBsCfgNoSignalCinrThreshold
                    Integer32,
                asxEbsBsCfgRfDlPropagationDelay
                    Integer32,
                asxEbsBsCfgRfUlPropagationDelay
                    Integer32,
                asxEbsBsCfgAlarmThresholdLowGain
                    Integer32,
                asxEbsBsCfgAlarmThresholdHighGain
                    Integer32,
                asxEbsBsCfgAlarmThresholdVswr
                    Integer32,
                asxEbsBsCfgPhyFrameIndAdvance
                    Integer32,
                asxEbsBsCfgFrameBuildTimeLimit
                    Integer32,
                asxEbsBsCfgFrameBuildPduLimit
                    Integer32,
                asxEbsBsCfgDiversityMode
                    INTEGER,
                asxEbsBsCfgDegradedTxPowerReduction
                    Integer32,
                asxEbsBsCfgPhyApiErrorThreshold
                    Integer32,
                asxEbsBsCfgArpRetryPeriod
                    Integer32,
                asxEbsBsCfgArpRefreshPeriod
                    Integer32,
                asxEbsBsCfgPhyActivityMonitorPeriod
                    Integer32,
                asxEbsBsCfgEncryptionLicenceCertificate
                    OCTET STRING,
                asxEbsBsCfgRequestedMobilityMode
                    AsxEbsMobilityMode,
                asxEbsBsCfgFeatureLicenceCertificate
                    OCTET STRING,
                asxEbsBsCfgUseNtp
                    AsmaxBooleanSwitch,
                asxEbsBsCfgAAAServerPort
                    Integer32,
                asxEbsBsCfgAAAServerMyIpAddressType
                    InetAddressType,
                asxEbsBsCfgAAAServerMyIpAddress
                    InetAddress,
                asxEbsBsCfgAAAServerAccountingPort
                    Integer32,
                asxEbsBsCfgRelayAgentCircuitId
                    OCTET STRING,
                asxEbsBsCfgNumberOfAntennas
                    Unsigned32,
                asxEbsBsCfgNumberOfSectors
                    Integer32,
                asxEbsBsCfgRtFileLogLevel
                    Integer32,
                asxEbsBsCfgGpsAdjustHoldoff
                    Integer32,
                asxEbsBsCfgPaCurrentAlarmMinThresh
                    Integer32,
                asxEbsBsCfgPaCurrentAlarmMaxThresh
                    Integer32,
                asxEbsBsCfgAntMismatchAlarmThresh
                    Integer32,
                asxEbsBsCfgLowFwdPwrAlarmThresh
                    Integer32,
                asxEbsBsCfgAaaCompatibilityMode
                    INTEGER,
                asxEbsBsCfgAaaAcctInterimPeriod
                    Integer32,
                asxEbsBsCfgAsnGatewayRedundancyAutoResume
                    AsmaxBooleanSwitch,
                asxEbsBsCfgAsnGatewayKeepaliveMethod
                    INTEGER
             }

        -- 1.3.6.1.4.1.989.1.16.2.7.4.1.1.1
        asxEbsBsIndex OBJECT-TYPE
            SYNTAX Integer32 (1)
            MAX-ACCESS accessible-for-notify
            STATUS current
            DESCRIPTION
                "Arbitrary index - only one instance ever."
            ::= { asxEbsBsCfgEntry 1 }

        
        -- 1.3.6.1.4.1.989.1.16.2.7.4.1.1.2
        asxEbsBsFramePeriodOfdma OBJECT-TYPE
            SYNTAX INTEGER
                {
                framePeriod2ms(1),
                framePeriod2dot5ms(2),
                framePeriod4ms(3),
                framePeriod5ms(4),
                framePeriod8ms(5),
                framePeriod10ms(6),
                framePeriod12dot5ms(7),
                framePeriod20ms(8)
                }
            MAX-ACCESS read-write
            STATUS current
            DESCRIPTION
                "Common frame duration for all the OFDMA sectors of the BS."
            ::= { asxEbsBsCfgEntry 2 }

        
        -- 1.3.6.1.4.1.989.1.16.2.7.4.1.1.3
        asxEbsBsCfgAAAServerIpAddressType OBJECT-TYPE
            SYNTAX InetAddressType
            MAX-ACCESS read-write
            STATUS current
            DESCRIPTION
                "The type of IP address of the AAA Server, if used."
            DEFVAL { ipv4 }
            ::= { asxEbsBsCfgEntry 3 }

        
        -- 1.3.6.1.4.1.989.1.16.2.7.4.1.1.4
        asxEbsBsCfgAAAServerIpAddress OBJECT-TYPE
            SYNTAX InetAddress
            MAX-ACCESS read-write
            STATUS current
            DESCRIPTION
                "The IP address of the AAA Server, if used."
            DEFVAL { "0.0.0.0" }
            ::= { asxEbsBsCfgEntry 4 }

        
        -- 1.3.6.1.4.1.989.1.16.2.7.4.1.1.5
        asxEbsBsCfgAAAServerTimerPeriod OBJECT-TYPE
            SYNTAX Integer32
            UNITS "s"
            MAX-ACCESS read-write
            STATUS current
            DESCRIPTION
                "The Timer Expiry Period in seconds for messages to the AAA Server."
            DEFVAL { 15 }
            ::= { asxEbsBsCfgEntry 5 }

        
        -- 1.3.6.1.4.1.989.1.16.2.7.4.1.1.6
        asxEbsBsCfgAAAServerToSsTimerPeriod OBJECT-TYPE
            SYNTAX Integer32
            UNITS "s"
            MAX-ACCESS read-write
            STATUS current
            DESCRIPTION
                "The Timer Expiry Period in seconds for messages to the AAA Server."
            DEFVAL { 15 }
            ::= { asxEbsBsCfgEntry 6 }

        
        -- 1.3.6.1.4.1.989.1.16.2.7.4.1.1.7
        asxEbsBsCfgAAAServerPassword OBJECT-TYPE
            SYNTAX DisplayString
            MAX-ACCESS read-write
            STATUS obsolete
            DESCRIPTION
                "The user password for the protocol to the AAA server."
            DEFVAL { "password" }
            ::= { asxEbsBsCfgEntry 7 }

        
        -- 1.3.6.1.4.1.989.1.16.2.7.4.1.1.8
        asxEbsBsCfgAAAServerSharedSecret OBJECT-TYPE
            SYNTAX DisplayString
            MAX-ACCESS read-write
            STATUS current
            DESCRIPTION
                "The shared secret used by the protocol to the AAA server."
            DEFVAL { "sharedsecret" }
            ::= { asxEbsBsCfgEntry 8 }

        
        -- 1.3.6.1.4.1.989.1.16.2.7.4.1.1.9
        asxEbsBsCfgResetPhy OBJECT-TYPE
            SYNTAX INTEGER
                {
                actionResetPhyIdle(0),
                actionResetPhyDo(1)
                }
            MAX-ACCESS read-write
            STATUS current
            DESCRIPTION
                "Performs a Picochip PHY reset."
            DEFVAL { actionResetPhyIdle }
            ::= { asxEbsBsCfgEntry 9 }

        
        -- 1.3.6.1.4.1.989.1.16.2.7.4.1.1.10
        asxEbsBsCfgMgmtPortIfIndex OBJECT-TYPE
            SYNTAX InterfaceIndex
            MAX-ACCESS read-write
            STATUS current
            DESCRIPTION
                "The ifIndex of the interface that management traffic is expected on. 
                If this value indicates one of the traffic ports, the managementVlan and 
                managementUserPriority fields are used to place the traffic in a VLAN on the port. 
                If the value indicates one of the management ports, the management traffic is untagged. "
            ::= { asxEbsBsCfgEntry 10 }

        
        -- 1.3.6.1.4.1.989.1.16.2.7.4.1.1.11
        asxEbsBsCfgResetRequest OBJECT-TYPE
            SYNTAX INTEGER
                {
                idle(0),
                resetAll(1),
                resetSdrOnly(2),
                resetMsmOnly(3),
                resetRfOnly(4),
                resetRf0Only(5),
                resetRf1Only(6),
                resetSoftwareAll(7)
                }
            MAX-ACCESS read-write
            STATUS current
            DESCRIPTION
                "Request to reset the card and/or other physically attached cards."
            DEFVAL { idle }
            ::= { asxEbsBsCfgEntry 11 }

        
        -- 1.3.6.1.4.1.989.1.16.2.7.4.1.1.12
        asxEbsBsCfgAsnGatewayProtocolFamily OBJECT-TYPE
            SYNTAX INTEGER
                {
                generic(0),
                starent(1),
                fujitsu(2),
                wichorus(3),
                aricent(4)
                }
            MAX-ACCESS read-write
            STATUS current
            DESCRIPTION
                "Which family of ASN-Gateway protocols the BS is to support."
            DEFVAL { starent }
            ::= { asxEbsBsCfgEntry 12 }

        
        -- 1.3.6.1.4.1.989.1.16.2.7.4.1.1.13
        asxEbsBsCfgAsnGatewayProtocolVersion OBJECT-TYPE
            SYNTAX INTEGER
                {
                v1p0p0(1),
                v1p1p1(2),
                v1p1p2(3)
                }
            MAX-ACCESS read-write
            STATUS current
            DESCRIPTION
                "Which version of ASN-Gateway protocol the BS is to support."
            DEFVAL { v1p0p0 }
            ::= { asxEbsBsCfgEntry 13 }

        
        -- 1.3.6.1.4.1.989.1.16.2.7.4.1.1.14
        asxEbsBsCfgClockSourceForSync OBJECT-TYPE
            SYNTAX INTEGER
                {
                gpsWithSuppress(0),
                gpsNoSuppress(1),
                internal(2),
                invalid(3)
                }
            MAX-ACCESS read-write
            STATUS current
            DESCRIPTION
                "The source of the clock sync reference signal."
            DEFVAL { gpsWithSuppress }
            ::= { asxEbsBsCfgEntry 14 }

        
        -- 1.3.6.1.4.1.989.1.16.2.7.4.1.1.15
        asxEbsBsCfgNumAntennas OBJECT-TYPE
            SYNTAX Unsigned32
            MAX-ACCESS read-write
            STATUS deprecated
            DESCRIPTION
                "The number of antennas used by the PHY. This value is used for all sectors in the card.
                This property is now superceded by asxEbsBsCfgNumberOfAntennas property"
            DEFVAL { 2 }
            ::= { asxEbsBsCfgEntry 15 }

        
        -- 1.3.6.1.4.1.989.1.16.2.7.4.1.1.16
        asxEbsBsCfgOperationalStatus OBJECT-TYPE
            SYNTAX AsxEbsOperationalStatus
            MAX-ACCESS read-write
            STATUS current
            DESCRIPTION
                "The requested operational status for the basestation."
            DEFVAL { operationalStatusOutOfService }
            ::= { asxEbsBsCfgEntry 16 }

        
        -- 1.3.6.1.4.1.989.1.16.2.7.4.1.1.17
        asxEbsBsCfgPagingMacHashLifetime OBJECT-TYPE
            SYNTAX Integer32 (0..2147483647)
            UNITS "ms"
            MAX-ACCESS read-write
            STATUS current
            DESCRIPTION
                "The lifetime of a paging MAC hash announcement before it is automatically deleted. "
            DEFVAL { 600000 }
            ::= { asxEbsBsCfgEntry 17 }

        
        -- 1.3.6.1.4.1.989.1.16.2.7.4.1.1.18
        asxEbsBsCfgPagingMacHashTransmissions OBJECT-TYPE
            SYNTAX Integer32 (0..2147483647)
            MAX-ACCESS read-write
            STATUS current
            DESCRIPTION
                "The number of times a paging MAC hash announcement is transmitted before it is automatically deleted."
            DEFVAL { 3 }
            ::= { asxEbsBsCfgEntry 18 }

        
        -- 1.3.6.1.4.1.989.1.16.2.7.4.1.1.19
        asxEbsBsCfgNoSignalCinrThreshold OBJECT-TYPE
            SYNTAX Integer32
            UNITS "0.25 dB"
            MAX-ACCESS read-write
            STATUS current
            DESCRIPTION
                "The threshold for uplink burst CINR below which the burst is considered to contain 
                no valid signal. Such bursts are not used for the purposes of uplink link adaptation 
                or power control. "
            DEFVAL { -50 }
            ::= { asxEbsBsCfgEntry 19 }

        
        -- 1.3.6.1.4.1.989.1.16.2.7.4.1.1.20
        asxEbsBsCfgRfDlPropagationDelay OBJECT-TYPE
            SYNTAX Integer32 (0..2147483647)
            UNITS "1/22.4 MHz"
            MAX-ACCESS read-write
            STATUS current
            DESCRIPTION
                "The downlink propagation delay through the RF module that will be used 
                to adjust the frame alignment to the 1pps GPS signal. "
            DEFVAL { 0 }
            ::= { asxEbsBsCfgEntry 20 }

        
        -- 1.3.6.1.4.1.989.1.16.2.7.4.1.1.21
        asxEbsBsCfgRfUlPropagationDelay OBJECT-TYPE
            SYNTAX Integer32 (0..2147483647)
            UNITS "1/22.4 MHz"
            MAX-ACCESS read-write
            STATUS current
            DESCRIPTION
                "The uplink propagation delay through the RF module that will be passed down 
                to the PicoArrays and used to adjust the uplink timing. "
            DEFVAL { 0 }
            ::= { asxEbsBsCfgEntry 21 }

        
        -- 1.3.6.1.4.1.989.1.16.2.7.4.1.1.22
        asxEbsBsCfgAlarmThresholdLowGain OBJECT-TYPE
            SYNTAX Integer32 (-7..-1)
            UNITS "dB"
            MAX-ACCESS read-write
            STATUS current
            DESCRIPTION
                "Specifies the theshold at which a low gain alarm will be generated."
            DEFVAL { -6 }
            ::= { asxEbsBsCfgEntry 22 }

        
        -- 1.3.6.1.4.1.989.1.16.2.7.4.1.1.23
        asxEbsBsCfgAlarmThresholdHighGain OBJECT-TYPE
            SYNTAX Integer32 (1..7)
            UNITS "dB"
            MAX-ACCESS read-write
            STATUS current
            DESCRIPTION
                "Specifies the theshold at which a high gain alarm will be generated."
            DEFVAL { 3 }
            ::= { asxEbsBsCfgEntry 23 }

        
        -- 1.3.6.1.4.1.989.1.16.2.7.4.1.1.24
        asxEbsBsCfgAlarmThresholdVswr OBJECT-TYPE
            SYNTAX Integer32 (0..9)
            UNITS "dB"
            MAX-ACCESS read-write
            STATUS current
            DESCRIPTION
                "Specifies the theshold at which a VSWR alarm will be generated."
            DEFVAL { 6 }
            ::= { asxEbsBsCfgEntry 24 }

        
        -- 1.3.6.1.4.1.989.1.16.2.7.4.1.1.25
        asxEbsBsCfgPhyFrameIndAdvance OBJECT-TYPE
            SYNTAX Integer32 (0..100)
            UNITS "%"
            MAX-ACCESS read-write
            STATUS current
            DESCRIPTION
                "The fraction of a frame period by which the frame indication signal 
                that is sent from the PHY to the MAC is advanced from the actual frame start. "
            DEFVAL { 5 }
            ::= { asxEbsBsCfgEntry 25 }

        
        -- 1.3.6.1.4.1.989.1.16.2.7.4.1.1.26
        asxEbsBsCfgFrameBuildTimeLimit OBJECT-TYPE
            SYNTAX Integer32 (0..100)
            UNITS "%"
            MAX-ACCESS read-write
            STATUS current
            DESCRIPTION
                "The maximum proportion of the frame period that can be devoted 
                to frame building. A value of 0 removes the limit and allows frame building 
                to use as much time as it needs. "
            DEFVAL { 45 }
            ::= { asxEbsBsCfgEntry 26 }

        
        -- 1.3.6.1.4.1.989.1.16.2.7.4.1.1.27
        asxEbsBsCfgFrameBuildPduLimit OBJECT-TYPE
            SYNTAX Integer32 (0..2147483647)
            MAX-ACCESS read-write
            STATUS current
            DESCRIPTION
                "The maximum number of PDUs that can be allocated in the downlink 
                before the frame build operation is terminated. A value of 0 removes 
                the limit and allows frame building to allocate as many PDUs as the frame can hold. "
            DEFVAL { 30 }
            ::= { asxEbsBsCfgEntry 27 }

        
        -- 1.3.6.1.4.1.989.1.16.2.7.4.1.1.28
        asxEbsBsCfgDiversityMode OBJECT-TYPE
            SYNTAX INTEGER
                {
                diversityModeCdd(0),
                diversityModeNoCdd(1)
                }
            MAX-ACCESS read-write
            STATUS current
            DESCRIPTION
                "Sets the basestation transmit diversity mode. "
            DEFVAL { diversityModeCdd }
            ::= { asxEbsBsCfgEntry 28 }

        
        -- 1.3.6.1.4.1.989.1.16.2.7.4.1.1.29
        asxEbsBsCfgDegradedTxPowerReduction OBJECT-TYPE
            SYNTAX Integer32 (-20..0)
            UNITS "dB"
            MAX-ACCESS read-write
            STATUS current
            DESCRIPTION
                "Reduced TxPower during GPS degraded status. When you indicate -6, 
                TxPower will be 34dBm during GPS degraded status if Max TxPower is 40dBm. "
            DEFVAL { -6 }
            ::= { asxEbsBsCfgEntry 29 }

        
        -- 1.3.6.1.4.1.989.1.16.2.7.4.1.1.30
        asxEbsBsCfgPhyApiErrorThreshold OBJECT-TYPE
            SYNTAX Integer32 (0..2147483647)
            MAX-ACCESS read-write
            STATUS current
            DESCRIPTION
                "The number of API message errors reported by the PHY in a one second period 
                above which an automatic PHY reset is performed. If set to 0, the threshold 
                is disabled and no PHY reset will be initiated when errors occur. "
            DEFVAL { 0 }
            ::= { asxEbsBsCfgEntry 30 }

        
        -- 1.3.6.1.4.1.989.1.16.2.7.4.1.1.31
        asxEbsBsCfgArpRetryPeriod OBJECT-TYPE
            SYNTAX Integer32 (0..2147483647)
            UNITS "ms"
            MAX-ACCESS read-write
            STATUS current
            DESCRIPTION
                "When the BS is trying to resolve an IP address using the ARP protocol, 
                this is the period at which retries are made in the case when no answer is received. "
            DEFVAL { 5000 }
            ::= { asxEbsBsCfgEntry 31 }

        
        -- 1.3.6.1.4.1.989.1.16.2.7.4.1.1.32
        asxEbsBsCfgArpRefreshPeriod OBJECT-TYPE
            SYNTAX Integer32 (0..2147483647)
            UNITS "ms"
            MAX-ACCESS read-write
            STATUS current
            DESCRIPTION
                "When the BS has resolved an IP address using the ARP protocol, 
                this is the period at which further ARP requests are made to refresh the address. "
            DEFVAL { 30000 }
            ::= { asxEbsBsCfgEntry 32 }

        
        -- 1.3.6.1.4.1.989.1.16.2.7.4.1.1.33
        asxEbsBsCfgPhyActivityMonitorPeriod OBJECT-TYPE
            SYNTAX Integer32 (0..2147483647)
            UNITS "ms"
            MAX-ACCESS read-write
            STATUS current
            DESCRIPTION
                "The period for which the PHY device must be completely inactive
                before an automatic PHY reset is triggered.
                If set to 0, automatic resets are disabled."
            DEFVAL { 0 }
            ::= { asxEbsBsCfgEntry 33 }

        
        -- 1.3.6.1.4.1.989.1.16.2.7.4.1.1.34
        asxEbsBsCfgEncryptionLicenceCertificate OBJECT-TYPE
            SYNTAX OCTET STRING (SIZE (0..65535))
            MAX-ACCESS read-write
            STATUS current
            DESCRIPTION
                "Certificate defining the licenced featurs for the BS 
                identified by inventory MacAddress. The principal use of
                the certificate is for licensing the encryption algorithms."
            DEFVAL { ''b }
            ::= { asxEbsBsCfgEntry 34 }

        
        -- 1.3.6.1.4.1.989.1.16.2.7.4.1.1.35
        asxEbsBsCfgRequestedMobilityMode OBJECT-TYPE
            SYNTAX AsxEbsMobilityMode
            MAX-ACCESS read-write
            STATUS current
            DESCRIPTION
                "Requested mode of operation Fixed or Mobile. Fixed mode prevents MS from 
                perfoming handover by send Dreg instead of MOB_BSHO_RSP and Reject to Idle Mode entry. "
            DEFVAL { mobilityModeSurveyOnly }
            ::= { asxEbsBsCfgEntry 35 }

        
        -- 1.3.6.1.4.1.989.1.16.2.7.4.1.1.36
        asxEbsBsCfgFeatureLicenceCertificate OBJECT-TYPE
            SYNTAX OCTET STRING (SIZE (0..65535))
            MAX-ACCESS read-write
            STATUS current
            DESCRIPTION
                "Certificate defining the licenced features other than AES for the BS identified 
                by Hardware MAC address. The principal use of the certificate is for licensing 
                the mobility mode features. "
            DEFVAL { ''b }
            ::= { asxEbsBsCfgEntry 36 }

        
        -- 1.3.6.1.4.1.989.1.16.2.7.4.1.1.37
        asxEbsBsCfgUseNtp OBJECT-TYPE
            SYNTAX AsmaxBooleanSwitch
            MAX-ACCESS read-write
            STATUS current
            DESCRIPTION
                "Use NTP to set and maintain the SDR date and time. 
                Needs the asxEbsBsNtpServerTable table configured. "
            DEFVAL { booleanFalse }
            ::= { asxEbsBsCfgEntry 37 }

        
        -- 1.3.6.1.4.1.989.1.16.2.7.4.1.1.38
        asxEbsBsCfgAAAServerPort OBJECT-TYPE
            SYNTAX Integer32 (0..65535)
            MAX-ACCESS read-write
            STATUS current
            DESCRIPTION
                "IP port used for authentication messages of RADIUS protocol.
                Typically 1812 or 1645."
            DEFVAL { 1812 }
            ::= { asxEbsBsCfgEntry 38 }

        
        -- 1.3.6.1.4.1.989.1.16.2.7.4.1.1.39
        asxEbsBsCfgAAAServerMyIpAddressType OBJECT-TYPE
            SYNTAX InetAddressType
            MAX-ACCESS read-write
            STATUS current
            DESCRIPTION
                "Address type for asxEbsBsCfgAAAServerMyIpAddress."
            DEFVAL { ipv4 }
            ::= { asxEbsBsCfgEntry 39 }

        
        -- 1.3.6.1.4.1.989.1.16.2.7.4.1.1.40
        asxEbsBsCfgAAAServerMyIpAddress OBJECT-TYPE
            SYNTAX InetAddress
            MAX-ACCESS read-write
            STATUS current
            DESCRIPTION
                "The IPv4 or IPv6 address used by the BS when talking to the RADIUS Server."
            DEFVAL { "0.0.0.0" }
            ::= { asxEbsBsCfgEntry 40 }

        
        -- 1.3.6.1.4.1.989.1.16.2.7.4.1.1.41
        asxEbsBsCfgAAAServerAccountingPort OBJECT-TYPE
            SYNTAX Integer32 (0..65535)
            MAX-ACCESS read-write
            STATUS current
            DESCRIPTION
                "IP port used for accounting messages of RADIUS protocol.
                Typically 1813 or 1646."
            ::= { asxEbsBsCfgEntry 41 }

        
        -- 1.3.6.1.4.1.989.1.16.2.7.4.1.1.42
        asxEbsBsCfgRelayAgentCircuitId OBJECT-TYPE
            SYNTAX OCTET STRING (SIZE (6))
            MAX-ACCESS read-write
            STATUS current
            DESCRIPTION
                "The MAC address to be used by the DHCP relay agent 
                information insertion as the circuit identifier.
                Also can hold any configurable, arbitrary ID defined by operator."
            ::= { asxEbsBsCfgEntry 42 }

        
        -- 1.3.6.1.4.1.989.1.16.2.7.4.1.1.43
        asxEbsBsCfgNumberOfAntennas OBJECT-TYPE
            SYNTAX Unsigned32
            MAX-ACCESS read-write
            STATUS current
            DESCRIPTION
                "Number of antennas. This property supercedes NumAntennas property"
            DEFVAL { 2 }
            ::= { asxEbsBsCfgEntry 43 }

        
        -- 1.3.6.1.4.1.989.1.16.2.7.4.1.1.44
        asxEbsBsCfgNumberOfSectors OBJECT-TYPE
            SYNTAX Integer32 (1..2)
            MAX-ACCESS read-write
            STATUS current
            DESCRIPTION
                "The number of enabled sectors. Physical support determined by the number of valid interfaces in table 75. Service mode is determined in table 17 by inService property. "
            DEFVAL { 1 }
            ::= { asxEbsBsCfgEntry 44 }

        
        -- 1.3.6.1.4.1.989.1.16.2.7.4.1.1.45
        asxEbsBsCfgRtFileLogLevel OBJECT-TYPE
            SYNTAX Integer32 (0..6)
            MAX-ACCESS read-write
            STATUS current
            DESCRIPTION
                "The minimum log level to write to the log file, from MMX adapt "
            DEFVAL { 6 }
            ::= { asxEbsBsCfgEntry 45 }

        
        -- 1.3.6.1.4.1.989.1.16.2.7.4.1.1.46
        asxEbsBsCfgGpsAdjustHoldoff OBJECT-TYPE
            SYNTAX Integer32 (0..2147483647)
            MAX-ACCESS read-write
            STATUS current
            DESCRIPTION
                "Number of GPS measurements indicating a correction before an adjustment is made."
            DEFVAL { 3 }
            ::= { asxEbsBsCfgEntry 46 }

        
        -- 1.3.6.1.4.1.989.1.16.2.7.4.1.1.47
        asxEbsBsCfgPaCurrentAlarmMinThresh OBJECT-TYPE
            SYNTAX Integer32 (0..255)
            MAX-ACCESS read-write
            STATUS current
            DESCRIPTION
                "PA current alarm minimum current threshold."
            DEFVAL { 0 }
            ::= { asxEbsBsCfgEntry 47 }

        
        -- 1.3.6.1.4.1.989.1.16.2.7.4.1.1.48
        asxEbsBsCfgPaCurrentAlarmMaxThresh OBJECT-TYPE
            SYNTAX Integer32 (0..255)
            MAX-ACCESS read-write
            STATUS current
            DESCRIPTION
                "PA current alarm maximum current threshold."
            DEFVAL { 255 }
            ::= { asxEbsBsCfgEntry 48 }

        
        -- 1.3.6.1.4.1.989.1.16.2.7.4.1.1.49
        asxEbsBsCfgAntMismatchAlarmThresh OBJECT-TYPE
            SYNTAX Integer32 (0..10000)
            UNITS "1/100dB"
            MAX-ACCESS read-write
            STATUS current
            DESCRIPTION
                "Antenna mismatch alarm threshold (1/100 dB)."
            DEFVAL { 600 }
            ::= { asxEbsBsCfgEntry 49 }

        
        -- 1.3.6.1.4.1.989.1.16.2.7.4.1.1.50
        asxEbsBsCfgLowFwdPwrAlarmThresh OBJECT-TYPE
            SYNTAX Integer32 (0..10000)
            MAX-ACCESS read-write
            STATUS current
            DESCRIPTION
                "Low forward power alarm threshold."
            DEFVAL { 600 }
            ::= { asxEbsBsCfgEntry 50 }

        
        -- 1.3.6.1.4.1.989.1.16.2.7.4.1.1.51
        asxEbsBsCfgAaaCompatibilityMode OBJECT-TYPE
            SYNTAX INTEGER
                {
                generic(1),
                omitNasId(2)
                }
            MAX-ACCESS read-write
            STATUS current
            DESCRIPTION
                "AAA Compatibility mode"
            DEFVAL { generic }
            ::= { asxEbsBsCfgEntry 51 }

        
        -- 1.3.6.1.4.1.989.1.16.2.7.4.1.1.52
        asxEbsBsCfgAaaAcctInterimPeriod OBJECT-TYPE
            SYNTAX Integer32
            MAX-ACCESS read-write
            STATUS current
            DESCRIPTION
                "Accounting Interim period in seconds for AAA."
            DEFVAL { 1800 }
            ::= { asxEbsBsCfgEntry 52 }

        
        -- 1.3.6.1.4.1.989.1.16.2.7.4.1.1.53
        asxEbsBsCfgAsnGatewayRedundancyAutoResume OBJECT-TYPE
            SYNTAX AsmaxBooleanSwitch
            MAX-ACCESS read-write
            STATUS current
            DESCRIPTION
                "Description."
            DEFVAL { booleanFalse }
            ::= { asxEbsBsCfgEntry 53 }

        
        -- 1.3.6.1.4.1.989.1.16.2.7.4.1.1.54
        asxEbsBsCfgAsnGatewayKeepaliveMethod OBJECT-TYPE
            SYNTAX INTEGER
                {
                disable(0),
                r6(1),
                ping(2)
                }
            MAX-ACCESS read-write
            STATUS current
            DESCRIPTION
                "Description."
            DEFVAL { disable }
            ::= { asxEbsBsCfgEntry 54 }

        
        -- 1.3.6.1.4.1.989.1.16.2.7.4.2
        asxEbsBsStatusTable OBJECT-TYPE
            SYNTAX SEQUENCE OF AsxEbsBsStatusEntry
            MAX-ACCESS not-accessible
            STATUS current
            DESCRIPTION
                "Description."
            ::= { asxEbsDevice 2 }

        
        -- 1.3.6.1.4.1.989.1.16.2.7.4.2.1
        asxEbsBsStatusEntry OBJECT-TYPE
            SYNTAX AsxEbsBsStatusEntry
            MAX-ACCESS not-accessible
            STATUS current
            DESCRIPTION
                "Description."
            INDEX { asxEbsBsIndex }
            ::= { asxEbsBsStatusTable 1 }

        
        AsxEbsBsStatusEntry ::=
            SEQUENCE { 
                asxEbsBsStatusOperationalStatus
                    AsxEbsOperationalStatus,
                asxEbsBsStatusOperationalStatusInfo
                    DisplayString,
                asxEbsBsStatusActiveEncryptionMode
                    AsxEbsEncryptionMode,
                asxEbsBsStatusEncryptionLicenceCertCapabilities
                    DisplayString,
                asxEbsBsStatusEncryptionLicenceCertInvalid
                    AsmaxBooleanSwitch,
                asxEbsBsStatusOperationalMobilityMode
                    AsxEbsMobilityMode,
                asxEbsBsStatusLicencedFeatures
                    BITS,
                asxEbsBsStatusFeatureLicenceCertCapabilities
                    DisplayString,
                asxEbsBsStatusFeatureLicenceCertInvalid
                    AsmaxBooleanSwitch,
                asxEbsBsStatusFeatureLicenceCertInvalidInfo
                    DisplayString,
                asxEbsBsStatusFeatureLicenceExpiryStatus
                    AsxEbsExpiryStatus,
                asxEbsBsStatusFeatureLicenceExpiryDaysRemaining
                    Integer32,
                asxEbsBsStatusFeatureLicenceExpiryStatusInfo
                    DisplayString,
                asxEbsBsStatusLicensedFeatures2
                    AsxEbsBsLicensedFeatures,
                asxEbsBsStatusImplementedFeatures
                    AsxEbsBsLicensedFeatures,
                asxEbsBsStatusNtpStatus
                    AsxEbsNtpStatus,
                asxEbsBsStatusNtpStatusInfo
                    DisplayString
             }

        -- 1.3.6.1.4.1.989.1.16.2.7.4.2.1.1
        asxEbsBsStatusOperationalStatus OBJECT-TYPE
            SYNTAX AsxEbsOperationalStatus
            MAX-ACCESS read-only
            STATUS current
            DESCRIPTION
                "The current operational status for the basestation."
            ::= { asxEbsBsStatusEntry 1 }

        
        -- 1.3.6.1.4.1.989.1.16.2.7.4.2.1.2
        asxEbsBsStatusOperationalStatusInfo OBJECT-TYPE
            SYNTAX DisplayString
            MAX-ACCESS read-only
            STATUS current
            DESCRIPTION
                "Provides further information on the BS Operational Status"
            ::= { asxEbsBsStatusEntry 2 }

        
        -- 1.3.6.1.4.1.989.1.16.2.7.4.2.1.3
        asxEbsBsStatusActiveEncryptionMode OBJECT-TYPE
            SYNTAX AsxEbsEncryptionMode
            MAX-ACCESS read-only
            STATUS current
            DESCRIPTION
                "Reports the active 'maximum' encryption mode that is allowed by 
                export licence and configured by the user of the EMS."
            ::= { asxEbsBsStatusEntry 3 }

        
        -- 1.3.6.1.4.1.989.1.16.2.7.4.2.1.4
        asxEbsBsStatusEncryptionLicenceCertCapabilities OBJECT-TYPE
            SYNTAX DisplayString
            MAX-ACCESS read-only
            STATUS current
            DESCRIPTION
                "BS capabilities licenced using object asxEbsBsCfgEncryptionLicenceCertificate.
                The capabilites are encoded in clear text ready to display on EMS GUI."
            DEFVAL { ''b }
            ::= { asxEbsBsStatusEntry 4 }

        
        -- 1.3.6.1.4.1.989.1.16.2.7.4.2.1.5
        asxEbsBsStatusEncryptionLicenceCertInvalid OBJECT-TYPE
            SYNTAX AsmaxBooleanSwitch
            MAX-ACCESS read-only
            STATUS current
            DESCRIPTION
                "Reports the invalidity of the configured certificate asxEbsBsCfgEncryptionLicenceCertificate."
            DEFVAL { booleanFalse }
            ::= { asxEbsBsStatusEntry 5 }

        
        -- 1.3.6.1.4.1.989.1.16.2.7.4.2.1.6
        asxEbsBsStatusOperationalMobilityMode OBJECT-TYPE
            SYNTAX AsxEbsMobilityMode
            MAX-ACCESS read-only
            STATUS current
            DESCRIPTION
                "Actual operating mode after validation of provisoned mobilityMode 
                with X509 cerfificate enabling feature."
            ::= { asxEbsBsStatusEntry 6 }

        
        -- 1.3.6.1.4.1.989.1.16.2.7.4.2.1.7
        asxEbsBsStatusLicencedFeatures OBJECT-TYPE
            SYNTAX BITS
                {
                licFeatureMobModeFixed(0),
                licFeatureMobModeMobile(1),
                licFeatureDualMacPhy(2)
                }
            MAX-ACCESS read-only
            STATUS deprecated
            DESCRIPTION
                "A set of bits indicating all Certificate enabled features available 
                and validated against installed certificates. "
            ::= { asxEbsBsStatusEntry 7 }

        
        -- 1.3.6.1.4.1.989.1.16.2.7.4.2.1.8
        asxEbsBsStatusFeatureLicenceCertCapabilities OBJECT-TYPE
            SYNTAX DisplayString
            MAX-ACCESS read-only
            STATUS current
            DESCRIPTION
                "BS capabilities licenced using featureLicenceCertificate. 
                The capabilities are reported in clear text ready to display on. "
            ::= { asxEbsBsStatusEntry 8 }

        
        -- 1.3.6.1.4.1.989.1.16.2.7.4.2.1.9
        asxEbsBsStatusFeatureLicenceCertInvalid OBJECT-TYPE
            SYNTAX AsmaxBooleanSwitch
            MAX-ACCESS read-only
            STATUS current
            DESCRIPTION
                "Reports the invalidity of the configured certificate asxEbsBsCfgFeatureLicenceCertificate."
            DEFVAL { booleanFalse }
            ::= { asxEbsBsStatusEntry 9 }

        
        -- 1.3.6.1.4.1.989.1.16.2.7.4.2.1.10
        asxEbsBsStatusFeatureLicenceCertInvalidInfo OBJECT-TYPE
            SYNTAX DisplayString
            MAX-ACCESS read-only
            STATUS current
            DESCRIPTION
                "Further textual string within the asxEbsBsStatusFeatureLicenceCertInvalidTrap describing the current status 
                of the feature licence configuration."
            ::= { asxEbsBsStatusEntry 10 }

        
        -- 1.3.6.1.4.1.989.1.16.2.7.4.2.1.11
        asxEbsBsStatusFeatureLicenceExpiryStatus OBJECT-TYPE
            SYNTAX AsxEbsExpiryStatus
            MAX-ACCESS read-only
            STATUS current
            DESCRIPTION
                "Property contained within the asxEbsBsFeatureLicenceExpiringTrap trap which indicates the status of the expiry. 
                - When the value is asxEbsExpiryStatusNoError, the licence is not close to expiry
                - When the value is asxEbsExpiryStatusWarning, property asxEbsBsStatusFeatureLicenceExpiryDaysRemaining 
                indicates the number of days remaining before the licence will expire.
                - A value of asxEbsExpiryStatusError indicates that the licence has expired.  In this case property 
                asxEbsBsStatusFeatureLicenceExpiryDaysRemaining returns 0."
            ::= { asxEbsBsStatusEntry 11 }

        
        -- 1.3.6.1.4.1.989.1.16.2.7.4.2.1.12
        asxEbsBsStatusFeatureLicenceExpiryDaysRemaining OBJECT-TYPE
            SYNTAX Integer32 (-32768..32767)
            MAX-ACCESS read-only
            STATUS current
            DESCRIPTION
                "Property contained within the asxEbsBsFeatureLicenceExpiringTrap trap which indicates the number of days left until 
                the BS Feature Licence certificate will expire."
            ::= { asxEbsBsStatusEntry 12 }

        
        -- 1.3.6.1.4.1.989.1.16.2.7.4.2.1.13
        asxEbsBsStatusFeatureLicenceExpiryStatusInfo OBJECT-TYPE
            SYNTAX DisplayString
            MAX-ACCESS read-only
            STATUS current
            DESCRIPTION
                "Further textual string within the asxEbsBsFeatureLicenceExpiringTrap describing the current expiry status 
                of the feature licence configuration."
            ::= { asxEbsBsStatusEntry 13 }

        
        -- 1.3.6.1.4.1.989.1.16.2.7.4.2.1.14
        asxEbsBsStatusLicensedFeatures2 OBJECT-TYPE
            SYNTAX AsxEbsBsLicensedFeatures
            MAX-ACCESS read-only
            STATUS current
            DESCRIPTION
                "A set of bits indicating all the features subject to licensing that have been made available
                via the installed licence certificate on the BS."
            ::= { asxEbsBsStatusEntry 14 }

        
        -- 1.3.6.1.4.1.989.1.16.2.7.4.2.1.15
        asxEbsBsStatusImplementedFeatures OBJECT-TYPE
            SYNTAX AsxEbsBsLicensedFeatures
            MAX-ACCESS read-only
            STATUS current
            DESCRIPTION
                "A set of bits indicating all the features subject to licensing that are implemented on the BS.
                Features are reported here irrespective of whether they are currently licensed or not. "
            ::= { asxEbsBsStatusEntry 15 }

        
        -- 1.3.6.1.4.1.989.1.16.2.7.4.2.1.16
        asxEbsBsStatusNtpStatus OBJECT-TYPE
            SYNTAX AsxEbsNtpStatus
            MAX-ACCESS read-only
            STATUS current
            DESCRIPTION
                "Reports the current state of the BS clock set as a result of NTP responses received."
            DEFVAL { asxEbsNtpStatusNoError }
            ::= { asxEbsBsStatusEntry 16 }

        
        -- 1.3.6.1.4.1.989.1.16.2.7.4.2.1.17
        asxEbsBsStatusNtpStatusInfo OBJECT-TYPE
            SYNTAX DisplayString
            MAX-ACCESS read-only
            STATUS current
            DESCRIPTION
                "Further textual string reporting the current state of the BS clock set as a result of NTP responses received."
            ::= { asxEbsBsStatusEntry 17 }

        
        -- 1.3.6.1.4.1.989.1.16.2.7.4.3
        asxEbsBsStaticIpRouteTable OBJECT-TYPE
            SYNTAX SEQUENCE OF AsxEbsBsStaticIpRouteEntry
            MAX-ACCESS not-accessible
            STATUS current
            DESCRIPTION
                "Table containing the static IP Routes to be configured on the basestation."
            ::= { asxEbsDevice 3 }

        
        -- 1.3.6.1.4.1.989.1.16.2.7.4.3.1
        asxEbsBsStaticIpRouteEntry OBJECT-TYPE
            SYNTAX AsxEbsBsStaticIpRouteEntry
            MAX-ACCESS not-accessible
            STATUS current
            DESCRIPTION
                "Description."
            INDEX { asxEbsBsStaticIpRouteId }
            ::= { asxEbsBsStaticIpRouteTable 1 }

        
        AsxEbsBsStaticIpRouteEntry ::=
            SEQUENCE { 
                asxEbsBsStaticIpRouteId
                    Integer32,
                asxEbsBsStaticIpRouteDestIpAddress
                    InetAddress,
                asxEbsBsStaticIpRouteNetMask
                    InetAddress,
                asxEbsBsStaticIpRouteNextHop
                    InetAddress,
                asxEbsBsStaticIpRouteRowStatus
                    RowStatus
             }

        -- 1.3.6.1.4.1.989.1.16.2.7.4.3.1.1
        asxEbsBsStaticIpRouteId OBJECT-TYPE
            SYNTAX Integer32 (1..2147483647)
            MAX-ACCESS not-accessible
            STATUS current
            DESCRIPTION
                "Arbitrary index for entry in static IP routes table. "
            ::= { asxEbsBsStaticIpRouteEntry 1 }

        
        -- 1.3.6.1.4.1.989.1.16.2.7.4.3.1.2
        asxEbsBsStaticIpRouteDestIpAddress OBJECT-TYPE
            SYNTAX InetAddress
            MAX-ACCESS read-create
            STATUS current
            DESCRIPTION
                "IP address of the destination subnet for this route."
            ::= { asxEbsBsStaticIpRouteEntry 2 }

        
        -- 1.3.6.1.4.1.989.1.16.2.7.4.3.1.3
        asxEbsBsStaticIpRouteNetMask OBJECT-TYPE
            SYNTAX InetAddress
            MAX-ACCESS read-create
            STATUS current
            DESCRIPTION
                "NetMask of the destination subnet for this route "
            ::= { asxEbsBsStaticIpRouteEntry 3 }

        
        -- 1.3.6.1.4.1.989.1.16.2.7.4.3.1.4
        asxEbsBsStaticIpRouteNextHop OBJECT-TYPE
            SYNTAX InetAddress
            MAX-ACCESS read-create
            STATUS current
            DESCRIPTION
                "IP address of router providing access to subnet for this route"
            ::= { asxEbsBsStaticIpRouteEntry 4 }

        
        -- 1.3.6.1.4.1.989.1.16.2.7.4.3.1.5
        asxEbsBsStaticIpRouteRowStatus OBJECT-TYPE
            SYNTAX RowStatus
            MAX-ACCESS read-create
            STATUS current
            DESCRIPTION
                "Handles Row Creation/ Deletion in the table."
            ::= { asxEbsBsStaticIpRouteEntry 5 }

        
        -- 1.3.6.1.4.1.989.1.16.2.7.4.4
        asxEbsBsNtpServerTable OBJECT-TYPE
            SYNTAX SEQUENCE OF AsxEbsBsNtpServerEntry
            MAX-ACCESS not-accessible
            STATUS current
            DESCRIPTION
                "Table containing the NTP Server definitions to be configured on the basestation."
            ::= { asxEbsDevice 4 }

        
        -- 1.3.6.1.4.1.989.1.16.2.7.4.4.1
        asxEbsBsNtpServerEntry OBJECT-TYPE
            SYNTAX AsxEbsBsNtpServerEntry
            MAX-ACCESS not-accessible
            STATUS current
            DESCRIPTION
                "Description."
            INDEX { asxEbsBsNtpServerId }
            ::= { asxEbsBsNtpServerTable 1 }

        
        AsxEbsBsNtpServerEntry ::=
            SEQUENCE { 
                asxEbsBsNtpServerId
                    Integer32,
                asxEbsBsNtpServerIpAddressType
                    InetAddressType,
                asxEbsBsNtpServerIpAddress
                    InetAddress,
                asxEbsBsNtpServerRowStatus
                    RowStatus
             }

        -- 1.3.6.1.4.1.989.1.16.2.7.4.4.1.1
        asxEbsBsNtpServerId OBJECT-TYPE
            SYNTAX Integer32 (1..2147483647)
            MAX-ACCESS not-accessible
            STATUS current
            DESCRIPTION
                "Arbitrary index for entry in NTP server table. "
            ::= { asxEbsBsNtpServerEntry 1 }

        
        -- 1.3.6.1.4.1.989.1.16.2.7.4.4.1.2
        asxEbsBsNtpServerIpAddressType OBJECT-TYPE
            SYNTAX InetAddressType
            MAX-ACCESS read-create
            STATUS current
            DESCRIPTION
                "The type of IP address of the NTP Server."
            DEFVAL { ipv4 }
            ::= { asxEbsBsNtpServerEntry 2 }

        
        -- 1.3.6.1.4.1.989.1.16.2.7.4.4.1.3
        asxEbsBsNtpServerIpAddress OBJECT-TYPE
            SYNTAX InetAddress
            MAX-ACCESS read-create
            STATUS current
            DESCRIPTION
                "IP address of the NTP server."
            DEFVAL { "0.0.0.0" }
            ::= { asxEbsBsNtpServerEntry 3 }

        
        -- 1.3.6.1.4.1.989.1.16.2.7.4.4.1.4
        asxEbsBsNtpServerRowStatus OBJECT-TYPE
            SYNTAX RowStatus
            MAX-ACCESS read-create
            STATUS current
            DESCRIPTION
                "Handles Row Creation/ Deletion in the table."
            ::= { asxEbsBsNtpServerEntry 4 }

        
        -- 1.3.6.1.4.1.989.1.16.2.7.4.5
        asxEbsBsStaticArpTable OBJECT-TYPE
            SYNTAX SEQUENCE OF AsxEbsBsStaticArpEntry
            MAX-ACCESS not-accessible
            STATUS obsolete
            DESCRIPTION
                "OBSOLETE"
            ::= { asxEbsDevice 5 }

        
        -- 1.3.6.1.4.1.989.1.16.2.7.4.5.1
        asxEbsBsStaticArpEntry OBJECT-TYPE
            SYNTAX AsxEbsBsStaticArpEntry
            MAX-ACCESS not-accessible
            STATUS obsolete
            DESCRIPTION
                "OBSOLETE"
            INDEX { asxEbsBsStaticArpIpAddressType, asxEbsBsStaticArpIpAddress }
            ::= { asxEbsBsStaticArpTable 1 }

        
        AsxEbsBsStaticArpEntry ::=
            SEQUENCE { 
                asxEbsBsStaticArpIpAddressType
                    InetAddressType,
                asxEbsBsStaticArpIpAddress
                    InetAddress,
                asxEbsBsStaticArpMac
                    MacAddress,
                asxEbsBsStaticArpRowStatus
                    RowStatus
             }

        -- 1.3.6.1.4.1.989.1.16.2.7.4.5.1.1
        asxEbsBsStaticArpIpAddressType OBJECT-TYPE
            SYNTAX InetAddressType
            MAX-ACCESS not-accessible
            STATUS obsolete
            DESCRIPTION
                "OBSOLETE"
            ::= { asxEbsBsStaticArpEntry 1 }

        
        -- 1.3.6.1.4.1.989.1.16.2.7.4.5.1.2
        asxEbsBsStaticArpIpAddress OBJECT-TYPE
            SYNTAX InetAddress
            MAX-ACCESS not-accessible
            STATUS obsolete
            DESCRIPTION
                "OBSOLETE"
            ::= { asxEbsBsStaticArpEntry 2 }

        
        -- 1.3.6.1.4.1.989.1.16.2.7.4.5.1.3
        asxEbsBsStaticArpMac OBJECT-TYPE
            SYNTAX MacAddress
            MAX-ACCESS read-create
            STATUS obsolete
            DESCRIPTION
                "OBSOLETE"
            ::= { asxEbsBsStaticArpEntry 3 }

        
        -- 1.3.6.1.4.1.989.1.16.2.7.4.5.1.4
        asxEbsBsStaticArpRowStatus OBJECT-TYPE
            SYNTAX RowStatus
            MAX-ACCESS read-create
            STATUS obsolete
            DESCRIPTION
                "OBSOLETE"
            ::= { asxEbsBsStaticArpEntry 4 }

        
        -- 1.3.6.1.4.1.989.1.16.2.7.4.6
        asxEbsBsStaticArp2Table OBJECT-TYPE
            SYNTAX SEQUENCE OF AsxEbsBsStaticArp2Entry
            MAX-ACCESS not-accessible
            STATUS current
            DESCRIPTION
                "Table for configuration of system static ARP.
                Replacement for asxEbsBsStaticArpTable, which was contaminated by mapping to IIB
                with broken encoding of indexes."
            ::= { asxEbsDevice 6 }

        
        -- 1.3.6.1.4.1.989.1.16.2.7.4.6.1
        asxEbsBsStaticArp2Entry OBJECT-TYPE
            SYNTAX AsxEbsBsStaticArp2Entry
            MAX-ACCESS not-accessible
            STATUS current
            DESCRIPTION
                "Description."
            INDEX { asxEbsBsStaticArp2IpAddressType, asxEbsBsStaticArp2IpAddress }
            ::= { asxEbsBsStaticArp2Table 1 }

        
        AsxEbsBsStaticArp2Entry ::=
            SEQUENCE { 
                asxEbsBsStaticArp2IpAddressType
                    InetAddressType,
                asxEbsBsStaticArp2IpAddress
                    InetAddress,
                asxEbsBsStaticArp2Mac
                    MacAddress,
                asxEbsBsStaticArp2RowStatus
                    RowStatus
             }

        -- 1.3.6.1.4.1.989.1.16.2.7.4.6.1.1
        asxEbsBsStaticArp2IpAddressType OBJECT-TYPE
            SYNTAX InetAddressType
            MAX-ACCESS not-accessible
            STATUS current
            DESCRIPTION
                "Type of IP address of the destination device - part of index for StaticArp table."
            ::= { asxEbsBsStaticArp2Entry 1 }

        
        -- 1.3.6.1.4.1.989.1.16.2.7.4.6.1.2
        asxEbsBsStaticArp2IpAddress OBJECT-TYPE
            SYNTAX InetAddress
            MAX-ACCESS not-accessible
            STATUS current
            DESCRIPTION
                "IP address of the destination device - part of index for StaticArp table."
            ::= { asxEbsBsStaticArp2Entry 2 }

        
        -- 1.3.6.1.4.1.989.1.16.2.7.4.6.1.3
        asxEbsBsStaticArp2Mac OBJECT-TYPE
            SYNTAX MacAddress
            MAX-ACCESS read-create
            STATUS current
            DESCRIPTION
                "Static ARP MAC address for destination device."
            ::= { asxEbsBsStaticArp2Entry 3 }

        
        -- 1.3.6.1.4.1.989.1.16.2.7.4.6.1.4
        asxEbsBsStaticArp2RowStatus OBJECT-TYPE
            SYNTAX RowStatus
            MAX-ACCESS read-create
            STATUS current
            DESCRIPTION
                "Handles Row Creation/ Deletion in the table."
            ::= { asxEbsBsStaticArp2Entry 4 }

        
        -- 1.3.6.1.4.1.989.1.16.2.7.5
        asxEbsStdDraft OBJECT IDENTIFIER ::= { asMaxEbs 5 }

        
        -- 1.3.6.1.4.1.989.1.16.2.7.5.1
        asxEbsStdOfdmaUlBurstProfTable OBJECT-TYPE
            SYNTAX SEQUENCE OF AsxEbsStdOfdmaUlBurstProfEntry
            MAX-ACCESS not-accessible
            STATUS current
            DESCRIPTION
                "Temporary table extending the 802.16i defintion 
                of table wmanIf2BsOfdmaUcdBurstProfileTable.
                This table may be obsoleted when the standard body
                introduces the objects defined here."
            ::= { asxEbsStdDraft 1 }

        
        -- 1.3.6.1.4.1.989.1.16.2.7.5.1.1
        asxEbsStdOfdmaUlBurstProfEntry OBJECT-TYPE
            SYNTAX AsxEbsStdOfdmaUlBurstProfEntry
            MAX-ACCESS not-accessible
            STATUS current
            DESCRIPTION
                "Description."
            INDEX { ifIndex, wmanIf2BsOfdmaUiucIndex }
            ::= { asxEbsStdOfdmaUlBurstProfTable 1 }

        
        AsxEbsStdOfdmaUlBurstProfEntry ::=
            SEQUENCE { 
                asxEbsStdOfdmaUlBurstRepetitionCoding
                    AsEbsStdRepetitionCodingType,
                asxEbsStdOfdmaUlBurstProfRowStatus
                    RowStatus,
                asxEbsStdOfdmaUlBurstMinEntryThresh
                    Integer32,
                asxEbsStdOfdmaUlBurstMandatExitThresh
                    Integer32
             }

        -- 1.3.6.1.4.1.989.1.16.2.7.5.1.1.1
        asxEbsStdOfdmaUlBurstRepetitionCoding OBJECT-TYPE
            SYNTAX AsEbsStdRepetitionCodingType
            MAX-ACCESS read-create
            STATUS current
            DESCRIPTION
                "Repetition coding indication used for burst profiles in UL-MAP."
            ::= { asxEbsStdOfdmaUlBurstProfEntry 1 }

        
        -- 1.3.6.1.4.1.989.1.16.2.7.5.1.1.2
        asxEbsStdOfdmaUlBurstProfRowStatus OBJECT-TYPE
            SYNTAX RowStatus
            MAX-ACCESS read-create
            STATUS current
            DESCRIPTION
                "Description."
            ::= { asxEbsStdOfdmaUlBurstProfEntry 2 }

        
        -- 1.3.6.1.4.1.989.1.16.2.7.5.1.1.3
        asxEbsStdOfdmaUlBurstMinEntryThresh OBJECT-TYPE
            SYNTAX Integer32 (-400..400)
            UNITS "0.25 dBm"
            MAX-ACCESS read-create
            STATUS current
            DESCRIPTION
                "Level at which or above it the modulation can be changed to less robust."
            DEFVAL { 0 }
            ::= { asxEbsStdOfdmaUlBurstProfEntry 3 }

        
        -- 1.3.6.1.4.1.989.1.16.2.7.5.1.1.4
        asxEbsStdOfdmaUlBurstMandatExitThresh OBJECT-TYPE
            SYNTAX Integer32 (-400..400)
            UNITS "0.25 dBm"
            MAX-ACCESS read-create
            STATUS current
            DESCRIPTION
                "Level at which or below it the modulation must be changed to more robust."
            DEFVAL { 0 }
            ::= { asxEbsStdOfdmaUlBurstProfEntry 4 }

        
        -- 1.3.6.1.4.1.989.1.16.2.7.5.2
        asxEbsStdOfdmaDlBurstProfTable OBJECT-TYPE
            SYNTAX SEQUENCE OF AsxEbsStdOfdmaDlBurstProfEntry
            MAX-ACCESS not-accessible
            STATUS current
            DESCRIPTION
                "Temporary table extending the 802.16i defintion 
                of table wmanIf2BsOfdmaDcdBurstProfileTable.
                This table may be obsoleted when the standard body
                introduces the objects defined here."
            ::= { asxEbsStdDraft 2 }

        
        -- 1.3.6.1.4.1.989.1.16.2.7.5.2.1
        asxEbsStdOfdmaDlBurstProfEntry OBJECT-TYPE
            SYNTAX AsxEbsStdOfdmaDlBurstProfEntry
            MAX-ACCESS not-accessible
            STATUS current
            DESCRIPTION
                "Description."
            INDEX { ifIndex, wmanIf2BsOfdmaDiucIndex }
            ::= { asxEbsStdOfdmaDlBurstProfTable 1 }

        
        AsxEbsStdOfdmaDlBurstProfEntry ::=
            SEQUENCE { 
                asxEbsStdOfdmaDlBurstRepetitionCoding
                    AsEbsStdRepetitionCodingType,
                asxEbsStdOfdmaDlBurstProfRowStatus
                    RowStatus,
                asxEbsStdOfdmaDlBurstMinEntryThresh
                    Integer32,
                asxEbsStdOfdmaDlBurstMandatExitThresh
                    Integer32
             }

        -- 1.3.6.1.4.1.989.1.16.2.7.5.2.1.1
        asxEbsStdOfdmaDlBurstRepetitionCoding OBJECT-TYPE
            SYNTAX AsEbsStdRepetitionCodingType
            MAX-ACCESS read-create
            STATUS current
            DESCRIPTION
                "Repetition coding indication used for burst profiles in DL-MAP."
            ::= { asxEbsStdOfdmaDlBurstProfEntry 1 }

        
        -- 1.3.6.1.4.1.989.1.16.2.7.5.2.1.2
        asxEbsStdOfdmaDlBurstProfRowStatus OBJECT-TYPE
            SYNTAX RowStatus
            MAX-ACCESS read-create
            STATUS current
            DESCRIPTION
                "Description."
            ::= { asxEbsStdOfdmaDlBurstProfEntry 2 }

        
        -- 1.3.6.1.4.1.989.1.16.2.7.5.2.1.3
        asxEbsStdOfdmaDlBurstMinEntryThresh OBJECT-TYPE
            SYNTAX Integer32 (-400..400)
            UNITS "0.25 dBm"
            MAX-ACCESS read-create
            STATUS current
            DESCRIPTION
                "Level at which or above it the modulation can be changed to less robust."
            DEFVAL { 0 }
            ::= { asxEbsStdOfdmaDlBurstProfEntry 3 }

        
        -- 1.3.6.1.4.1.989.1.16.2.7.5.2.1.4
        asxEbsStdOfdmaDlBurstMandatExitThresh OBJECT-TYPE
            SYNTAX Integer32 (-400..400)
            UNITS "0.25 dBm"
            MAX-ACCESS read-create
            STATUS current
            DESCRIPTION
                "Level at which or below it the modulation must be changed to more robust."
            DEFVAL { 0 }
            ::= { asxEbsStdOfdmaDlBurstProfEntry 4 }

        
        -- 1.3.6.1.4.1.989.1.16.2.7.5.3
        asxEbsStdReservedTable OBJECT-TYPE
            SYNTAX SEQUENCE OF AsxEbsStdReservedEntry
            MAX-ACCESS not-accessible
            STATUS current
            DESCRIPTION
                "Description."
            ::= { asxEbsStdDraft 3 }

        
        -- 1.3.6.1.4.1.989.1.16.2.7.5.3.1
        asxEbsStdReservedEntry OBJECT-TYPE
            SYNTAX AsxEbsStdReservedEntry
            MAX-ACCESS not-accessible
            STATUS current
            DESCRIPTION
                "Description."
            INDEX { asxEbsStdReservedObject }
            ::= { asxEbsStdReservedTable 1 }

        
        AsxEbsStdReservedEntry ::=
            SEQUENCE { 
                asxEbsStdReservedObject
                    Integer32
             }

        -- 1.3.6.1.4.1.989.1.16.2.7.5.3.1.1
        asxEbsStdReservedObject OBJECT-TYPE
            SYNTAX Integer32 (1)
            MAX-ACCESS read-write
            STATUS current
            DESCRIPTION
                "Description."
            ::= { asxEbsStdReservedEntry 1 }

        
        -- 1.3.6.1.4.1.989.1.16.2.7.5.4
        asxEbsStdZoneTable OBJECT-TYPE
            SYNTAX SEQUENCE OF AsxEbsStdZoneEntry
            MAX-ACCESS not-accessible
            STATUS current
            DESCRIPTION
                "This table defines the Zones."
            ::= { asxEbsStdDraft 4 }

        
        -- 1.3.6.1.4.1.989.1.16.2.7.5.4.1
        asxEbsStdZoneEntry OBJECT-TYPE
            SYNTAX AsxEbsStdZoneEntry
            MAX-ACCESS not-accessible
            STATUS current
            DESCRIPTION
                "Description."
            INDEX { ifIndex, asxEbsStdZoneIndex }
            ::= { asxEbsStdZoneTable 1 }

        
        AsxEbsStdZoneEntry ::=
            SEQUENCE { 
                asxEbsStdZoneIndex
                    Integer32,
                asxEbsStdZoneType
                    AsxEbsZoneType,
                asxEbsStdZoneUseAllSubchannels
                    AsmaxBooleanSwitch,
                asxEbsStdZoneMaxProportion
                    Integer32,
                asxEbsStdZonePermutationBase
                    Integer32,
                asxEbsStdZonePrbsId
                    Integer32,
                asxEbsStdZoneStcMode
                    AsxEbsStcMode,
                asxEbsStdZoneStcMatrix
                    AsxEbsStcMatrix,
                asxEbsStdZoneAmcType
                    AsxEbsAmcType,
                asxEbsStdZoneMidambles
                    AsmaxBooleanSwitch,
                asxEbsStdZoneMidambleBoost
                    AsmaxBooleanSwitch,
                asxEbsStdZoneDedicatedPilots
                    AsmaxBooleanSwitch,
                asxEbsStdZoneRowStatus
                    RowStatus,
                asxEbsStdZoneMinProportion
                    Integer32,
                asxEbsStdZoneStartProportion
                    Integer32,
                asxEbsStdZoneHarqEnabled
                    AsmaxBooleanSwitch
             }

        -- 1.3.6.1.4.1.989.1.16.2.7.5.4.1.1
        asxEbsStdZoneIndex OBJECT-TYPE
            SYNTAX Integer32 (0..2147483647)
            MAX-ACCESS not-accessible
            STATUS current
            DESCRIPTION
                "Arbitrary index which implicitly defines the order of zones in the frame.
                Zones are arranged in the subframes in order of increasing index. "
            ::= { asxEbsStdZoneEntry 1 }

        
        -- 1.3.6.1.4.1.989.1.16.2.7.5.4.1.2
        asxEbsStdZoneType OBJECT-TYPE
            SYNTAX AsxEbsZoneType
            MAX-ACCESS read-create
            STATUS current
            DESCRIPTION
                "The zone type, which defines
                the zone's direction (UL or DL),
                PHY mode (OFDM or OFDMA) and 
                structure (PUSC, STC, etc). "
            ::= { asxEbsStdZoneEntry 2 }

        
        -- 1.3.6.1.4.1.989.1.16.2.7.5.4.1.3
        asxEbsStdZoneUseAllSubchannels OBJECT-TYPE
            SYNTAX AsmaxBooleanSwitch
            MAX-ACCESS read-create
            STATUS current
            DESCRIPTION
                "Set to TRUE if the zone must use all subchannels.
                If FALSE, uplink zones will use the subchannels defined by the 
                UCD subchannel maps, and downlink zones will use the subchannels 
                defined by the FCH segment map."
            ::= { asxEbsStdZoneEntry 3 }

        
        -- 1.3.6.1.4.1.989.1.16.2.7.5.4.1.4
        asxEbsStdZoneMaxProportion OBJECT-TYPE
            SYNTAX Integer32 (0..100)
            MAX-ACCESS read-create
            STATUS current
            DESCRIPTION
                "The maximum percentage of the subframe that this zone will occupy. 
                The zone will grow as allocations occur but will not grow above the subframe percentage configured here. 
                This is ignored for OFDM zones."
            ::= { asxEbsStdZoneEntry 4 }

        
        -- 1.3.6.1.4.1.989.1.16.2.7.5.4.1.5
        asxEbsStdZonePermutationBase OBJECT-TYPE
            SYNTAX Integer32 (0..31)
            MAX-ACCESS read-create
            STATUS current
            DESCRIPTION
                "The base used for the sub-carrier permutation in PUSC zones."
            ::= { asxEbsStdZoneEntry 5 }

        
        -- 1.3.6.1.4.1.989.1.16.2.7.5.4.1.6
        asxEbsStdZonePrbsId OBJECT-TYPE
            SYNTAX Integer32 (0..2)
            MAX-ACCESS read-create
            STATUS current
            DESCRIPTION
                "The PRBS identifier used in PUSC zones when the useAllSubchannels field is TRUE."
            ::= { asxEbsStdZoneEntry 6 }

        
        -- 1.3.6.1.4.1.989.1.16.2.7.5.4.1.7
        asxEbsStdZoneStcMode OBJECT-TYPE
            SYNTAX AsxEbsStcMode
            MAX-ACCESS read-create
            STATUS current
            DESCRIPTION
                "The STC mode and number of antennas used in this zone."
            ::= { asxEbsStdZoneEntry 7 }

        
        -- 1.3.6.1.4.1.989.1.16.2.7.5.4.1.8
        asxEbsStdZoneStcMatrix OBJECT-TYPE
            SYNTAX AsxEbsStcMatrix
            MAX-ACCESS read-create
            STATUS current
            DESCRIPTION
                "The STC matrix used in this zone, if STC is enabled. 
                Note that matrix C is not valid if the STC mode is FHDC with 2 antennas. "
            ::= { asxEbsStdZoneEntry 8 }

        
        -- 1.3.6.1.4.1.989.1.16.2.7.5.4.1.9
        asxEbsStdZoneAmcType OBJECT-TYPE
            SYNTAX AsxEbsAmcType
            MAX-ACCESS read-create
            STATUS current
            DESCRIPTION
                "The AMC type used in this zone. "
            ::= { asxEbsStdZoneEntry 9 }

        
        -- 1.3.6.1.4.1.989.1.16.2.7.5.4.1.10
        asxEbsStdZoneMidambles OBJECT-TYPE
            SYNTAX AsmaxBooleanSwitch
            MAX-ACCESS read-create
            STATUS current
            DESCRIPTION
                "Set to TRUE if midambles are required for all bursts in this zone."
            ::= { asxEbsStdZoneEntry 10 }

        
        -- 1.3.6.1.4.1.989.1.16.2.7.5.4.1.11
        asxEbsStdZoneMidambleBoost OBJECT-TYPE
            SYNTAX AsmaxBooleanSwitch
            MAX-ACCESS read-create
            STATUS current
            DESCRIPTION
                "Set to TRUE if +3dB midamble boost is required for all bursts in this zone."
            ::= { asxEbsStdZoneEntry 11 }

        
        -- 1.3.6.1.4.1.989.1.16.2.7.5.4.1.12
        asxEbsStdZoneDedicatedPilots OBJECT-TYPE
            SYNTAX AsmaxBooleanSwitch
            MAX-ACCESS read-create
            STATUS current
            DESCRIPTION
                "Set to TRUE if dedicated pilots aee required in this zone, or FALSE if broadcast pilots are required"
            ::= { asxEbsStdZoneEntry 12 }

        
        -- 1.3.6.1.4.1.989.1.16.2.7.5.4.1.13
        asxEbsStdZoneRowStatus OBJECT-TYPE
            SYNTAX RowStatus
            MAX-ACCESS read-create
            STATUS current
            DESCRIPTION
                "Description."
            ::= { asxEbsStdZoneEntry 13 }

        
        -- 1.3.6.1.4.1.989.1.16.2.7.5.4.1.14
        asxEbsStdZoneMinProportion OBJECT-TYPE
            SYNTAX Integer32
            MAX-ACCESS read-create
            STATUS current
            DESCRIPTION
                "The minimum percentage of the subframe that this zone will occupy, rounded up to the next symbol boundary. 
                Even if there are no allocations made in the zone, it will still occupy the amount of space configured here. 
                This is ignored for OFDM zones."
            ::= { asxEbsStdZoneEntry 14 }

        
        -- 1.3.6.1.4.1.989.1.16.2.7.5.4.1.15
        asxEbsStdZoneStartProportion OBJECT-TYPE
            SYNTAX Integer32
            MAX-ACCESS read-create
            STATUS current
            DESCRIPTION
                "The fixed position in the subframe at which this zone will begin, rounded up to the next symbol boundary. 
                If it is set to 0, then the zone may begin at any position in the subframe. 
                This is ignored for OFDM zones. "
            ::= { asxEbsStdZoneEntry 15 }

        
        -- 1.3.6.1.4.1.989.1.16.2.7.5.4.1.16
        asxEbsStdZoneHarqEnabled OBJECT-TYPE
            SYNTAX AsmaxBooleanSwitch
            MAX-ACCESS read-create
            STATUS current
            DESCRIPTION
                "Set to TRUE if HARQ connections are permitted in this zone."
            DEFVAL { booleanFalse }
            ::= { asxEbsStdZoneEntry 16 }

        
        -- 1.3.6.1.4.1.989.1.16.2.7.6
        asxEbsSs OBJECT IDENTIFIER ::= { asMaxEbs 6 }

        
        -- 1.3.6.1.4.1.989.1.16.2.7.6.1
        asxEbsSsProvTable OBJECT-TYPE
            SYNTAX SEQUENCE OF AsxEbsSsProvEntry
            MAX-ACCESS not-accessible
            STATUS current
            DESCRIPTION
                "Configuration of SS for legacy provisioning."
            ::= { asxEbsSs 1 }

        
        -- 1.3.6.1.4.1.989.1.16.2.7.6.1.1
        asxEbsSsProvEntry OBJECT-TYPE
            SYNTAX AsxEbsSsProvEntry
            MAX-ACCESS not-accessible
            STATUS current
            DESCRIPTION
                "Description."
            INDEX { ifIndex, wmanIf2BsSsMacAddress }
            ::= { asxEbsSsProvTable 1 }

        
        AsxEbsSsProvEntry ::=
            SEQUENCE { 
                asxEbsSsProvInService
                    AsmaxBooleanSwitch,
                asxEbsSsProvDlZoneIndex
                    Integer32,
                asxEbsSsProvDlZoneSelStyle
                    AsxEbsSsConfigSelStyle,
                asxEbsSsProvUlZoneIndex
                    Integer32,
                asxEbsSsProvUlZoneSelStyle
                    AsxEbsSsConfigSelStyle,
                asxEbsSsProvDiuc
                    Integer32,
                asxEbsSsProvDiucSelStyle
                    AsxEbsSsConfigSelStyle,
                asxEbsSsProvUiuc
                    Integer32,
                asxEbsSsProvUiucSelStyle
                    AsxEbsSsConfigSelStyle,
                asxEbsSsProvCSType
                    CSTypes,
                asxEbsSsProvRowStatus
                    RowStatus,
                asxEbsSsProvMaxUlSubchannels
                    Integer32,
                asxEbsSsProvDlMatrixStyle
                    AsxEbsSsConfigSelStyle,
                asxEbsSsProvFixedDlMatrix
                    AsxEbsStcMatrix,
                asxEbsSsProvDlMatrixBMaxMcs
                    WmanIf2OfdmaDcdFecCode,
                asxEbsSsProvControlMode
                    AsxEbsMsControlMode,
                asxEbsSsProvUlMatrixStyle
                    AsxEbsSsConfigSelStyle,
                asxEbsSsProvFixedUlMatrix
                    AsxEbsStcMatrix
             }

        -- 1.3.6.1.4.1.989.1.16.2.7.6.1.1.1
        asxEbsSsProvInService OBJECT-TYPE
            SYNTAX AsmaxBooleanSwitch
            MAX-ACCESS read-create
            STATUS current
            DESCRIPTION
                "Defines in service state of the port."
            DEFVAL { booleanTrue }
            ::= { asxEbsSsProvEntry 1 }

        
        -- 1.3.6.1.4.1.989.1.16.2.7.6.1.1.2
        asxEbsSsProvDlZoneIndex OBJECT-TYPE
            SYNTAX Integer32 (0..2147483647)
            MAX-ACCESS read-create
            STATUS current
            DESCRIPTION
                "Fixed downlink Zone index used when selection style is fixed."
            ::= { asxEbsSsProvEntry 2 }

        
        -- 1.3.6.1.4.1.989.1.16.2.7.6.1.1.3
        asxEbsSsProvDlZoneSelStyle OBJECT-TYPE
            SYNTAX AsxEbsSsConfigSelStyle
            MAX-ACCESS read-create
            STATUS current
            DESCRIPTION
                "When fixed BS uses corresponding fixed config."
            DEFVAL { selStyleDynamic }
            ::= { asxEbsSsProvEntry 3 }

        
        -- 1.3.6.1.4.1.989.1.16.2.7.6.1.1.4
        asxEbsSsProvUlZoneIndex OBJECT-TYPE
            SYNTAX Integer32 (0..2147483647)
            MAX-ACCESS read-create
            STATUS current
            DESCRIPTION
                "Fixed uplink Zone index used when selection style is fixed."
            ::= { asxEbsSsProvEntry 4 }

        
        -- 1.3.6.1.4.1.989.1.16.2.7.6.1.1.5
        asxEbsSsProvUlZoneSelStyle OBJECT-TYPE
            SYNTAX AsxEbsSsConfigSelStyle
            MAX-ACCESS read-create
            STATUS current
            DESCRIPTION
                "When fixed BS uses corresponding fixed config."
            DEFVAL { selStyleDynamic }
            ::= { asxEbsSsProvEntry 5 }

        
        -- 1.3.6.1.4.1.989.1.16.2.7.6.1.1.6
        asxEbsSsProvDiuc OBJECT-TYPE
            SYNTAX Integer32 (0..12)
            MAX-ACCESS read-create
            STATUS current
            DESCRIPTION
                "Fixed DIUC used when selection style is fixed."
            ::= { asxEbsSsProvEntry 6 }

        
        -- 1.3.6.1.4.1.989.1.16.2.7.6.1.1.7
        asxEbsSsProvDiucSelStyle OBJECT-TYPE
            SYNTAX AsxEbsSsConfigSelStyle
            MAX-ACCESS read-create
            STATUS current
            DESCRIPTION
                "When fixed BS uses corresponding fixed config."
            DEFVAL { selStyleDynamic }
            ::= { asxEbsSsProvEntry 7 }

        
        -- 1.3.6.1.4.1.989.1.16.2.7.6.1.1.8
        asxEbsSsProvUiuc OBJECT-TYPE
            SYNTAX Integer32 (1..10)
            MAX-ACCESS read-create
            STATUS current
            DESCRIPTION
                "Fixed UIUC used when selection style is fixed."
            ::= { asxEbsSsProvEntry 8 }

        
        -- 1.3.6.1.4.1.989.1.16.2.7.6.1.1.9
        asxEbsSsProvUiucSelStyle OBJECT-TYPE
            SYNTAX AsxEbsSsConfigSelStyle
            MAX-ACCESS read-create
            STATUS current
            DESCRIPTION
                "When fixed BS uses corresponding fixed config."
            DEFVAL { selStyleDynamic }
            ::= { asxEbsSsProvEntry 9 }

        
        -- 1.3.6.1.4.1.989.1.16.2.7.6.1.1.10
        asxEbsSsProvCSType OBJECT-TYPE
            SYNTAX CSTypes
            MAX-ACCESS read-create
            STATUS current
            DESCRIPTION
                "Convergence Sublayer Type applicable to each of the service flows of this SS"
            DEFVAL { packetIpV4 }
            ::= { asxEbsSsProvEntry 10 }

        
        -- 1.3.6.1.4.1.989.1.16.2.7.6.1.1.11
        asxEbsSsProvRowStatus OBJECT-TYPE
            SYNTAX RowStatus
            MAX-ACCESS read-create
            STATUS current
            DESCRIPTION
                "Description."
            ::= { asxEbsSsProvEntry 11 }

        
        -- 1.3.6.1.4.1.989.1.16.2.7.6.1.1.12
        asxEbsSsProvMaxUlSubchannels OBJECT-TYPE
            SYNTAX Integer32
            MAX-ACCESS read-create
            STATUS current
            DESCRIPTION
                "Indicates the maximum number of subchannels that an uplink burst from this SS may use. A value of 0 inidicates that there is no limit."
            ::= { asxEbsSsProvEntry 12 }

        
        -- 1.3.6.1.4.1.989.1.16.2.7.6.1.1.13
        asxEbsSsProvDlMatrixStyle OBJECT-TYPE
            SYNTAX AsxEbsSsConfigSelStyle
            MAX-ACCESS read-create
            STATUS current
            DESCRIPTION
                "When the SS receives downlink bursts in a MIMO zone,
                selects whether the MIMO Matrix is fixed or dynamically determined. "
            DEFVAL { selStyleDynamic }
            ::= { asxEbsSsProvEntry 13 }

        
        -- 1.3.6.1.4.1.989.1.16.2.7.6.1.1.14
        asxEbsSsProvFixedDlMatrix OBJECT-TYPE
            SYNTAX AsxEbsStcMatrix
            MAX-ACCESS read-create
            STATUS current
            DESCRIPTION
                "Sets the Matrix used in fixed MIMO mode. 0 = MatrixA, 1 = MatrixB."
            DEFVAL { matrixA }
            ::= { asxEbsSsProvEntry 14 }

        
        -- 1.3.6.1.4.1.989.1.16.2.7.6.1.1.15
        asxEbsSsProvDlMatrixBMaxMcs OBJECT-TYPE
            SYNTAX WmanIf2OfdmaDcdFecCode
            MAX-ACCESS read-create
            STATUS current
            DESCRIPTION
                "The maximum modulation/FEC to be used for MatrixB allocations.
                Note that unlike the (sector table) matrixBMinMcs, this is
                in MCS, NOT an index into a table of MCS."
            DEFVAL { sixtyFourQamCtc5Over6 }
            ::= { asxEbsSsProvEntry 15 }

        
        -- 1.3.6.1.4.1.989.1.16.2.7.6.1.1.16
        asxEbsSsProvControlMode OBJECT-TYPE
            SYNTAX AsxEbsMsControlMode
            MAX-ACCESS read-create
            STATUS current
            DESCRIPTION
                "Defines how the MS will be contolled and provisioned."
            DEFVAL { msControlModeMibAndAsnGw }
            ::= { asxEbsSsProvEntry 16 }

        
        -- 1.3.6.1.4.1.989.1.16.2.7.6.1.1.17
        asxEbsSsProvUlMatrixStyle OBJECT-TYPE
            SYNTAX AsxEbsSsConfigSelStyle
            MAX-ACCESS read-create
            STATUS current
            DESCRIPTION
                "Selects whether the MIMO Matrix used for uplink grants is fixed or dynamically determined. Has no effect for grants in a non-MIMO zone."
            DEFVAL { selStyleDynamic }
            ::= { asxEbsSsProvEntry 17 }

        
        -- 1.3.6.1.4.1.989.1.16.2.7.6.1.1.18
        asxEbsSsProvFixedUlMatrix OBJECT-TYPE
            SYNTAX AsxEbsStcMatrix
            MAX-ACCESS read-create
            STATUS current
            DESCRIPTION
                "Sets the Matrix used in fixed uplink MIMO mode. 0 = MatrixA, 1 = MatrixB. Has no effect for grants in a non-MIMO zone."
            DEFVAL { matrixA }
            ::= { asxEbsSsProvEntry 18 }

        
        -- 1.3.6.1.4.1.989.1.16.2.7.6.2
        asxEbsSsStatusTable OBJECT-TYPE
            SYNTAX SEQUENCE OF AsxEbsSsStatusEntry
            MAX-ACCESS not-accessible
            STATUS current
            DESCRIPTION
                "Table reporting status of registered MS. Also used to trigger MS commands."
            ::= { asxEbsSs 2 }

        
        -- 1.3.6.1.4.1.989.1.16.2.7.6.2.1
        asxEbsSsStatusEntry OBJECT-TYPE
            SYNTAX AsxEbsSsStatusEntry
            MAX-ACCESS not-accessible
            STATUS current
            DESCRIPTION
                "Description."
            INDEX { ifIndex, wmanIf2BsSsMacAddress }
            ::= { asxEbsSsStatusTable 1 }

        
        AsxEbsSsStatusEntry ::=
            SEQUENCE { 
                asxEbsSsStatRequestedOptions
                    SsCapabilityOptions,
                asxEbsSsStatGrantedOptions
                    SsCapabilityOptions,
                asxEbsSsStatDeregisterCmd
                    AsxEbsCommand,
                asxEbsSsStatDeregisterAction
                    INTEGER,
                asxEbsSsStatResetCmd
                    AsxEbsCommand
             }

        -- 1.3.6.1.4.1.989.1.16.2.7.6.2.1.1
        asxEbsSsStatRequestedOptions OBJECT-TYPE
            SYNTAX SsCapabilityOptions
            MAX-ACCESS read-only
            STATUS current
            DESCRIPTION
                "SS requested options in bitmap."
            ::= { asxEbsSsStatusEntry 1 }

        
        -- 1.3.6.1.4.1.989.1.16.2.7.6.2.1.2
        asxEbsSsStatGrantedOptions OBJECT-TYPE
            SYNTAX SsCapabilityOptions
            MAX-ACCESS read-only
            STATUS current
            DESCRIPTION
                "SS granted options in bitmap."
            ::= { asxEbsSsStatusEntry 2 }

        
        -- 1.3.6.1.4.1.989.1.16.2.7.6.2.1.3
        asxEbsSsStatDeregisterCmd OBJECT-TYPE
            SYNTAX AsxEbsCommand
            MAX-ACCESS read-write
            STATUS current
            DESCRIPTION
                "Set to 'do' to trigger a reset of the SS. The system sets it back to 'idle' on execution.
                BS uses DREG-CMD message to instruct MS to reset itself."
            ::= { asxEbsSsStatusEntry 3 }

        
        -- 1.3.6.1.4.1.989.1.16.2.7.6.2.1.4
        asxEbsSsStatDeregisterAction OBJECT-TYPE
            SYNTAX INTEGER
                {
                ssDeregActionTerminateService(0),
                ssDeregActionListenOnly(1),
                ssDeregActionListenWithManagement(2),
                ssDeregActionReturnToNormal(3),
                ssDeregActionGoToIdle(5)
                }
            MAX-ACCESS read-write
            STATUS current
            DESCRIPTION
                "The type of de-registration to perform when the command is invoked 
                with the object asxEbsSsStatDeregisterCmd."
            DEFVAL { ssDeregActionTerminateService }
            ::= { asxEbsSsStatusEntry 4 }

        
        -- 1.3.6.1.4.1.989.1.16.2.7.6.2.1.5
        asxEbsSsStatResetCmd OBJECT-TYPE
            SYNTAX AsxEbsCommand
            MAX-ACCESS read-write
            STATUS current
            DESCRIPTION
                "Set to 'do' to trigger a reset of the SS. The system sets it back to 'idle' on execution.
                BS uses RES-CMD message to instruct MS to reset itself."
            ::= { asxEbsSsStatusEntry 5 }

        
        -- 1.3.6.1.4.1.989.1.16.2.7.6.3
        asxEbsSsClassTable OBJECT-TYPE
            SYNTAX SEQUENCE OF AsxEbsSsClassEntry
            MAX-ACCESS not-accessible
            STATUS current
            DESCRIPTION
                "Class based provisioning equivalent of table asxEbsSsProvTable."
            ::= { asxEbsSs 3 }

        
        -- 1.3.6.1.4.1.989.1.16.2.7.6.3.1
        asxEbsSsClassEntry OBJECT-TYPE
            SYNTAX AsxEbsSsClassEntry
            MAX-ACCESS not-accessible
            STATUS current
            DESCRIPTION
                "Configuration of SS for class based provisioning of SS."
            INDEX { ifIndex, asxEbsSsClassName }
            ::= { asxEbsSsClassTable 1 }

        
        AsxEbsSsClassEntry ::=
            SEQUENCE { 
                asxEbsSsClassName
                    AsxEbsClassName,
                asxEbsSsClassInService
                    AsmaxBooleanSwitch,
                asxEbsSsClassDlZoneIndex
                    Integer32,
                asxEbsSsClassDlZoneSelStyle
                    AsxEbsSsConfigSelStyle,
                asxEbsSsClassUlZoneIndex
                    Integer32,
                asxEbsSsClassUlZoneSelStyle
                    AsxEbsSsConfigSelStyle,
                asxEbsSsClassDiuc
                    Integer32,
                asxEbsSsClassDiucSelStyle
                    AsxEbsSsConfigSelStyle,
                asxEbsSsClassUiuc
                    Integer32,
                asxEbsSsClassUiucSelStyle
                    AsxEbsSsConfigSelStyle,
                asxEbsSsClassCSType
                    CSTypes,
                asxEbsSsClassRowStatus
                    RowStatus,
                asxEbsSsClassMaxUlSubchannels
                    Integer32,
                asxEbsSsClassDlMatrixStyle
                    AsxEbsSsConfigSelStyle,
                asxEbsSsClassFixedDlMatrix
                    AsxEbsStcMatrix,
                asxEbsSsClassDlMatrixBMaxMcs
                    WmanIf2OfdmaDcdFecCode,
                asxEbsSsClassControlMode
                    AsxEbsMsControlMode,
                asxEbsSsClassForceCsFromMib
                    AsmaxBooleanSwitch,
                asxEbsSsClassUlMatrixStyle
                    AsxEbsSsConfigSelStyle,
                asxEbsSsClassFixedUlMatrix
                    AsxEbsStcMatrix
             }

        -- 1.3.6.1.4.1.989.1.16.2.7.6.3.1.1
        asxEbsSsClassName OBJECT-TYPE
            SYNTAX AsxEbsClassName
            MAX-ACCESS not-accessible
            STATUS current
            DESCRIPTION
                "Description."
            ::= { asxEbsSsClassEntry 1 }

        
        -- 1.3.6.1.4.1.989.1.16.2.7.6.3.1.2
        asxEbsSsClassInService OBJECT-TYPE
            SYNTAX AsmaxBooleanSwitch
            MAX-ACCESS read-create
            STATUS current
            DESCRIPTION
                "Defines in service state of the port of SS using this class."
            DEFVAL { booleanTrue }
            ::= { asxEbsSsClassEntry 2 }

        
        -- 1.3.6.1.4.1.989.1.16.2.7.6.3.1.3
        asxEbsSsClassDlZoneIndex OBJECT-TYPE
            SYNTAX Integer32 (0..2147483647)
            MAX-ACCESS read-create
            STATUS current
            DESCRIPTION
                "Fixed downlink Zone index used when selection style is fixed."
            ::= { asxEbsSsClassEntry 3 }

        
        -- 1.3.6.1.4.1.989.1.16.2.7.6.3.1.4
        asxEbsSsClassDlZoneSelStyle OBJECT-TYPE
            SYNTAX AsxEbsSsConfigSelStyle
            MAX-ACCESS read-create
            STATUS current
            DESCRIPTION
                "When fixed BS uses corresponding fixed config."
            DEFVAL { selStyleDynamic }
            ::= { asxEbsSsClassEntry 4 }

        
        -- 1.3.6.1.4.1.989.1.16.2.7.6.3.1.5
        asxEbsSsClassUlZoneIndex OBJECT-TYPE
            SYNTAX Integer32 (0..2147483647)
            MAX-ACCESS read-create
            STATUS current
            DESCRIPTION
                "Fixed uplink Zone index used when selection style is fixed."
            ::= { asxEbsSsClassEntry 5 }

        
        -- 1.3.6.1.4.1.989.1.16.2.7.6.3.1.6
        asxEbsSsClassUlZoneSelStyle OBJECT-TYPE
            SYNTAX AsxEbsSsConfigSelStyle
            MAX-ACCESS read-create
            STATUS current
            DESCRIPTION
                "When fixed BS uses corresponding fixed config."
            DEFVAL { selStyleDynamic }
            ::= { asxEbsSsClassEntry 6 }

        
        -- 1.3.6.1.4.1.989.1.16.2.7.6.3.1.7
        asxEbsSsClassDiuc OBJECT-TYPE
            SYNTAX Integer32 (0..12)
            MAX-ACCESS read-create
            STATUS current
            DESCRIPTION
                "Fixed DIUC used when selection style is fixed."
            ::= { asxEbsSsClassEntry 7 }

        
        -- 1.3.6.1.4.1.989.1.16.2.7.6.3.1.8
        asxEbsSsClassDiucSelStyle OBJECT-TYPE
            SYNTAX AsxEbsSsConfigSelStyle
            MAX-ACCESS read-create
            STATUS current
            DESCRIPTION
                "When fixed BS uses corresponding fixed config."
            DEFVAL { selStyleDynamic }
            ::= { asxEbsSsClassEntry 8 }

        
        -- 1.3.6.1.4.1.989.1.16.2.7.6.3.1.9
        asxEbsSsClassUiuc OBJECT-TYPE
            SYNTAX Integer32 (1..10)
            MAX-ACCESS read-create
            STATUS current
            DESCRIPTION
                "Fixed UIUC used when selection style is fixed."
            ::= { asxEbsSsClassEntry 9 }

        
        -- 1.3.6.1.4.1.989.1.16.2.7.6.3.1.10
        asxEbsSsClassUiucSelStyle OBJECT-TYPE
            SYNTAX AsxEbsSsConfigSelStyle
            MAX-ACCESS read-create
            STATUS current
            DESCRIPTION
                "When fixed BS uses corresponding fixed config."
            DEFVAL { selStyleDynamic }
            ::= { asxEbsSsClassEntry 10 }

        
        -- 1.3.6.1.4.1.989.1.16.2.7.6.3.1.11
        asxEbsSsClassCSType OBJECT-TYPE
            SYNTAX CSTypes
            MAX-ACCESS read-create
            STATUS current
            DESCRIPTION
                "Convergence Sublayer Type applicable to each of the service flows of this SS"
            DEFVAL { packetIpV4 }
            ::= { asxEbsSsClassEntry 11 }

        
        -- 1.3.6.1.4.1.989.1.16.2.7.6.3.1.12
        asxEbsSsClassRowStatus OBJECT-TYPE
            SYNTAX RowStatus
            MAX-ACCESS read-create
            STATUS current
            DESCRIPTION
                "Description."
            ::= { asxEbsSsClassEntry 12 }

        
        -- 1.3.6.1.4.1.989.1.16.2.7.6.3.1.13
        asxEbsSsClassMaxUlSubchannels OBJECT-TYPE
            SYNTAX Integer32
            MAX-ACCESS read-create
            STATUS current
            DESCRIPTION
                "Indicates the maximum number of subchannels that an uplink burst from this SS may use. A value of 0 inidicates that there is no limit."
            ::= { asxEbsSsClassEntry 13 }

        
        -- 1.3.6.1.4.1.989.1.16.2.7.6.3.1.14
        asxEbsSsClassDlMatrixStyle OBJECT-TYPE
            SYNTAX AsxEbsSsConfigSelStyle
            MAX-ACCESS read-create
            STATUS current
            DESCRIPTION
                "When the SS receives downlink bursts in a MIMO zone,
                selects whether the MIMO Matrix is fixed or dynamically determined. "
            DEFVAL { selStyleDynamic }
            ::= { asxEbsSsClassEntry 14 }

        
        -- 1.3.6.1.4.1.989.1.16.2.7.6.3.1.15
        asxEbsSsClassFixedDlMatrix OBJECT-TYPE
            SYNTAX AsxEbsStcMatrix
            MAX-ACCESS read-create
            STATUS current
            DESCRIPTION
                "Sets the Matrix used in fixed MIMO mode. 0 = MatrixA, 1 = MatrixB."
            DEFVAL { matrixA }
            ::= { asxEbsSsClassEntry 15 }

        
        -- 1.3.6.1.4.1.989.1.16.2.7.6.3.1.16
        asxEbsSsClassDlMatrixBMaxMcs OBJECT-TYPE
            SYNTAX WmanIf2OfdmaDcdFecCode
            MAX-ACCESS read-create
            STATUS current
            DESCRIPTION
                "The maximum modulation/FEC to be used for MatrixB allocations.
                Note that unlike the (sector table) matrixBMinMcs, this is
                in MCS, NOT an index into a table of MCS."
            DEFVAL { sixtyFourQamCtc5Over6 }
            ::= { asxEbsSsClassEntry 16 }

        
        -- 1.3.6.1.4.1.989.1.16.2.7.6.3.1.17
        asxEbsSsClassControlMode OBJECT-TYPE
            SYNTAX AsxEbsMsControlMode
            MAX-ACCESS read-create
            STATUS current
            DESCRIPTION
                "Defines how the MS will be contolled and provisioned."
            DEFVAL { msControlModeAsnGw }
            ::= { asxEbsSsClassEntry 17 }

        
        -- 1.3.6.1.4.1.989.1.16.2.7.6.3.1.18
        asxEbsSsClassForceCsFromMib OBJECT-TYPE
            SYNTAX AsmaxBooleanSwitch
            MAX-ACCESS read-create
            STATUS current
            DESCRIPTION
                "If true, the CS type is taken only from the SS class, and the CS type from the ASN-GW/AAA is ignored."
            DEFVAL { booleanFalse }
            ::= { asxEbsSsClassEntry 18 }

        
        -- 1.3.6.1.4.1.989.1.16.2.7.6.3.1.19
        asxEbsSsClassUlMatrixStyle OBJECT-TYPE
            SYNTAX AsxEbsSsConfigSelStyle
            MAX-ACCESS read-create
            STATUS current
            DESCRIPTION
                "Selects whether the MIMO Matrix used for uplink grants is fixed or dynamically determined. Has no effect for grants in a non-MIMO zone."
            DEFVAL { selStyleDynamic }
            ::= { asxEbsSsClassEntry 19 }

        
        -- 1.3.6.1.4.1.989.1.16.2.7.6.3.1.20
        asxEbsSsClassFixedUlMatrix OBJECT-TYPE
            SYNTAX AsxEbsStcMatrix
            MAX-ACCESS read-create
            STATUS current
            DESCRIPTION
                "Sets the Matrix used in fixed uplink MIMO mode. 0 = MatrixA, 1 = MatrixB. Has no effect for grants in a non-MIMO zone."
            DEFVAL { matrixA }
            ::= { asxEbsSsClassEntry 20 }

        
        -- 1.3.6.1.4.1.989.1.16.2.7.7
        asxEbsRf OBJECT IDENTIFIER ::= { asMaxEbs 7 }

        
        -- 1.3.6.1.4.1.989.1.16.2.7.7.1
        asxEbsRfCfgTable OBJECT-TYPE
            SYNTAX SEQUENCE OF AsxEbsRfCfgEntry
            MAX-ACCESS not-accessible
            STATUS current
            DESCRIPTION
                "Description."
            ::= { asxEbsRf 1 }

        
        -- 1.3.6.1.4.1.989.1.16.2.7.7.1.1
        asxEbsRfCfgEntry OBJECT-TYPE
            SYNTAX AsxEbsRfCfgEntry
            MAX-ACCESS not-accessible
            STATUS current
            DESCRIPTION
                "Description."
            INDEX { asxEbsRfPathId }
            ::= { asxEbsRfCfgTable 1 }

        
        AsxEbsRfCfgEntry ::=
            SEQUENCE { 
                asxEbsRfPathId
                    Integer32,
                asxEbsRfPaInService
                    AsmaxBooleanSwitch,
                asxEbsRfReset
                    AsmaxBooleanSwitch
             }

        -- 1.3.6.1.4.1.989.1.16.2.7.7.1.1.1
        asxEbsRfPathId OBJECT-TYPE
            SYNTAX Integer32 (0..65535)
            MAX-ACCESS accessible-for-notify
            STATUS current
            DESCRIPTION
                "Index to identify particular RF Path.
                The index starts from 0, although this throws a warning,
                in order to match the index range in IIB mapping"
            ::= { asxEbsRfCfgEntry 1 }

        
        -- 1.3.6.1.4.1.989.1.16.2.7.7.1.1.2
        asxEbsRfPaInService OBJECT-TYPE
            SYNTAX AsmaxBooleanSwitch
            MAX-ACCESS read-write
            STATUS current
            DESCRIPTION
                "Puts the PA for this Path In Service or Out of Service"
            DEFVAL { booleanTrue }
            ::= { asxEbsRfCfgEntry 2 }

        
        -- 1.3.6.1.4.1.989.1.16.2.7.7.1.1.3
        asxEbsRfReset OBJECT-TYPE
            SYNTAX AsmaxBooleanSwitch
            MAX-ACCESS read-write
            STATUS current
            DESCRIPTION
                "Resets a particular antenna"
            DEFVAL { booleanFalse }
            ::= { asxEbsRfCfgEntry 3 }

        
        -- 1.3.6.1.4.1.989.1.16.2.7.7.2
        asxEbsRfStatusTable OBJECT-TYPE
            SYNTAX SEQUENCE OF AsxEbsRfStatusEntry
            MAX-ACCESS not-accessible
            STATUS current
            DESCRIPTION
                "Reports current status of each RF Path."
            ::= { asxEbsRf 2 }

        
        -- 1.3.6.1.4.1.989.1.16.2.7.7.2.1
        asxEbsRfStatusEntry OBJECT-TYPE
            SYNTAX AsxEbsRfStatusEntry
            MAX-ACCESS not-accessible
            STATUS current
            DESCRIPTION
                "One row per RF Path."
            INDEX { asxEbsRfPathId }
            ::= { asxEbsRfStatusTable 1 }

        
        AsxEbsRfStatusEntry ::=
            SEQUENCE { 
                asxEbsRfPathStatus
                    AsxEbsRfPathStatus,
                asxEbsRfPathStatusInfo
                    DisplayString,
                asxEbsRfStatusAchievedTxPower
                    Integer32,
                asxEbsRfStatusAchievedRxGain
                    Integer32,
                asxEbsRfStatusMeasuredTxPower
                    Integer32,
                asxEbsRfStatusMeasuredVswr
                    Integer32,
                asxEbsRfStatusScrtFwdPower
                    Integer32,
                asxEbsRfStatusScrtRevPower
                    Integer32
             }

        -- 1.3.6.1.4.1.989.1.16.2.7.7.2.1.1
        asxEbsRfPathStatus OBJECT-TYPE
            SYNTAX AsxEbsRfPathStatus
            MAX-ACCESS read-only
            STATUS current
            DESCRIPTION
                "Reports current status of RF Path."
            ::= { asxEbsRfStatusEntry 1 }

        
        -- 1.3.6.1.4.1.989.1.16.2.7.7.2.1.2
        asxEbsRfPathStatusInfo OBJECT-TYPE
            SYNTAX DisplayString
            MAX-ACCESS read-only
            STATUS deprecated
            DESCRIPTION
                "Indicates any problem in text. Where practical multiple faults 
                can be indicated by a comma separated list"
            ::= { asxEbsRfStatusEntry 2 }

        
        -- 1.3.6.1.4.1.989.1.16.2.7.7.2.1.3
        asxEbsRfStatusAchievedTxPower OBJECT-TYPE
            SYNTAX Integer32 (0..2147483647)
            UNITS "1/100 dBm"
            MAX-ACCESS read-only
            STATUS current
            DESCRIPTION
                "The actual Tx power to which the transmitter is set.
                NOTE: this is the nearest value achievable from the cal tables "
            ::= { asxEbsRfStatusEntry 3 }

        
        -- 1.3.6.1.4.1.989.1.16.2.7.7.2.1.4
        asxEbsRfStatusAchievedRxGain OBJECT-TYPE
            SYNTAX Integer32 (0..2147483647)
            UNITS "1/100 dB"
            MAX-ACCESS read-only
            STATUS current
            DESCRIPTION
                "The actual Rx gain to which the transmitter is set.
                NOTE: this is the nearest value achievable from the cal tables "
            ::= { asxEbsRfStatusEntry 4 }

        
        -- 1.3.6.1.4.1.989.1.16.2.7.7.2.1.5
        asxEbsRfStatusMeasuredTxPower OBJECT-TYPE
            SYNTAX Integer32 (0..2147483647)
            UNITS "1/100 dBm"
            MAX-ACCESS read-only
            STATUS current
            DESCRIPTION
                "The measured Tx power. "
            ::= { asxEbsRfStatusEntry 5 }

        
        -- 1.3.6.1.4.1.989.1.16.2.7.7.2.1.6
        asxEbsRfStatusMeasuredVswr OBJECT-TYPE
            SYNTAX Integer32
            UNITS "1/100 dB"
            MAX-ACCESS read-only
            STATUS current
            DESCRIPTION
                "The measured VSWR. "
            ::= { asxEbsRfStatusEntry 6 }

        
        -- 1.3.6.1.4.1.989.1.16.2.7.7.2.1.7
        asxEbsRfStatusScrtFwdPower OBJECT-TYPE
            SYNTAX Integer32
            MAX-ACCESS read-only
            STATUS current
            DESCRIPTION
                "The forward power as measured by the SCRT in arbitary or calibrated units."
            ::= { asxEbsRfStatusEntry 7 }

        
        -- 1.3.6.1.4.1.989.1.16.2.7.7.2.1.8
        asxEbsRfStatusScrtRevPower OBJECT-TYPE
            SYNTAX Integer32
            MAX-ACCESS read-only
            STATUS current
            DESCRIPTION
                "The reverse power as measured by the SCRT in or calibrated arbitary units."
            ::= { asxEbsRfStatusEntry 8 }

        
        -- 1.3.6.1.4.1.989.1.16.2.7.8
        asxEbsMsm OBJECT IDENTIFIER ::= { asMaxEbs 8 }

        
        -- 1.3.6.1.4.1.989.1.16.2.7.8.1
        asxEbsMsmStatusTable OBJECT-TYPE
            SYNTAX SEQUENCE OF AsxEbsMsmStatusEntry
            MAX-ACCESS not-accessible
            STATUS current
            DESCRIPTION
                "Reports current status of the MSM, if fitted."
            ::= { asxEbsMsm 1 }

        
        -- 1.3.6.1.4.1.989.1.16.2.7.8.1.1
        asxEbsMsmStatusEntry OBJECT-TYPE
            SYNTAX AsxEbsMsmStatusEntry
            MAX-ACCESS not-accessible
            STATUS current
            DESCRIPTION
                "A single row table."
            INDEX { asxEbsBsIndex }
            ::= { asxEbsMsmStatusTable 1 }

        
        AsxEbsMsmStatusEntry ::=
            SEQUENCE { 
                asxEbsMsmPresent
                    AsmaxBooleanSwitch,
                asxEbsMsmStatus
                    AsxEbsMsmStatus,
                asxEbsMsmStatusInfo
                    DisplayString,
                asxEbsMsmStatusHardwareType
                    AsxEbsMsmHardwareType,
                asxEbsMsmStatusFirmwareVersion
                    Integer32,
                asxEbsMsmStatusFpgaVersion
                    Integer32,
                asxEbsMsmStatusFirmwareUpgradeRequired
                    AsmaxBooleanSwitch,
                asxEbsMsmStatus50HzClockError
                    AsmaxBooleanSwitch,
                asxEbsMsmStatus25HzClockError
                    AsmaxBooleanSwitch,
                asxEbsMsmStatusFirmwareError
                    AsmaxBooleanSwitch,
                asxEbsMsmStatus100BaseFxOpticalModuleError
                    AsmaxBooleanSwitch,
                asxEbsMsmStatus100BaseFxLosError
                    AsmaxBooleanSwitch,
                asxEbsMsmStatus100BaseFxTxFault
                    AsmaxBooleanSwitch,
                asxEbsMsmStatus1000BaseSxOpticalModuleError
                    AsmaxBooleanSwitch,
                asxEbsMsmStatus1000BaseSxLosError
                    AsmaxBooleanSwitch,
                asxEbsMsmStatus1000BaseSxTxFault
                    AsmaxBooleanSwitch,
                asxEbsMsmStatusOverallPortStatus
                    AsxEbsMsmPortOverallStatus,
                asxEbsMsmStatusOverallPortStatusInfo
                    DisplayString
             }

        -- 1.3.6.1.4.1.989.1.16.2.7.8.1.1.1
        asxEbsMsmPresent OBJECT-TYPE
            SYNTAX AsmaxBooleanSwitch
            MAX-ACCESS read-only
            STATUS current
            DESCRIPTION
                "Denotes whether the MSM is fitted or not"
            DEFVAL { booleanFalse }
            ::= { asxEbsMsmStatusEntry 1 }

        
        -- 1.3.6.1.4.1.989.1.16.2.7.8.1.1.2
        asxEbsMsmStatus OBJECT-TYPE
            SYNTAX AsxEbsMsmStatus
            MAX-ACCESS read-only
            STATUS current
            DESCRIPTION
                "Reports current status of MSM as a whole."
            ::= { asxEbsMsmStatusEntry 2 }

        
        -- 1.3.6.1.4.1.989.1.16.2.7.8.1.1.3
        asxEbsMsmStatusInfo OBJECT-TYPE
            SYNTAX DisplayString
            MAX-ACCESS read-only
            STATUS current
            DESCRIPTION
                "Reports current status of MSM as a textual string."
            ::= { asxEbsMsmStatusEntry 3 }

        
        -- 1.3.6.1.4.1.989.1.16.2.7.8.1.1.4
        asxEbsMsmStatusHardwareType OBJECT-TYPE
            SYNTAX AsxEbsMsmHardwareType
            MAX-ACCESS read-write
            STATUS current
            DESCRIPTION
                "Denotes the variant of MSM hardware."
            ::= { asxEbsMsmStatusEntry 4 }

        
        -- 1.3.6.1.4.1.989.1.16.2.7.8.1.1.5
        asxEbsMsmStatusFirmwareVersion OBJECT-TYPE
            SYNTAX Integer32
            MAX-ACCESS read-write
            STATUS current
            DESCRIPTION
                "Version of MSM Firmware."
            ::= { asxEbsMsmStatusEntry 5 }

        
        -- 1.3.6.1.4.1.989.1.16.2.7.8.1.1.6
        asxEbsMsmStatusFpgaVersion OBJECT-TYPE
            SYNTAX Integer32
            MAX-ACCESS read-write
            STATUS current
            DESCRIPTION
                "Version of MSM FPGA."
            ::= { asxEbsMsmStatusEntry 6 }

        
        -- 1.3.6.1.4.1.989.1.16.2.7.8.1.1.7
        asxEbsMsmStatusFirmwareUpgradeRequired OBJECT-TYPE
            SYNTAX AsmaxBooleanSwitch
            MAX-ACCESS read-only
            STATUS current
            DESCRIPTION
                "Indicates if the firmware needs upgrading to use the latest fpga image."
            DEFVAL { booleanFalse }
            ::= { asxEbsMsmStatusEntry 7 }

        
        -- 1.3.6.1.4.1.989.1.16.2.7.8.1.1.8
        asxEbsMsmStatus50HzClockError OBJECT-TYPE
            SYNTAX AsmaxBooleanSwitch
            MAX-ACCESS read-only
            STATUS current
            DESCRIPTION
                "Denotes whether there is a 50Hz Clock Error"
            DEFVAL { booleanFalse }
            ::= { asxEbsMsmStatusEntry 8 }

        
        -- 1.3.6.1.4.1.989.1.16.2.7.8.1.1.9
        asxEbsMsmStatus25HzClockError OBJECT-TYPE
            SYNTAX AsmaxBooleanSwitch
            MAX-ACCESS read-only
            STATUS current
            DESCRIPTION
                "Denotes whether there is a 25Hz Clock Error"
            DEFVAL { booleanFalse }
            ::= { asxEbsMsmStatusEntry 9 }

        
        -- 1.3.6.1.4.1.989.1.16.2.7.8.1.1.10
        asxEbsMsmStatusFirmwareError OBJECT-TYPE
            SYNTAX AsmaxBooleanSwitch
            MAX-ACCESS read-only
            STATUS current
            DESCRIPTION
                "Denotes whether there is a Firmware Error"
            DEFVAL { booleanFalse }
            ::= { asxEbsMsmStatusEntry 10 }

        
        -- 1.3.6.1.4.1.989.1.16.2.7.8.1.1.11
        asxEbsMsmStatus100BaseFxOpticalModuleError OBJECT-TYPE
            SYNTAX AsmaxBooleanSwitch
            MAX-ACCESS read-only
            STATUS current
            DESCRIPTION
                "100BASE-FX optical module error"
            DEFVAL { booleanFalse }
            ::= { asxEbsMsmStatusEntry 11 }

        
        -- 1.3.6.1.4.1.989.1.16.2.7.8.1.1.12
        asxEbsMsmStatus100BaseFxLosError OBJECT-TYPE
            SYNTAX AsmaxBooleanSwitch
            MAX-ACCESS read-only
            STATUS current
            DESCRIPTION
                "100BASE-FX loss of signal error"
            DEFVAL { booleanFalse }
            ::= { asxEbsMsmStatusEntry 12 }

        
        -- 1.3.6.1.4.1.989.1.16.2.7.8.1.1.13
        asxEbsMsmStatus100BaseFxTxFault OBJECT-TYPE
            SYNTAX AsmaxBooleanSwitch
            MAX-ACCESS read-only
            STATUS current
            DESCRIPTION
                "100BASE-FX transmit fault"
            DEFVAL { booleanFalse }
            ::= { asxEbsMsmStatusEntry 13 }

        
        -- 1.3.6.1.4.1.989.1.16.2.7.8.1.1.14
        asxEbsMsmStatus1000BaseSxOpticalModuleError OBJECT-TYPE
            SYNTAX AsmaxBooleanSwitch
            MAX-ACCESS read-only
            STATUS current
            DESCRIPTION
                "1000BASE-SX optical module error"
            DEFVAL { booleanFalse }
            ::= { asxEbsMsmStatusEntry 14 }

        
        -- 1.3.6.1.4.1.989.1.16.2.7.8.1.1.15
        asxEbsMsmStatus1000BaseSxLosError OBJECT-TYPE
            SYNTAX AsmaxBooleanSwitch
            MAX-ACCESS read-only
            STATUS current
            DESCRIPTION
                "1000BASE-SX loss of signal error"
            DEFVAL { booleanFalse }
            ::= { asxEbsMsmStatusEntry 15 }

        
        -- 1.3.6.1.4.1.989.1.16.2.7.8.1.1.16
        asxEbsMsmStatus1000BaseSxTxFault OBJECT-TYPE
            SYNTAX AsmaxBooleanSwitch
            MAX-ACCESS read-only
            STATUS current
            DESCRIPTION
                "1000BASE-SX transmit fault"
            DEFVAL { booleanFalse }
            ::= { asxEbsMsmStatusEntry 16 }

        
        -- 1.3.6.1.4.1.989.1.16.2.7.8.1.1.17
        asxEbsMsmStatusOverallPortStatus OBJECT-TYPE
            SYNTAX AsxEbsMsmPortOverallStatus
            MAX-ACCESS read-only
            STATUS current
            DESCRIPTION
                "A bit field which denotes those ports on the MSM on which there is a fault"
            ::= { asxEbsMsmStatusEntry 17 }

        
        -- 1.3.6.1.4.1.989.1.16.2.7.8.1.1.18
        asxEbsMsmStatusOverallPortStatusInfo OBJECT-TYPE
            SYNTAX DisplayString
            MAX-ACCESS read-only
            STATUS current
            DESCRIPTION
                "A textual string which can be used to indicate why there has been a change in asxEbsMsmStatusOverallPortStatus."
            ::= { asxEbsMsmStatusEntry 18 }

        
        -- 1.3.6.1.4.1.989.1.16.2.7.8.2
        asxEbsMsmCfgTable OBJECT-TYPE
            SYNTAX SEQUENCE OF AsxEbsMsmCfgEntry
            MAX-ACCESS not-accessible
            STATUS current
            DESCRIPTION
                "Configuration/ Actions for the MSM, if fitted."
            ::= { asxEbsMsm 2 }

        
        -- 1.3.6.1.4.1.989.1.16.2.7.8.2.1
        asxEbsMsmCfgEntry OBJECT-TYPE
            SYNTAX AsxEbsMsmCfgEntry
            MAX-ACCESS not-accessible
            STATUS current
            DESCRIPTION
                "Description."
            INDEX { asxEbsBsIndex }
            ::= { asxEbsMsmCfgTable 1 }

        
        AsxEbsMsmCfgEntry ::=
            SEQUENCE { 
                asxEbsMsmCfgReset
                    AsmaxBooleanSwitch,
                asxEbsMsmCfgShutdownOpticalModule
                    AsmaxBooleanSwitch
             }

        -- 1.3.6.1.4.1.989.1.16.2.7.8.2.1.1
        asxEbsMsmCfgReset OBJECT-TYPE
            SYNTAX AsmaxBooleanSwitch
            MAX-ACCESS read-write
            STATUS current
            DESCRIPTION
                "Set to TRUE to reset the MSM."
            DEFVAL { booleanFalse }
            ::= { asxEbsMsmCfgEntry 1 }

        
        -- 1.3.6.1.4.1.989.1.16.2.7.8.2.1.2
        asxEbsMsmCfgShutdownOpticalModule OBJECT-TYPE
            SYNTAX AsmaxBooleanSwitch
            MAX-ACCESS read-write
            STATUS current
            DESCRIPTION
                "Set to TRUE to shutdown the MSM Optical Module."
            DEFVAL { booleanFalse }
            ::= { asxEbsMsmCfgEntry 2 }

        
        -- 1.3.6.1.4.1.989.1.16.2.7.8.3
        asxEbsMsmPortCfgTable OBJECT-TYPE
            SYNTAX SEQUENCE OF AsxEbsMsmPortCfgEntry
            MAX-ACCESS not-accessible
            STATUS current
            DESCRIPTION
                "Configuration/ Actions for the MSM ports, if fitted."
            ::= { asxEbsMsm 3 }

        
        -- 1.3.6.1.4.1.989.1.16.2.7.8.3.1
        asxEbsMsmPortCfgEntry OBJECT-TYPE
            SYNTAX AsxEbsMsmPortCfgEntry
            MAX-ACCESS not-accessible
            STATUS current
            DESCRIPTION
                "Description."
            INDEX { asxEbsMsmPortIndex }
            ::= { asxEbsMsmPortCfgTable 1 }

        
        AsxEbsMsmPortCfgEntry ::=
            SEQUENCE { 
                asxEbsMsmPortIndex
                    Integer32,
                asxEbsMsmPortAdminStatus
                    AsxEbsMsmPortAdminStatus
             }

        -- 1.3.6.1.4.1.989.1.16.2.7.8.3.1.1
        asxEbsMsmPortIndex OBJECT-TYPE
            SYNTAX Integer32 (1..6)
            MAX-ACCESS not-accessible
            STATUS current
            DESCRIPTION
                "An arbitrary index to identify an MSM port."
            ::= { asxEbsMsmPortCfgEntry 1 }

        
        -- 1.3.6.1.4.1.989.1.16.2.7.8.3.1.2
        asxEbsMsmPortAdminStatus OBJECT-TYPE
            SYNTAX AsxEbsMsmPortAdminStatus
            MAX-ACCESS read-write
            STATUS current
            DESCRIPTION
                "Denotes the required state for the port."
            ::= { asxEbsMsmPortCfgEntry 2 }

        
        -- 1.3.6.1.4.1.989.1.16.2.7.8.4
        asxEbsMsmPortStatusTable OBJECT-TYPE
            SYNTAX SEQUENCE OF AsxEbsMsmPortStatusEntry
            MAX-ACCESS not-accessible
            STATUS current
            DESCRIPTION
                "Status for the MSM ports, if the MSM is fitted."
            ::= { asxEbsMsm 4 }

        
        -- 1.3.6.1.4.1.989.1.16.2.7.8.4.1
        asxEbsMsmPortStatusEntry OBJECT-TYPE
            SYNTAX AsxEbsMsmPortStatusEntry
            MAX-ACCESS not-accessible
            STATUS current
            DESCRIPTION
                "Description."
            INDEX { asxEbsMsmPortIndex }
            ::= { asxEbsMsmPortStatusTable 1 }

        
        AsxEbsMsmPortStatusEntry ::=
            SEQUENCE { 
                asxEbsMsmPortStatusPortDesc
                    DisplayString,
                asxEbsMsmPortStatusLinkStatus
                    AsxEbsMsmPortOperationalStatus,
                asxEbsMsmPortStatusSpeed
                    AsxEbsMsmPortStatusSpeed,
                asxEbsMsmPortStatusDuplexMode
                    EthernetDuplexMode
             }

        -- 1.3.6.1.4.1.989.1.16.2.7.8.4.1.1
        asxEbsMsmPortStatusPortDesc OBJECT-TYPE
            SYNTAX DisplayString
            MAX-ACCESS read-only
            STATUS current
            DESCRIPTION
                "A textual description to permit identification of the port."
            ::= { asxEbsMsmPortStatusEntry 1 }

        
        -- 1.3.6.1.4.1.989.1.16.2.7.8.4.1.2
        asxEbsMsmPortStatusLinkStatus OBJECT-TYPE
            SYNTAX AsxEbsMsmPortOperationalStatus
            MAX-ACCESS read-only
            STATUS current
            DESCRIPTION
                "The current operational state of the port"
            ::= { asxEbsMsmPortStatusEntry 2 }

        
        -- 1.3.6.1.4.1.989.1.16.2.7.8.4.1.3
        asxEbsMsmPortStatusSpeed OBJECT-TYPE
            SYNTAX AsxEbsMsmPortStatusSpeed
            MAX-ACCESS read-only
            STATUS current
            DESCRIPTION
                "The current speed for the port."
            ::= { asxEbsMsmPortStatusEntry 3 }

        
        -- 1.3.6.1.4.1.989.1.16.2.7.8.4.1.4
        asxEbsMsmPortStatusDuplexMode OBJECT-TYPE
            SYNTAX EthernetDuplexMode
            MAX-ACCESS read-only
            STATUS current
            DESCRIPTION
                "The current ethernet duplex mode for the port."
            ::= { asxEbsMsmPortStatusEntry 4 }

        
        -- 1.3.6.1.4.1.989.1.16.2.7.9
        asxEbsGps OBJECT IDENTIFIER ::= { asMaxEbs 9 }

        
        -- 1.3.6.1.4.1.989.1.16.2.7.9.1
        asxEbsGpsCw25StatusTable OBJECT-TYPE
            SYNTAX SEQUENCE OF AsxEbsGpsCw25StatusEntry
            MAX-ACCESS not-accessible
            STATUS current
            DESCRIPTION
                "Description."
            ::= { asxEbsGps 1 }

        
        -- 1.3.6.1.4.1.989.1.16.2.7.9.1.1
        asxEbsGpsCw25StatusEntry OBJECT-TYPE
            SYNTAX AsxEbsGpsCw25StatusEntry
            MAX-ACCESS not-accessible
            STATUS current
            DESCRIPTION
                "Description."
            INDEX { asMaxBsCmGpsInstance }
            ::= { asxEbsGpsCw25StatusTable 1 }

        
        AsxEbsGpsCw25StatusEntry ::=
            SEQUENCE { 
                asxEbsGpsCw25Mode
                    INTEGER,
                asxEbsGpsCw25LedStatus
                    INTEGER,
                asxEbsGpsCw25HoldoverGuaranteedStatus
                    INTEGER,
                asxEbsGpsCw25HoldoverDegradedStatus
                    INTEGER,
                asxEbsGpsCw25StatusSvSnr
                    OCTET STRING
             }

        -- 1.3.6.1.4.1.989.1.16.2.7.9.1.1.1
        asxEbsGpsCw25Mode OBJECT-TYPE
            SYNTAX INTEGER
                {
                modeUnknown(0),
                modeInitialising(1),
                modeLockedWarmUp(2),
                modeLocked(3),
                modeLockedWtrDegraded(4),
                modeLockedWtrExpired(5),
                modeHoldoverGuaranteed(6),
                modeHoldoverDegraded(7),
                modeHoldoverExpired(8)
                }
            MAX-ACCESS read-only
            STATUS current
            DESCRIPTION
                "Current working mode. "
            ::= { asxEbsGpsCw25StatusEntry 1 }

        
        -- 1.3.6.1.4.1.989.1.16.2.7.9.1.1.2
        asxEbsGpsCw25LedStatus OBJECT-TYPE
            SYNTAX INTEGER
                {
                cw25LedsOff(0),
                cw25LedsRedOn(1),
                cw25LedsGreenOn(2),
                cw25LedsGreenRedOn(3)
                }
            MAX-ACCESS read-only
            STATUS current
            DESCRIPTION
                "GPS LED status indicating GPS lock / out-of-lock. "
            ::= { asxEbsGpsCw25StatusEntry 2 }

        
        -- 1.3.6.1.4.1.989.1.16.2.7.9.1.1.3
        asxEbsGpsCw25HoldoverGuaranteedStatus OBJECT-TYPE
            SYNTAX INTEGER (0..30000)
            UNITS "s"
            MAX-ACCESS read-only
            STATUS current
            DESCRIPTION
                "Time remaining in Holdover Guaranteed Mode in seconds. In normal operation, this value is equal to the configured Holdover Guaranteed Period."
            ::= { asxEbsGpsCw25StatusEntry 3 }

        
        -- 1.3.6.1.4.1.989.1.16.2.7.9.1.1.4
        asxEbsGpsCw25HoldoverDegradedStatus OBJECT-TYPE
            SYNTAX INTEGER (0..1000)
            UNITS "mins"
            MAX-ACCESS read-only
            STATUS current
            DESCRIPTION
                "Time remaining in Holdover Degraded Mode in minutes. In normal operation, this value is equal to the configured Holdover Degraded Period. "
            ::= { asxEbsGpsCw25StatusEntry 4 }

        
        -- 1.3.6.1.4.1.989.1.16.2.7.9.1.1.5
        asxEbsGpsCw25StatusSvSnr OBJECT-TYPE
            SYNTAX OCTET STRING (SIZE (12))
            UNITS "dB"
            MAX-ACCESS read-only
            STATUS current
            DESCRIPTION
                "SNR of satellite in view, reported in a byte-array."
            ::= { asxEbsGpsCw25StatusEntry 5 }

        
        -- 1.3.6.1.4.1.989.1.16.2.7.9.2
        asxEbsGpsCw25ConfigTable OBJECT-TYPE
            SYNTAX SEQUENCE OF AsxEbsGpsCw25ConfigEntry
            MAX-ACCESS not-accessible
            STATUS current
            DESCRIPTION
                "Configures CW25 specific GPS configuration. For OSA, refer to BS-Common mib."
            ::= { asxEbsGps 2 }

        
        -- 1.3.6.1.4.1.989.1.16.2.7.9.2.1
        asxEbsGpsCw25ConfigEntry OBJECT-TYPE
            SYNTAX AsxEbsGpsCw25ConfigEntry
            MAX-ACCESS not-accessible
            STATUS current
            DESCRIPTION
                "CW25 specific GPS configuration."
            INDEX { asMaxBsCmGpsInstance }
            ::= { asxEbsGpsCw25ConfigTable 1 }

        
        AsxEbsGpsCw25ConfigEntry ::=
            SEQUENCE { 
                asxEbsGpsCw25ModeMU
                    INTEGER,
                asxEbsGpsCw25HoldoverGuaranteedPeriod
                    Unsigned32,
                asxEbsGpsCw25HoldoverDegradedPeriod
                    Unsigned32,
                asxEbsGpsCw25DegradedBehaviour
                    INTEGER,
                asxEbsGpsCw25ExpiredBehaviour
                    INTEGER,
                asxEbsGpsCw25ResetGps
                    AsmaxBooleanSwitch
             }

        -- 1.3.6.1.4.1.989.1.16.2.7.9.2.1.1
        asxEbsGpsCw25ModeMU OBJECT-TYPE
            SYNTAX INTEGER
                {
                modeAutomatic(0),
                modeHoldover(1)
                }
            MAX-ACCESS read-write
            STATUS current
            DESCRIPTION
                "User Working Mode. "
            DEFVAL { modeAutomatic }
            ::= { asxEbsGpsCw25ConfigEntry 1 }

        
        -- 1.3.6.1.4.1.989.1.16.2.7.9.2.1.2
        asxEbsGpsCw25HoldoverGuaranteedPeriod OBJECT-TYPE
            SYNTAX Unsigned32 (0..30000)
            UNITS "s"
            MAX-ACCESS read-write
            STATUS current
            DESCRIPTION
                "Time Period OCXO can accurately holdover when GPS signal lost. "
            DEFVAL { 60 }
            ::= { asxEbsGpsCw25ConfigEntry 2 }

        
        -- 1.3.6.1.4.1.989.1.16.2.7.9.2.1.3
        asxEbsGpsCw25HoldoverDegradedPeriod OBJECT-TYPE
            SYNTAX Unsigned32 (0..1000)
            UNITS "mins"
            MAX-ACCESS read-write
            STATUS current
            DESCRIPTION
                "Time Period OCXO can accurately holdover in Degraded Mode."
            DEFVAL { 60 }
            ::= { asxEbsGpsCw25ConfigEntry 3 }

        
        -- 1.3.6.1.4.1.989.1.16.2.7.9.2.1.4
        asxEbsGpsCw25DegradedBehaviour OBJECT-TYPE
            SYNTAX INTEGER
                {
                behaviourStopRadio(0),
                behaviourNoAction(1),
                behaviourDegraded(2)
                }
            MAX-ACCESS read-write
            STATUS current
            DESCRIPTION
                "Action to take when Degraded Mode is entered."
            DEFVAL { behaviourDegraded }
            ::= { asxEbsGpsCw25ConfigEntry 4 }

        
        -- 1.3.6.1.4.1.989.1.16.2.7.9.2.1.5
        asxEbsGpsCw25ExpiredBehaviour OBJECT-TYPE
            SYNTAX INTEGER
                {
                behaviourStopRadio(0),
                behaviourNoAction(1),
                behaviourDegraded(2)
                }
            MAX-ACCESS read-write
            STATUS current
            DESCRIPTION
                "Action to take when Expired Mode is entered. "
            DEFVAL { behaviourStopRadio }
            ::= { asxEbsGpsCw25ConfigEntry 5 }

        
        -- 1.3.6.1.4.1.989.1.16.2.7.9.2.1.6
        asxEbsGpsCw25ResetGps OBJECT-TYPE
            SYNTAX AsmaxBooleanSwitch
            MAX-ACCESS read-write
            STATUS current
            DESCRIPTION
                "Set to TRUE to force reset of GPS module."
            DEFVAL { booleanFalse }
            ::= { asxEbsGpsCw25ConfigEntry 6 }

        
        -- 1.3.6.1.4.1.989.1.16.2.7.10
        asxEbsVoip OBJECT IDENTIFIER ::= { asMaxEbs 10 }

        
        -- 1.3.6.1.4.1.989.1.16.2.7.10.1
        asxEbsVoipCfgTable OBJECT-TYPE
            SYNTAX SEQUENCE OF AsxEbsVoipCfgEntry
            MAX-ACCESS not-accessible
            STATUS current
            DESCRIPTION
                "Description."
            ::= { asxEbsVoip 1 }

        
        -- 1.3.6.1.4.1.989.1.16.2.7.10.1.1
        asxEbsVoipCfgEntry OBJECT-TYPE
            SYNTAX AsxEbsVoipCfgEntry
            MAX-ACCESS not-accessible
            STATUS current
            DESCRIPTION
                "Description."
            INDEX { asxEbsVoipCfgId }
            ::= { asxEbsVoipCfgTable 1 }

        
        AsxEbsVoipCfgEntry ::=
            SEQUENCE { 
                asxEbsVoipCfgId
                    Unsigned32,
                asxEbsVoipCfgEnabled
                    AsmaxBooleanSwitch,
                asxEbsVoipCfgServerAddressType
                    InetAddressType,
                asxEbsVoipCfgServerAddress
                    InetAddress,
                asxEbsVoipCfgMaxBandwidth
                    Unsigned32,
                asxEbsVoipCfgMaxCalls
                    Unsigned32,
                asxEbsVoipCfgMaxMsCalls
                    Unsigned32,
                asxEbsVoipCfgMaxSfCalls
                    Unsigned32,
                asxEbsVoipCfgLocalTcpPort
                    Unsigned32,
                asxEbsVoipCfgDiscoveryPort
                    Unsigned32,
                asxEbsVoipCfgUplinkServiceClassId
                    Unsigned32,
                asxEbsVoipCfgDownlinkServiceClassId
                    Unsigned32,
                asxEbsVoipCfgGainPerPacket
                    Unsigned32
             }

        -- 1.3.6.1.4.1.989.1.16.2.7.10.1.1.1
        asxEbsVoipCfgId OBJECT-TYPE
            SYNTAX Unsigned32 (1)
            MAX-ACCESS not-accessible
            STATUS current
            DESCRIPTION
                "Instance of the voicemax configuration. Only one configuration instance is allowed."
            ::= { asxEbsVoipCfgEntry 1 }

        
        -- 1.3.6.1.4.1.989.1.16.2.7.10.1.1.2
        asxEbsVoipCfgEnabled OBJECT-TYPE
            SYNTAX AsmaxBooleanSwitch
            MAX-ACCESS read-write
            STATUS current
            DESCRIPTION
                "Set to TRUE to enable the operation of VoiceMAX. "
            DEFVAL { 0 }
            ::= { asxEbsVoipCfgEntry 2 }

        
        -- 1.3.6.1.4.1.989.1.16.2.7.10.1.1.3
        asxEbsVoipCfgServerAddressType OBJECT-TYPE
            SYNTAX InetAddressType
            MAX-ACCESS read-write
            STATUS current
            DESCRIPTION
                "Indicates the type of the IP addresses used by the VoiceMAX server. "
            DEFVAL { ipv4 }
            ::= { asxEbsVoipCfgEntry 3 }

        
        -- 1.3.6.1.4.1.989.1.16.2.7.10.1.1.4
        asxEbsVoipCfgServerAddress OBJECT-TYPE
            SYNTAX InetAddress
            MAX-ACCESS read-write
            STATUS current
            DESCRIPTION
                "Description."
            DEFVAL { "0.0.0.0" }
            ::= { asxEbsVoipCfgEntry 4 }

        
        -- 1.3.6.1.4.1.989.1.16.2.7.10.1.1.5
        asxEbsVoipCfgMaxBandwidth OBJECT-TYPE
            SYNTAX Unsigned32 (0..4294967295)
            MAX-ACCESS read-write
            STATUS current
            DESCRIPTION
                "The maximum bandwidth (kbps) allocated for VoIP. "
            DEFVAL { 2048 }
            ::= { asxEbsVoipCfgEntry 5 }

        
        -- 1.3.6.1.4.1.989.1.16.2.7.10.1.1.6
        asxEbsVoipCfgMaxCalls OBJECT-TYPE
            SYNTAX Unsigned32 (0..4294967295)
            MAX-ACCESS read-write
            STATUS current
            DESCRIPTION
                "The maximum allowed VoIP calls. "
            DEFVAL { 100 }
            ::= { asxEbsVoipCfgEntry 6 }

        
        -- 1.3.6.1.4.1.989.1.16.2.7.10.1.1.7
        asxEbsVoipCfgMaxMsCalls OBJECT-TYPE
            SYNTAX Unsigned32 (1..128)
            MAX-ACCESS read-write
            STATUS current
            DESCRIPTION
                "The maximum allowed VoIP calls for MS."
            DEFVAL { 4 }
            ::= { asxEbsVoipCfgEntry 7 }

        
        -- 1.3.6.1.4.1.989.1.16.2.7.10.1.1.8
        asxEbsVoipCfgMaxSfCalls OBJECT-TYPE
            SYNTAX Unsigned32 (1..8)
            MAX-ACCESS read-write
            STATUS current
            DESCRIPTION
                "The maximum allowed VoIP calls on one SF."
            DEFVAL { 1 }
            ::= { asxEbsVoipCfgEntry 8 }

        
        -- 1.3.6.1.4.1.989.1.16.2.7.10.1.1.9
        asxEbsVoipCfgLocalTcpPort OBJECT-TYPE
            SYNTAX Unsigned32 (1024..65535)
            MAX-ACCESS read-write
            STATUS current
            DESCRIPTION
                "The local TCP port on which BS will listen for VoiceMAX server connection. "
            DEFVAL { 2000 }
            ::= { asxEbsVoipCfgEntry 9 }

        
        -- 1.3.6.1.4.1.989.1.16.2.7.10.1.1.10
        asxEbsVoipCfgDiscoveryPort OBJECT-TYPE
            SYNTAX Unsigned32 (1024..65535)
            MAX-ACCESS read-write
            STATUS current
            DESCRIPTION
                "Description."
            DEFVAL { 5888 }
            ::= { asxEbsVoipCfgEntry 10 }

        
        -- 1.3.6.1.4.1.989.1.16.2.7.10.1.1.11
        asxEbsVoipCfgUplinkServiceClassId OBJECT-TYPE
            SYNTAX Unsigned32
            MAX-ACCESS read-write
            STATUS current
            DESCRIPTION
                "The service class that is used to supply the service flow configuration for uplink service flows created by the VoiceMAX. "
            DEFVAL { 0 }
            ::= { asxEbsVoipCfgEntry 11 }

        
        -- 1.3.6.1.4.1.989.1.16.2.7.10.1.1.12
        asxEbsVoipCfgDownlinkServiceClassId OBJECT-TYPE
            SYNTAX Unsigned32
            MAX-ACCESS read-write
            STATUS current
            DESCRIPTION
                "The service class that is used to supply the service flow configuration for downlink service flows created by the VoiceMAX. "
            DEFVAL { 0 }
            ::= { asxEbsVoipCfgEntry 12 }

        
        -- 1.3.6.1.4.1.989.1.16.2.7.10.1.1.13
        asxEbsVoipCfgGainPerPacket OBJECT-TYPE
            SYNTAX Unsigned32 (0..65535)
            MAX-ACCESS read-write
            STATUS current
            DESCRIPTION
                "A spare BW allocation per packet. "
            DEFVAL { 10 }
            ::= { asxEbsVoipCfgEntry 13 }

        
        -- 1.3.6.1.4.1.989.1.16.2.7.10.2
        asxEbsVoipStatusTable OBJECT-TYPE
            SYNTAX SEQUENCE OF AsxEbsVoipStatusEntry
            MAX-ACCESS not-accessible
            STATUS current
            DESCRIPTION
                "Description."
            ::= { asxEbsVoip 2 }

        
        -- 1.3.6.1.4.1.989.1.16.2.7.10.2.1
        asxEbsVoipStatusEntry OBJECT-TYPE
            SYNTAX AsxEbsVoipStatusEntry
            MAX-ACCESS not-accessible
            STATUS current
            DESCRIPTION
                "Description."
            INDEX { asxEbsVoipCfgId }
            ::= { asxEbsVoipStatusTable 1 }

        
        AsxEbsVoipStatusEntry ::=
            SEQUENCE { 
                asxEbsVoipStatusUsedBandwidth
                    Unsigned32,
                asxEbsVoipStatusUsedCalls
                    Unsigned32
             }

        -- 1.3.6.1.4.1.989.1.16.2.7.10.2.1.1
        asxEbsVoipStatusUsedBandwidth OBJECT-TYPE
            SYNTAX Unsigned32 (0..4294967295)
            MAX-ACCESS read-only
            STATUS current
            DESCRIPTION
                "The bandwidth (kbps) currently allocated for VoIP. "
            DEFVAL { 0 }
            ::= { asxEbsVoipStatusEntry 1 }

        
        -- 1.3.6.1.4.1.989.1.16.2.7.10.2.1.2
        asxEbsVoipStatusUsedCalls OBJECT-TYPE
            SYNTAX Unsigned32 (0..4294967295)
            MAX-ACCESS read-only
            STATUS current
            DESCRIPTION
                "The current VoIP calls."
            DEFVAL { 0 }
            ::= { asxEbsVoipStatusEntry 2 }

        
    
    END

--
-- ASMAX-EBS-MIB.mib
--
