NEC-WIMAX-BS-IF-MIB DEFINITIONS ::= BEGIN
    IMPORTS
    MODULE-IDENTITY, OBJECT-TYPE, Integer32,
    Counter64, Unsigned32, IpAddress, enterprises,
    Counter32
        FROM SNMPv2-SMI
    OBJECT-GROUP
        FROM SNMPv2-CONF
    ifIndex
        FROM IF-MIB
    TruthValue, MacAddress, RowStatus, TEXTUAL-CONVENTION
        FROM SNMPv2-TC;

    necWimaxBsIfMib MODULE-IDENTITY
        LAST-UPDATED        "200811050000Z"
        ORGANIZATION        "NEC/J MWN"
        CONTACT-INFO        "NEC/J MWN"
        DESCRIPTION         "NEC WIMAX BS IF MIB: Revision 5.6"

        ::= { wimaxbs 2 }

    NecWimaxBsMacVersion ::= TEXTUAL-CONVENTION
        STATUS              current
        DESCRIPTION         "Version number of IEEE 802.16."
        SYNTAX              INTEGER {
                                ieee802Dot16Of2001( 1 ),
                                ieee802Dot16cOf2002( 2 ),
                                ieee802Dot16aOf2003( 3 ),
                                ieee802Dot16Of2004( 4 ),
                                ieee802Dot16eOf2005( 5 ),
                                ieee802Dot16fOf2005( 6 ),
                                ieee802Dot16gOf2007( 7 )
                            }



    nec OBJECT IDENTIFIER ::= { enterprises 119 }

    necmib OBJECT IDENTIFIER ::= { nec 2 }

    necProductDepend OBJECT IDENTIFIER ::= { necmib 3 }

    wa802 OBJECT IDENTIFIER ::= { necProductDepend 163 }

    wimaxbs OBJECT IDENTIFIER ::= { wa802 100 }

    necWimaxBsIfObjects OBJECT IDENTIFIER ::= { necWimaxBsIfMib 1 }

    necWimaxBsCps OBJECT IDENTIFIER ::= { necWimaxBsIfObjects 1 }

    necWimaxBsCapabilities OBJECT IDENTIFIER ::= { necWimaxBsCps 1 }

    necWimaxBsBasicCapabilitiesTable OBJECT-TYPE
        SYNTAX              SEQUENCE OF NecWimaxBsBasicCapabilitiesEntry
        MAX-ACCESS          not-accessible
        STATUS              current
        DESCRIPTION         "BS Capabilities"
        ::= { necWimaxBsCapabilities 1 }

    necWimaxBsBasicCapabilitiesEntry OBJECT-TYPE
        SYNTAX              NecWimaxBsBasicCapabilitiesEntry
        MAX-ACCESS          not-accessible
        STATUS              current
        DESCRIPTION         "basic"
        INDEX               {
                                ifIndex
                            }
        ::= { necWimaxBsBasicCapabilitiesTable 1 }

    NecWimaxBsBasicCapabilitiesEntry ::= SEQUENCE {
        necWimaxBsCapFragmentSupport
            INTEGER,
        necWimaxBsCapHarqSupport
            INTEGER,
        necWimaxBsCapHarqPduSn
            INTEGER
    }

    necWimaxBsCapFragmentSupport OBJECT-TYPE
        SYNTAX              INTEGER {
                                disable( 0 ),
                                enable( 1 )
                            }
        MAX-ACCESS          read-only
        STATUS              current
        DESCRIPTION         "Fragment support"
        ::= { necWimaxBsBasicCapabilitiesEntry 1 }

    necWimaxBsCapHarqSupport OBJECT-TYPE
        SYNTAX              INTEGER {
                                disable( 0 ),
                                enable( 1 )
                            }
        MAX-ACCESS          read-only
        STATUS              current
        DESCRIPTION         "HARQ support"
        ::= { necWimaxBsBasicCapabilitiesEntry 2 }

    necWimaxBsCapHarqPduSn OBJECT-TYPE
        SYNTAX              INTEGER {
                                none( 0 ),
                                short( 1 ),
                                long( 2 )
                            }
        MAX-ACCESS          read-only
        STATUS              current
        DESCRIPTION         "PDU SN extended subheader for HARQ reordering.
                            Indicate whether PDU SN extended subheader is
                            used. This parameter is only applicable to HARQ
                            Service Flow = 1. default value = 0"
        ::= { necWimaxBsBasicCapabilitiesEntry 3 }

    necWimaxBsCapabilitiesConfigTable OBJECT-TYPE
        SYNTAX              SEQUENCE OF NecWimaxBsCapabilitiesConfigEntry
        MAX-ACCESS          not-accessible
        STATUS              current
        DESCRIPTION         "BS Capabilities"
        ::= { necWimaxBsCapabilities 2 }

    necWimaxBsCapabilitiesConfigEntry OBJECT-TYPE
        SYNTAX              NecWimaxBsCapabilitiesConfigEntry
        MAX-ACCESS          not-accessible
        STATUS              current
        DESCRIPTION         "basic"
        INDEX               {
                                ifIndex
                            }
        ::= { necWimaxBsCapabilitiesConfigTable 1 }

    NecWimaxBsCapabilitiesConfigEntry ::= SEQUENCE {
        necWimaxBsCapCfgFragmentSupport
            INTEGER,
        necWimaxBsCapCfgHarqSupport
            INTEGER,
        necWimaxBsCapCfgHarqPduSn
            INTEGER
    }

    necWimaxBsCapCfgFragmentSupport OBJECT-TYPE
        SYNTAX              INTEGER {
                                disable( 0 ),
                                enable( 1 )
                            }
        MAX-ACCESS          read-write
        STATUS              current
        DESCRIPTION         "Fragment support"
        ::= { necWimaxBsCapabilitiesConfigEntry 1 }

    necWimaxBsCapCfgHarqSupport OBJECT-TYPE
        SYNTAX              INTEGER {
                                disable( 0 ),
                                enable( 1 )
                            }
        MAX-ACCESS          read-write
        STATUS              current
        DESCRIPTION         "HARQ support"
        ::= { necWimaxBsCapabilitiesConfigEntry 2 }

    necWimaxBsCapCfgHarqPduSn OBJECT-TYPE
        SYNTAX              INTEGER {
                                none( 0 ),
                                short( 1 ),
                                long( 2 )
                            }
        MAX-ACCESS          read-write
        STATUS              current
        DESCRIPTION         "PDU SN extended subheader for HARQ reordering.
                            Indicate whether PDU SN extended subheader is
                            used. This parameter is only applicable to HARQ
                            Service Flow = 1. default value = 0"
        ::= { necWimaxBsCapabilitiesConfigEntry 3 }

    necWimaxBsIfConfigurationsTable OBJECT-TYPE
        SYNTAX              SEQUENCE OF NecWimaxBsIfConfigurationsEntry
        MAX-ACCESS          not-accessible
        STATUS              current
        DESCRIPTION         "This table provides one row for each BS sector
                            that contains the BS system parameters as defined
                            in Subclause 10.1 of [3]. The objects in this
                            table define the default behaviour of the BS
                            for 2nd Management connection scheduling and
                            SFID allocation as well as configuration parameters
                            of the CPS scheduler and AAS system."
        ::= { necWimaxBsCps 2 }

    necWimaxBsIfConfigurationsEntry OBJECT-TYPE
        SYNTAX              NecWimaxBsIfConfigurationsEntry
        MAX-ACCESS          not-accessible
        STATUS              current
        DESCRIPTION         "This table is indexed by ifIndex with an ifType
                            of?H."
        INDEX               {
                                ifIndex
                            }
        ::= { necWimaxBsIfConfigurationsTable 1 }

    NecWimaxBsIfConfigurationsEntry ::= SEQUENCE {
        necWimaxBsDlUlRatio
            INTEGER,
        necWimaxBsPermutation
            INTEGER,
        necWimaxBsFuscPermBase
            Integer32,
        necWimaxBsFuscPrbsId
            Integer32,
        necWimaxBsPreambleId
            Integer32,
        necWimaxBsSegment
            INTEGER,
        necWimaxBsDlSubchannelBitmap
            BITS,
        necWimaxBsUlSubchannelBitmap
            OCTET STRING,
        necWimaxBsCompressedMap
            INTEGER,
        necWimaxBsDlMapRepitition
            INTEGER,
        necWimaxBsDcdUcdRepitition
            INTEGER,
        necWimaxBsAdmissionThreshold
            Integer32,
        necWimaxBsMinPhyRateUgs
            INTEGER,
        necWimaxBsMinPhyRateErtps
            INTEGER,
        necWimaxBsMinPhyRateRtps
            INTEGER,
        necWimaxBsMinPhyRateNrtps
            INTEGER,
        necWimaxBsMinPhyRateBe
            INTEGER,
        necWimaxBsAgingTimeout
            Integer32,
        necWimaxBsUlPuscRoration
            INTEGER,
        necWimaxBsPduSnWaitTime
            Integer32,
        necWimaxBsBwMode
            INTEGER,
        necWimaxBsMimoEnable
            INTEGER,
        necWimaxBsMimoMatrixMode
            INTEGER,
        necWimaxBsMimoFeedbackCycle
            INTEGER,
        necWimaxBsSsEntryNo
            Integer32,
        necWimaxBsDlMapEncodeType
            INTEGER,
        necWimaxBsFnRandseed
            INTEGER,
        necWimaxBsSduMaxDelay
            Unsigned32,
        necWimaxBsMaxSf
            Integer32,
        necWimaxBsFrameAdjustThreshold
            Unsigned32,
        necWimaxBsFrameSyncMode
            INTEGER,
        necWimaxBsRxInitRangMax
            Integer32,
        necWimaxBsRxHoRangMax
            Integer32,
        necWimaxBsRfCableLength
            Integer32,
        necWimaxBsOduAlarmControl
            Unsigned32,
        necWimaxBsTimingGapOffset
            Integer32,
        necWimaxBsSiiAdvInterval
            Integer32,
        necWimaxBsGmsEnable
            BITS,
        necWimaxBsMacVersion
            NecWimaxBsMacVersion,
        necWimaxBsMulticastRepetitionCount
            INTEGER,
        necWimaxBsBcpIeTransmitCount
            Integer32,
        necWimaxBsSegmentUl
            INTEGER,
        necWimaxBsCqichBwReq
            INTEGER,
        necWimaxBsFairnessMode
            INTEGER,
        necWimaxBsFairnessCounterResetPeriod
            Integer32,
        necWimaxBsMimoUlHarq
            INTEGER,
        necWimaxBsUlMimoEnable
            INTEGER,
        necWimaxBsNumOfSegment
            INTEGER,
        necWimaxBsFairnessCountMode
            INTEGER,
        necWimaxBsAdmissionThresholdDl
            Integer32,
        necWimaxBsAdmissionThresholdUl
            Integer32,
        necWimaxBsCongestionThresholdDl
            Integer32,
        necWimaxBsCongestionThresholdUl
            Integer32,
        necWimaxBsProportionalShare
            INTEGER,
        necWimaxBsShareRateUlRtvr
            Integer32,
        necWimaxBsShareRateUlNrtvr
            Integer32,
        necWimaxBsShareRateUlBe
            Integer32,
        necWimaxBsShareRateDlRtvr
            Integer32,
        necWimaxBsShareRateDlNrtvr
            Integer32,
        necWimaxBsShareRateDlBe
            Integer32,
        necWimaxBsThroughputCapacityDl
            Integer32,
        necWimaxBsThroughputCapacityUl
            Integer32
    }

    necWimaxBsDlUlRatio OBJECT-TYPE
        SYNTAX              INTEGER {
                                d35u12( 0 ),
                                d32u15( 1 ),
                                d29u18( 2 ),
                                d26u21( 3 )
                            }
        MAX-ACCESS          read-write
        STATUS              current
        DESCRIPTION         "This object indicates the pattern of the DL-Ul
                            ratio. default value = 1"
        ::= { necWimaxBsIfConfigurationsEntry 1 }

    necWimaxBsPermutation OBJECT-TYPE
        SYNTAX              INTEGER {
                                pusc( 0 ),
                                fusc( 1 )
                            }
        MAX-ACCESS          read-write
        STATUS              current
        DESCRIPTION         "If set to one, it is switched from the next symbol
                            of the DL-MAP transmission to FUSC. However,
                            in case of the segment effective, this parameter
                            disregards and becomes PUSC."
        ::= { necWimaxBsIfConfigurationsEntry 2 }

    necWimaxBsFuscPermBase OBJECT-TYPE
        SYNTAX              Integer32 (0..31)
        MAX-ACCESS          read-write
        STATUS              current
        DESCRIPTION         "This object indicates the value set to STC-zone
                            IE, at FUSC."
        ::= { necWimaxBsIfConfigurationsEntry 4 }

    necWimaxBsFuscPrbsId OBJECT-TYPE
        SYNTAX              Integer32 (0..2)
        MAX-ACCESS          read-write
        STATUS              current
        DESCRIPTION         "This object indicates the value set to STC-zone
                            IE, at FUSC."
        ::= { necWimaxBsIfConfigurationsEntry 5 }

    necWimaxBsPreambleId OBJECT-TYPE
        SYNTAX              Integer32 (0..113)
        MAX-ACCESS          read-write
        STATUS              current
        DESCRIPTION         "Priambl number. A different value in each BS segment
                            is set. The IDcell\segment number is decided
                            depending on this value. segment 0:0-31,96,99,102,105,108,111
                            segment 1:32-63,97,100,103,106,109,112 segment
                            2:64-95,98,101,104,107,110,113"
        REFERENCE           "Subclause 8.4.6.1.1, Table 309a, in IEEE Std 802.16e-2005"
        ::= { necWimaxBsIfConfigurationsEntry 6 }

    necWimaxBsSegment OBJECT-TYPE
        SYNTAX              INTEGER {
                                segmentDisable( 0 ),
                                segmentEnable( 1 )
                            }
        MAX-ACCESS          read-write
        STATUS              current
        DESCRIPTION         "This object indicates whether Segment is used."
        ::= { necWimaxBsIfConfigurationsEntry 7 }

    necWimaxBsDlSubchannelBitmap OBJECT-TYPE
        SYNTAX              BITS {
                                group0( 0 ),
                                group1( 1 ),
                                group2( 2 ),
                                group3( 3 ),
                                group4( 4 ),
                                group5( 5 )
                            }
        MAX-ACCESS          read-write
        STATUS              current
        DESCRIPTION         "This object specifies Major group used in the
                            DL."
        ::= { necWimaxBsIfConfigurationsEntry 8 }

    necWimaxBsUlSubchannelBitmap OBJECT-TYPE
        SYNTAX              OCTET STRING (SIZE(9))
        MAX-ACCESS          read-write
        STATUS              current
        DESCRIPTION         "This object specifies subchannel used in the UL.
                            The LSB of the last byte shall correspond to
                            subchannel 0. default value = 0x0000000007FFFFFFFF"
        ::= { necWimaxBsIfConfigurationsEntry 9 }

    necWimaxBsCompressedMap OBJECT-TYPE
        SYNTAX              INTEGER {
                                compressedMapDisable( 0 ),
                                compressedMapEnable( 1 )
                            }
        MAX-ACCESS          read-write
        STATUS              current
        DESCRIPTION         "This object indicates whether Comprssed-MAP is
                            used. In case of the H-ARQ function effective,
                            this parameter is disregarded and Compressed-MAP
                            is used without fail."
        ::= { necWimaxBsIfConfigurationsEntry 10 }

    necWimaxBsDlMapRepitition OBJECT-TYPE
        SYNTAX              INTEGER {
                                zero( 0 ),
                                two( 2 ),
                                four( 4 ),
                                six( 6 )
                            }
        MAX-ACCESS          read-write
        STATUS              current
        DESCRIPTION         "This object indicates whether the repetition is
                            used for the burst of DL-MAP and UL-MAP."
        ::= { necWimaxBsIfConfigurationsEntry 11 }

    necWimaxBsDcdUcdRepitition OBJECT-TYPE
        SYNTAX              INTEGER {
                                zero( 0 ),
                                two( 2 ),
                                four( 4 ),
                                six( 6 )
                            }
        MAX-ACCESS          read-write
        STATUS              current
        DESCRIPTION         "This object indicates whether the repetition is
                            used for DCD/UCD."
        ::= { necWimaxBsIfConfigurationsEntry 12 }

    necWimaxBsAdmissionThreshold OBJECT-TYPE
        SYNTAX              Integer32 (0..100)
        MAX-ACCESS          read-write
        STATUS              current
        DESCRIPTION         "This value decides the threshold in which the
                            service flow generation is refused with Admission
                            Control. If set to 0, AdmissionControl is not
                            done."
        ::= { necWimaxBsIfConfigurationsEntry 13 }

    necWimaxBsMinPhyRateUgs OBJECT-TYPE
        SYNTAX              INTEGER {
                                qpsk12( 0 ),
                                qpsk34( 1 ),
                                qam1612( 2 ),
                                qam1634( 3 ),
                                qam6412( 4 ),
                                qam6423( 5 ),
                                qam6456( 6 )
                            }
        MAX-ACCESS          read-write
        STATUS              current
        DESCRIPTION         "The minimum phy rate(for UGS). The lower limit
                            of BurstProfile used of the UGS service is this
                            value."
        ::= { necWimaxBsIfConfigurationsEntry 14 }

    necWimaxBsMinPhyRateErtps OBJECT-TYPE
        SYNTAX              INTEGER {
                                qpsk12( 0 ),
                                qpsk34( 1 ),
                                qam1612( 2 ),
                                qam1634( 3 ),
                                qam6412( 4 ),
                                qam6423( 5 ),
                                qam6456( 6 )
                            }
        MAX-ACCESS          read-write
        STATUS              current
        DESCRIPTION         "The minimum phy rate(for Ertps). The lower limit
                            of BurstProfile used of the Ertps service is
                            this value."
        ::= { necWimaxBsIfConfigurationsEntry 15 }

    necWimaxBsMinPhyRateRtps OBJECT-TYPE
        SYNTAX              INTEGER {
                                qpsk12( 0 ),
                                qpsk34( 1 ),
                                qam1612( 2 ),
                                qam1634( 3 ),
                                qam6412( 4 ),
                                qam6423( 5 ),
                                qam6456( 6 )
                            }
        MAX-ACCESS          read-write
        STATUS              current
        DESCRIPTION         "The minimum phy rate(for Rtps). The lower limit
                            of BurstProfile used of the Rtps service is this
                            value."
        ::= { necWimaxBsIfConfigurationsEntry 16 }

    necWimaxBsMinPhyRateNrtps OBJECT-TYPE
        SYNTAX              INTEGER {
                                qpsk12( 0 ),
                                qpsk34( 1 ),
                                qam1612( 2 ),
                                qam1634( 3 ),
                                qam6412( 4 ),
                                qam6423( 5 ),
                                qam6456( 6 )
                            }
        MAX-ACCESS          read-write
        STATUS              current
        DESCRIPTION         "The minimum phy rate(for Nrtps). The lower limit
                            of BurstProfile used of the Nrtps service is
                            this value."
        ::= { necWimaxBsIfConfigurationsEntry 17 }

    necWimaxBsMinPhyRateBe OBJECT-TYPE
        SYNTAX              INTEGER {
                                qpsk12( 0 ),
                                qpsk34( 1 ),
                                qam1612( 2 ),
                                qam1634( 3 ),
                                qam6412( 4 ),
                                qam6423( 5 ),
                                qam6456( 6 )
                            }
        MAX-ACCESS          read-write
        STATUS              current
        DESCRIPTION         "The minimum phy rate(for BE). The lower limit
                            of BurstProfile used of the BE service is this
                            value."
        ::= { necWimaxBsIfConfigurationsEntry 18 }

    necWimaxBsAgingTimeout OBJECT-TYPE
        SYNTAX              Integer32 (0..255)
        UNITS               "sec"
        MAX-ACCESS          read-write
        STATUS              current
        DESCRIPTION         "aging-timeout"
        ::= { necWimaxBsIfConfigurationsEntry 19 }

    necWimaxBsUlPuscRoration OBJECT-TYPE
        SYNTAX              INTEGER {
                                enable( 0 ),
                                disable( 1 )
                            }
        MAX-ACCESS          read-write
        STATUS              current
        DESCRIPTION         "ul-pusc-roration"
        ::= { necWimaxBsIfConfigurationsEntry 20 }

    necWimaxBsPduSnWaitTime OBJECT-TYPE
        SYNTAX              Integer32 (0..255)
        MAX-ACCESS          read-write
        STATUS              current
        DESCRIPTION         "In PDU SN reordering, this parameter is used to
                            calculate time to wait for the frame."
        ::= { necWimaxBsIfConfigurationsEntry 21 }

    necWimaxBsBwMode OBJECT-TYPE
        SYNTAX              INTEGER {
                                bw10MHz( 0 ),
                                bw5MHz( 1 ),
                                bw7MHz( 2 ),
                                bw875MHz( 3 )
                            }
        MAX-ACCESS          read-write
        STATUS              current
        DESCRIPTION         "BW"
        ::= { necWimaxBsIfConfigurationsEntry 22 }

    necWimaxBsMimoEnable OBJECT-TYPE
        SYNTAX              INTEGER {
                                disable( 0 ),
                                enable( 1 )
                            }
        MAX-ACCESS          read-write
        STATUS              current
        DESCRIPTION         "MIMO support"
        ::= { necWimaxBsIfConfigurationsEntry 23 }

    necWimaxBsMimoMatrixMode OBJECT-TYPE
        SYNTAX              INTEGER {
                                matrixA( 0 ),
                                matrixB( 1 ),
                                matrixAandB( 2 )
                            }
        MAX-ACCESS          read-write
        STATUS              current
        DESCRIPTION         "MIMO Matrix Mode"
        ::= { necWimaxBsIfConfigurationsEntry 24 }

    necWimaxBsMimoFeedbackCycle OBJECT-TYPE
        SYNTAX              INTEGER {
                                mimoFeedbackIsNotSent( 0 ),
                                oncePer4CQICHFrames( 1 ),
                                oncePer8CQICHFrames( 2 ),
                                oncePer16CQICHFrames( 3 )
                            }
        MAX-ACCESS          read-write
        STATUS              current
        DESCRIPTION         "Cycle when MIMO Mode feedback is sent."
        ::= { necWimaxBsIfConfigurationsEntry 25 }

    necWimaxBsSsEntryNo OBJECT-TYPE
        SYNTAX              Integer32 (0..256)
        MAX-ACCESS          read-write
        STATUS              current
        DESCRIPTION         "Maximum number of MS Entry."
        ::= { necWimaxBsIfConfigurationsEntry 26 }

    necWimaxBsDlMapEncodeType OBJECT-TYPE
        SYNTAX              INTEGER {
                                ctc( 0 ),
                                cc( 1 )
                            }
        MAX-ACCESS          read-write
        STATUS              current
        DESCRIPTION         "It is shown whether to use CC or CTC for encoding
                            of DL-MAP. Default = 0"
        ::= { necWimaxBsIfConfigurationsEntry 27 }

    necWimaxBsFnRandseed OBJECT-TYPE
        SYNTAX              INTEGER {
                                enable( 0 ),
                                disable( 1 )
                            }
        MAX-ACCESS          read-write
        STATUS              current
        DESCRIPTION         "It is shown whether to use Frame number for UL
                            PRBS seed."
        ::= { necWimaxBsIfConfigurationsEntry 28 }

    necWimaxBsSduMaxDelay OBJECT-TYPE
        SYNTAX              Unsigned32
        MAX-ACCESS          read-write
        STATUS              current
        DESCRIPTION         "SDU MAX Delay"
        ::= { necWimaxBsIfConfigurationsEntry 29 }

    necWimaxBsMaxSf OBJECT-TYPE
        SYNTAX              Integer32 (2..1000)
        MAX-ACCESS          read-write
        STATUS              current
        DESCRIPTION         "Maximum number of Service Flow defval {600}"
        ::= { necWimaxBsIfConfigurationsEntry 30 }

    necWimaxBsFrameAdjustThreshold OBJECT-TYPE
        SYNTAX              Unsigned32 (0..999999)
        MAX-ACCESS          read-write
        STATUS              current
        DESCRIPTION         "This value is used for Frame Sync Adjustment(default=500000(0.5s))."
        ::= { necWimaxBsIfConfigurationsEntry 31 }

    necWimaxBsFrameSyncMode OBJECT-TYPE
        SYNTAX              INTEGER {
                                normal( 0 ),
                                noGps( 1 ),
                                noNtpd( 2 )
                            }
        MAX-ACCESS          read-write
        STATUS              current
        DESCRIPTION         "Flame Sync Mode. This value should be NORMAL(except
                            debugging)."
        ::= { necWimaxBsIfConfigurationsEntry 32 }

    necWimaxBsRxInitRangMax OBJECT-TYPE
        SYNTAX              Integer32 (0..16)
        MAX-ACCESS          read-write
        STATUS              current
        DESCRIPTION         "The maximum number of RX Initial Ranging CDMA
                            Code"
        ::= { necWimaxBsIfConfigurationsEntry 33 }

    necWimaxBsRxHoRangMax OBJECT-TYPE
        SYNTAX              Integer32 (0..16)
        MAX-ACCESS          read-write
        STATUS              current
        DESCRIPTION         "The maximum number of RX Handover Ranging CDMA
                            Code"
        ::= { necWimaxBsIfConfigurationsEntry 34 }

    necWimaxBsRfCableLength OBJECT-TYPE
        SYNTAX              Integer32 (0..255)
        MAX-ACCESS          read-write
        STATUS              current
        DESCRIPTION         "RF Cable Length"
        ::= { necWimaxBsIfConfigurationsEntry 35 }

    necWimaxBsOduAlarmControl OBJECT-TYPE
        SYNTAX              Unsigned32
        MAX-ACCESS          read-write
        STATUS              current
        DESCRIPTION         "ODU alarm control bits"
        ::= { necWimaxBsIfConfigurationsEntry 36 }

    necWimaxBsTimingGapOffset OBJECT-TYPE
        SYNTAX              Integer32 (-1200..16383)
        MAX-ACCESS          read-write
        STATUS              current
        DESCRIPTION         "Timing GAP offset"
        ::= { necWimaxBsIfConfigurationsEntry 37 }

    necWimaxBsSiiAdvInterval OBJECT-TYPE
        SYNTAX              Integer32 (1..30)
        UNITS               "sec"
        MAX-ACCESS          read-write
        STATUS              current
        DESCRIPTION         "Tx interval for SII-ADV. If 0, BS doesn't send
                            SII-ADV periodically."
        ::= { necWimaxBsIfConfigurationsEntry 38 }

    necWimaxBsGmsEnable OBJECT-TYPE
        SYNTAX              BITS {
                                pm( 0 ),
                                si( 1 ),
                                fliFl( 2 )
                            }
        MAX-ACCESS          read-write
        STATUS              current
        DESCRIPTION         "Register Grant Management Subheader's each function(1=enable
                            0=disable)."
        ::= { necWimaxBsIfConfigurationsEntry 39 }

    necWimaxBsMacVersion OBJECT-TYPE
        SYNTAX              NecWimaxBsMacVersion
        MAX-ACCESS          read-write
        STATUS              current
        DESCRIPTION         "BS Mac Version (for R/W)"
        ::= { necWimaxBsIfConfigurationsEntry 40 }

    necWimaxBsMulticastRepetitionCount OBJECT-TYPE
        SYNTAX              INTEGER {
                                zero( 0 ),
                                two( 2 ),
                                four( 4 ),
                                six( 6 )
                            }
        MAX-ACCESS          read-write
        STATUS              current
        DESCRIPTION         "Repetition for Multicast flame"
        ::= { necWimaxBsIfConfigurationsEntry 41 }

    necWimaxBsBcpIeTransmitCount OBJECT-TYPE
        SYNTAX              Integer32 (0..117)
        UNITS               "flame"
        MAX-ACCESS          read-write
        STATUS              current
        DESCRIPTION         "The number of Broadcast Control Pointer IE transmittion
                            before DCD/UCD transmittion."
        ::= { necWimaxBsIfConfigurationsEntry 42 }

    necWimaxBsSegmentUl OBJECT-TYPE
        SYNTAX              INTEGER {
                                segmentDisable( 0 ),
                                segmentEnable( 1 )
                            }
        MAX-ACCESS          read-write
        STATUS              current
        DESCRIPTION         "This object indicates whether UL Segment is used."
        ::= { necWimaxBsIfConfigurationsEntry 43 }

    necWimaxBsCqichBwReq OBJECT-TYPE
        SYNTAX              INTEGER {
                                disable( 0 ),
                                enable( 1 )
                            }
        MAX-ACCESS          read-write
        STATUS              current
        DESCRIPTION         "This object indicates whether BW-REQ by CQICH
                            codeword is used."
        ::= { necWimaxBsIfConfigurationsEntry 44 }

    necWimaxBsFairnessMode OBJECT-TYPE
        SYNTAX              INTEGER {
                                mode1( 0 ),
                                mode2( 1 )
                            }
        MAX-ACCESS          read-write
        STATUS              current
        DESCRIPTION         "This object indicates fairness mode."
        ::= { necWimaxBsIfConfigurationsEntry 45 }

    necWimaxBsFairnessCounterResetPeriod OBJECT-TYPE
        SYNTAX              Integer32 (1..65535)
        UNITS               "frames"
        MAX-ACCESS          read-write
        STATUS              current
        DESCRIPTION         "fairness counter reset period. default value =
                            2000 frames"
        ::= { necWimaxBsIfConfigurationsEntry 46 }

    necWimaxBsMimoUlHarq OBJECT-TYPE
        SYNTAX              INTEGER {
                                ul( 0 ),
                                mimoUl( 1 )
                            }
        MAX-ACCESS          read-write
        STATUS              current
        DESCRIPTION         "The subburst IE (UL-MIMO with HARQ)"
        ::= { necWimaxBsIfConfigurationsEntry 47 }

    necWimaxBsUlMimoEnable OBJECT-TYPE
        SYNTAX              INTEGER {
                                disable( 0 ),
                                enable( 1 )
                            }
        MAX-ACCESS          read-write
        STATUS              current
        DESCRIPTION         "UL-MIMO support"
        ::= { necWimaxBsIfConfigurationsEntry 48 }

    necWimaxBsNumOfSegment OBJECT-TYPE
        SYNTAX              INTEGER {
                                two( 0 ),
                                three( 1 )
                            }
        MAX-ACCESS          read-write
        STATUS              current
        DESCRIPTION         "This object indicates the number of segments."
        ::= { necWimaxBsIfConfigurationsEntry 49 }

    necWimaxBsFairnessCountMode OBJECT-TYPE
        SYNTAX              INTEGER {
                                byteCount( 0 ),
                                slotCount( 1 )
                            }
        MAX-ACCESS          read-write
        STATUS              current
        DESCRIPTION         "This object indicates fairness count mode."
        ::= { necWimaxBsIfConfigurationsEntry 50 }

    necWimaxBsAdmissionThresholdDl OBJECT-TYPE
        SYNTAX              Integer32 (0..100)
        MAX-ACCESS          read-write
        STATUS              current
        DESCRIPTION         "This value decides the threshold in which the
                            service flow generation is refused with Admission
                            Control(for DL). If set to 0, AdmissionControl
                            is not done."
        ::= { necWimaxBsIfConfigurationsEntry 51 }

    necWimaxBsAdmissionThresholdUl OBJECT-TYPE
        SYNTAX              Integer32 (0..100)
        MAX-ACCESS          read-write
        STATUS              current
        DESCRIPTION         "This value decides the threshold in which the
                            service flow generation is refused with Admission
                            Control(for UL). If set to 0, AdmissionControl
                            is not done."
        ::= { necWimaxBsIfConfigurationsEntry 52 }

    necWimaxBsCongestionThresholdDl OBJECT-TYPE
        SYNTAX              Integer32 (0..100)
        MAX-ACCESS          read-write
        STATUS              current
        DESCRIPTION         "This value decides the threshold in which the
                            service flow generation is refused with Congestion
                            Control(for DL). If set to 0, CongestionControl
                            is not done."
        ::= { necWimaxBsIfConfigurationsEntry 53 }

    necWimaxBsCongestionThresholdUl OBJECT-TYPE
        SYNTAX              Integer32 (0..100)
        MAX-ACCESS          read-write
        STATUS              current
        DESCRIPTION         "This value decides the threshold in which the
                            service flow generation is refused with Congestion
                            Control(for UL). If set to 0, CongestionControl
                            is not done."
        ::= { necWimaxBsIfConfigurationsEntry 54 }

    necWimaxBsProportionalShare OBJECT-TYPE
        SYNTAX              INTEGER {
                                disable( 0 ),
                                enable( 1 )
                            }
        MAX-ACCESS          read-write
        STATUS              current
        DESCRIPTION         "Proportional Sharing"
        ::= { necWimaxBsIfConfigurationsEntry 55 }

    necWimaxBsShareRateUlRtvr OBJECT-TYPE
        SYNTAX              Integer32 (0..100)
        MAX-ACCESS          read-write
        STATUS              current
        DESCRIPTION         "This value indicates the share ratio of the rest
                            area for UL RT-VR."
        ::= { necWimaxBsIfConfigurationsEntry 56 }

    necWimaxBsShareRateUlNrtvr OBJECT-TYPE
        SYNTAX              Integer32 (0..100)
        MAX-ACCESS          read-write
        STATUS              current
        DESCRIPTION         "This value indicates the share ratio of the rest
                            area for UL NRT-VR."
        ::= { necWimaxBsIfConfigurationsEntry 57 }

    necWimaxBsShareRateUlBe OBJECT-TYPE
        SYNTAX              Integer32 (0..100)
        MAX-ACCESS          read-write
        STATUS              current
        DESCRIPTION         "This value indicates the share ratio of the rest
                            area for UL BE."
        ::= { necWimaxBsIfConfigurationsEntry 58 }

    necWimaxBsShareRateDlRtvr OBJECT-TYPE
        SYNTAX              Integer32 (0..100)
        MAX-ACCESS          read-write
        STATUS              current
        DESCRIPTION         "This value indicates the share ratio of the rest
                            area for DL RT-VR."
        ::= { necWimaxBsIfConfigurationsEntry 59 }

    necWimaxBsShareRateDlNrtvr OBJECT-TYPE
        SYNTAX              Integer32 (0..100)
        MAX-ACCESS          read-write
        STATUS              current
        DESCRIPTION         "This value indicates the share ratio of the rest
                            area for DL NRT-VR."
        ::= { necWimaxBsIfConfigurationsEntry 60 }

    necWimaxBsShareRateDlBe OBJECT-TYPE
        SYNTAX              Integer32 (0..100)
        MAX-ACCESS          read-write
        STATUS              current
        DESCRIPTION         "This value indicates the share ratio of the rest
                            area for DL BE."
        ::= { necWimaxBsIfConfigurationsEntry 61 }

    necWimaxBsThroughputCapacityDl OBJECT-TYPE
        SYNTAX              Integer32 (0..100)
        MAX-ACCESS          read-write
        STATUS              current
        DESCRIPTION         "This value indicates the DL throughput capacity."
        ::= { necWimaxBsIfConfigurationsEntry 62 }

    necWimaxBsThroughputCapacityUl OBJECT-TYPE
        SYNTAX              Integer32 (0..100)
        MAX-ACCESS          read-write
        STATUS              current
        DESCRIPTION         "This value indicates the UL throughput capacity."
        ::= { necWimaxBsIfConfigurationsEntry 63 }

    necWimaxBsArqTable OBJECT-TYPE
        SYNTAX              SEQUENCE OF NecWimaxBsArqEntry
        MAX-ACCESS          not-accessible
        STATUS              current
        DESCRIPTION         "Base Station Arq Mode."
        ::= { necWimaxBsCps 3 }

    necWimaxBsArqEntry OBJECT-TYPE
        SYNTAX              NecWimaxBsArqEntry
        MAX-ACCESS          not-accessible
        STATUS              current
        DESCRIPTION         "H"
        INDEX               {
                                ifIndex
                            }
        ::= { necWimaxBsArqTable 1 }

    NecWimaxBsArqEntry ::= SEQUENCE {
        necWimaxBsArqWindowSize
            Integer32,
        necWimaxBsArqRetryTimerTx
            Integer32,
        necWimaxBsArqRetryTimerRx
            Integer32,
        necWimaxBsArqBlcokLifetime
            Integer32,
        necWimaxBsArqSyncLossTimeout
            Integer32,
        necWimaxBsArqDeliverInOrder
            Integer32,
        necWimaxBsArqPurgeTimeout
            Integer32,
        necWimaxBsArqBlockSize
            Integer32,
        necWimaxBsArqAckProcTime
            Integer32,
        necWimaxBsArqAckDelay
            Integer32,
        necWimaxBsArqT22
            Integer32,
        necWimaxBsArqT22retry
            Integer32
    }

    necWimaxBsArqWindowSize OBJECT-TYPE
        SYNTAX              Integer32 (1..1024)
        MAX-ACCESS          read-write
        STATUS              current
        DESCRIPTION         "Indicates the maximum number of unacknowledged
                            fragments at any time."
        ::= { necWimaxBsArqEntry 1 }

    necWimaxBsArqRetryTimerTx OBJECT-TYPE
        SYNTAX              Integer32 (0..65535)
        MAX-ACCESS          read-write
        STATUS              current
        DESCRIPTION         "The object defines the ARQ transmitter delay for
                            downlink and uplink transmission."
        ::= { necWimaxBsArqEntry 2 }

    necWimaxBsArqRetryTimerRx OBJECT-TYPE
        SYNTAX              Integer32 (0..65535)
        UNITS               "100us"
        MAX-ACCESS          read-write
        STATUS              current
        DESCRIPTION         "The object defines the ARQ receiver delay for
                            downlink and uplink transmission."
        ::= { necWimaxBsArqEntry 3 }

    necWimaxBsArqBlcokLifetime OBJECT-TYPE
        SYNTAX              Integer32 (0..65535)
        UNITS               "100us"
        MAX-ACCESS          read-write
        STATUS              current
        DESCRIPTION         "The maximum time interval an ARQ fragment will
                            be managed by the transmitter ARQ machine, once
                            initial transmission of the fragment has occured.
                            If transmission or retransmission of the fragment
                            is not acknowledged by the receiver before the
                            time limit is reached, the fragment is discarded.
                            A value of 0 means Infinite."
        ::= { necWimaxBsArqEntry 4 }

    necWimaxBsArqSyncLossTimeout OBJECT-TYPE
        SYNTAX              Integer32 (0..65535)
        UNITS               "100us"
        MAX-ACCESS          read-write
        STATUS              current
        DESCRIPTION         "The maximum interval before declaring a loss of
                            synchronization of the sender and receiver state
                            machines. A value of 0 means Infinite."
        ::= { necWimaxBsArqEntry 5 }

    necWimaxBsArqDeliverInOrder OBJECT-TYPE
        SYNTAX              Integer32 (0..1)
        MAX-ACCESS          read-write
        STATUS              current
        DESCRIPTION         "Indicates whether or not data is to be delivered
                            by the receiving MAC to its client application
                            in the order in which data was handed off to
                            the originating MAC."
        ::= { necWimaxBsArqEntry 6 }

    necWimaxBsArqPurgeTimeout OBJECT-TYPE
        SYNTAX              Integer32 (0..65535)
        UNITS               "100us"
        MAX-ACCESS          read-write
        STATUS              current
        DESCRIPTION         "Indicates the time interval the ARQ window is
                            advanced after a fragment is received. A value
                            of 0 means Infinite."
        ::= { necWimaxBsArqEntry 7 }

    necWimaxBsArqBlockSize OBJECT-TYPE
        SYNTAX              Integer32 (0..1024)
        MAX-ACCESS          read-write
        STATUS              current
        DESCRIPTION         "The value of this parameter specifies the size
                            of an ARQ block. This parameter shall be established
                            by negotiation during the connection creation
                            dialog."
        ::= { necWimaxBsArqEntry 8 }

    necWimaxBsArqAckProcTime OBJECT-TYPE
        SYNTAX              Integer32 (0..255)
        MAX-ACCESS          read-write
        STATUS              current
        DESCRIPTION         "When the number of ACK untransmission blocks reaches
                            this value, ACK is transmitted. If set to 0,
                            the number of blocks is not checked."
        ::= { necWimaxBsArqEntry 9 }

    necWimaxBsArqAckDelay OBJECT-TYPE
        SYNTAX              Integer32 (0..65535)
        UNITS               "100us"
        MAX-ACCESS          read-write
        STATUS              current
        DESCRIPTION         "This object indicates time until ACK to the received
                            block is transmitted. The unit is 100 micro second."
        ::= { necWimaxBsArqEntry 10 }

    necWimaxBsArqT22 OBJECT-TYPE
        SYNTAX              Integer32 (10..65535)
        UNITS               "ms"
        MAX-ACCESS          read-write
        STATUS              current
        DESCRIPTION         "This object indicates T22 time."
        ::= { necWimaxBsArqEntry 11 }

    necWimaxBsArqT22retry OBJECT-TYPE
        SYNTAX              Integer32 (0..65535)
        MAX-ACCESS          read-write
        STATUS              current
        DESCRIPTION         "This object indicates T22 retry count."
        ::= { necWimaxBsArqEntry 12 }

    necWimaxBsMeasurementControlTable OBJECT-TYPE
        SYNTAX              SEQUENCE OF NecWimaxBsMeasurementControlEntry
        MAX-ACCESS          not-accessible
        STATUS              current
        DESCRIPTION         "This table indicates the list of the MAC address
                            of MS that measures power."
        ::= { necWimaxBsCps 4 }

    necWimaxBsMeasurementControlEntry OBJECT-TYPE
        SYNTAX              NecWimaxBsMeasurementControlEntry
        MAX-ACCESS          not-accessible
        STATUS              current
        DESCRIPTION         "This table is indexed by necWimaxBsMeasurementControlIndex."
        INDEX               {
                                necWimaxBsMeasurementControlIndex
                            }
        ::= { necWimaxBsMeasurementControlTable 1 }

    NecWimaxBsMeasurementControlEntry ::= SEQUENCE {
        necWimaxBsMeasurementControlIndex
            Integer32,
        necWimaxBsMeasurementControlMacAddress
            MacAddress,
        necWimaxBsMeasurementControlRowStatus
            RowStatus
    }

    necWimaxBsMeasurementControlIndex OBJECT-TYPE
        SYNTAX              Integer32 (1..650000000)
        MAX-ACCESS          not-accessible
        STATUS              current
        DESCRIPTION         "It is an index used when power is measured."
        ::= { necWimaxBsMeasurementControlEntry 1 }

    necWimaxBsMeasurementControlMacAddress OBJECT-TYPE
        SYNTAX              MacAddress
        MAX-ACCESS          read-create
        STATUS              current
        DESCRIPTION         "It is a list of the MAC address of SS that measures
                            power."
        ::= { necWimaxBsMeasurementControlEntry 2 }

    necWimaxBsMeasurementControlRowStatus OBJECT-TYPE
        SYNTAX              RowStatus
        MAX-ACCESS          read-create
        STATUS              current
        DESCRIPTION         "This object is used to ensure that the write operation
                            to multiple columns is guaranteed to be treated
                            as atomic operation by agent."
        ::= { necWimaxBsMeasurementControlEntry 3 }

    necWimaxBsTimerTable OBJECT-TYPE
        SYNTAX              SEQUENCE OF NecWimaxBsTimerEntry
        MAX-ACCESS          not-accessible
        STATUS              current
        DESCRIPTION         "Timer Table"
        ::= { necWimaxBsCps 5 }

    necWimaxBsTimerEntry OBJECT-TYPE
        SYNTAX              NecWimaxBsTimerEntry
        MAX-ACCESS          not-accessible
        STATUS              current
        DESCRIPTION         "indexd by ifIndex"
        INDEX               {
                                ifIndex
                            }
        ::= { necWimaxBsTimerTable 1 }

    NecWimaxBsTimerEntry ::= SEQUENCE {
        necWimaxBsTimerT9
            Unsigned32,
        necWimaxBsTimerT17
            Unsigned32,
        necWimaxBsTimerT7
            Unsigned32,
        necWimaxBsTimerT7retry
            Integer32,
        necWimaxBsTimerT8
            Unsigned32,
        necWimaxBsTimerT8retry
            Integer32,
        necWimaxBsTimerT10
            Unsigned32,
        necWimaxBsTimerEntryAgingTime
            Unsigned32,
        necWimaxBsTimerR6T3
            Unsigned32
    }

    necWimaxBsTimerT9 OBJECT-TYPE
        SYNTAX              Unsigned32 (10..4294967295)
        UNITS               "ms"
        MAX-ACCESS          read-write
        STATUS              current
        DESCRIPTION         "T9(SBC-REQ wait timer) defalut=1000ms"
        ::= { necWimaxBsTimerEntry 1 }

    necWimaxBsTimerT17 OBJECT-TYPE
        SYNTAX              Unsigned32 (10..4294967295)
        UNITS               "ms"
        MAX-ACCESS          read-write
        STATUS              current
        DESCRIPTION         "T17(REG-REQ wait timer) defalut=300000ms(5 min)"
        ::= { necWimaxBsTimerEntry 2 }

    necWimaxBsTimerT7 OBJECT-TYPE
        SYNTAX              Unsigned32 (10..4294967295)
        UNITS               "ms"
        MAX-ACCESS          read-write
        STATUS              current
        DESCRIPTION         "T7(DSx-RSP wait timer) defalut=1000ms"
        ::= { necWimaxBsTimerEntry 3 }

    necWimaxBsTimerT7retry OBJECT-TYPE
        SYNTAX              Integer32 (0..65535)
        MAX-ACCESS          read-write
        STATUS              current
        DESCRIPTION         "T7 max retry count defalut=3"
        ::= { necWimaxBsTimerEntry 4 }

    necWimaxBsTimerT8 OBJECT-TYPE
        SYNTAX              Unsigned32 (10..4294967295)
        UNITS               "ms"
        MAX-ACCESS          read-write
        STATUS              current
        DESCRIPTION         "T8(DSx-ACK wait timer) defalut=1000ms"
        ::= { necWimaxBsTimerEntry 5 }

    necWimaxBsTimerT8retry OBJECT-TYPE
        SYNTAX              Integer32 (0..65535)
        MAX-ACCESS          read-write
        STATUS              current
        DESCRIPTION         "T8 max retry count defalut=3"
        ::= { necWimaxBsTimerEntry 6 }

    necWimaxBsTimerT10 OBJECT-TYPE
        SYNTAX              Unsigned32 (10..4294967295)
        UNITS               "ms"
        MAX-ACCESS          read-write
        STATUS              current
        DESCRIPTION         "T10(Transaction complete wait timer) defalut=3000ms"
        ::= { necWimaxBsTimerEntry 7 }

    necWimaxBsTimerEntryAgingTime OBJECT-TYPE
        SYNTAX              Unsigned32
        UNITS               "ms"
        MAX-ACCESS          read-write
        STATUS              current
        DESCRIPTION         "entry aging timer defalut=9000ms"
        ::= { necWimaxBsTimerEntry 8 }

    necWimaxBsTimerR6T3 OBJECT-TYPE
        SYNTAX              Unsigned32
        UNITS               "ms"
        MAX-ACCESS          read-write
        STATUS              current
        DESCRIPTION         "Monitoring timer after transmitting MS_PreAttachment_Ack
                            before receiving AR_EAP_Transfer defalut=10000ms"
        ::= { necWimaxBsTimerEntry 9 }

    necWimaxBsPhy OBJECT IDENTIFIER ::= { necWimaxBsIfObjects 2 }

    necWimaxBsOfdmaPhy OBJECT IDENTIFIER ::= { necWimaxBsPhy 1 }

    necWimaxBsUlmapTable OBJECT-TYPE
        SYNTAX              SEQUENCE OF NecWimaxBsUlmapEntry
        MAX-ACCESS          not-accessible
        STATUS              current
        DESCRIPTION         "This table contains Ulmap?"
        ::= { necWimaxBsOfdmaPhy 1 }

    necWimaxBsUlmapEntry OBJECT-TYPE
        SYNTAX              NecWimaxBsUlmapEntry
        MAX-ACCESS          not-accessible
        STATUS              current
        DESCRIPTION         "H"
        INDEX               {
                                ifIndex
                            }
        ::= { necWimaxBsUlmapTable 1 }

    NecWimaxBsUlmapEntry ::= SEQUENCE {
        necWimaxBsUlmapFeedbackSymStart
            Integer32,
        necWimaxBsUlmapFeedbackSubchanStart
            Integer32,
        necWimaxBsUlmapFeedbackSymNumber
            Integer32,
        necWimaxBsUlmapFeedbackSubchanNumber
            Integer32,
        necWimaxBsUlmapBwreqSymStart
            Integer32,
        necWimaxBsUlmapBwreqSubchanStart
            Integer32,
        necWimaxBsUlmapBwreqSymNumber
            Integer32,
        necWimaxBsUlmapBwreqSubchanNumber
            Integer32,
        necWimaxBsUlmapRangingSymStart
            Integer32,
        necWimaxBsUlmapRangingSubchanStart
            Integer32,
        necWimaxBsUlmapRangingSymNumber
            Integer32,
        necWimaxBsUlmapRangingSubchanNumber
            Integer32,
        necWimaxBsUlmapHarqSymStart
            Integer32,
        necWimaxBsUlmapHarqSubchanStart
            Integer32,
        necWimaxBsUlmapHarqSymNumber
            Integer32,
        necWimaxBsUlmapHarqSubchanNumber
            Integer32,
        necWimaxBsUlmapPerRngBackoffStart
            Integer32,
        necWimaxBsUlmapPerRngBackoffEnd
            Integer32,
        necWimaxBsUlmapInitRngCodes
            Integer32,
        necWimaxBsUlmapPeriodicRngCodes
            Integer32,
        necWimaxBsUlmapBWReqCodes
            Integer32
    }

    necWimaxBsUlmapFeedbackSymStart OBJECT-TYPE
        SYNTAX              Integer32 (0..47)
        MAX-ACCESS          read-write
        STATUS              current
        DESCRIPTION         "Arrangement of FAST-FEEDBACK area in UL. The position
                            of starting symbol."
        ::= { necWimaxBsUlmapEntry 1 }

    necWimaxBsUlmapFeedbackSubchanStart OBJECT-TYPE
        SYNTAX              Integer32 (0..35)
        MAX-ACCESS          read-write
        STATUS              current
        DESCRIPTION         "Arrangement of FAST-FEEDBACK area in UL. The position
                            of starting sub-channel."
        ::= { necWimaxBsUlmapEntry 2 }

    necWimaxBsUlmapFeedbackSymNumber OBJECT-TYPE
        SYNTAX              Integer32 (0..47)
        MAX-ACCESS          read-write
        STATUS              current
        DESCRIPTION         "Arrangement of FAST-FEEDBACK area in UL. Number
                            of symbols."
        ::= { necWimaxBsUlmapEntry 3 }

    necWimaxBsUlmapFeedbackSubchanNumber OBJECT-TYPE
        SYNTAX              Integer32 (0..35)
        MAX-ACCESS          read-write
        STATUS              current
        DESCRIPTION         "Arrangement of FAST-FEEDBACK area in UL. Number
                            of sub-channels."
        ::= { necWimaxBsUlmapEntry 4 }

    necWimaxBsUlmapBwreqSymStart OBJECT-TYPE
        SYNTAX              Integer32 (0..47)
        MAX-ACCESS          read-write
        STATUS              current
        DESCRIPTION         "Specification of area for BW-REQ/Periodic Ranging.
                            The position of starting symbol."
        ::= { necWimaxBsUlmapEntry 5 }

    necWimaxBsUlmapBwreqSubchanStart OBJECT-TYPE
        SYNTAX              Integer32 (0..35)
        MAX-ACCESS          read-write
        STATUS              current
        DESCRIPTION         "Specification of area for BW-REQ/Periodic Ranging.
                            The position of starting sub-channel."
        ::= { necWimaxBsUlmapEntry 6 }

    necWimaxBsUlmapBwreqSymNumber OBJECT-TYPE
        SYNTAX              Integer32 (0..47)
        MAX-ACCESS          read-write
        STATUS              current
        DESCRIPTION         "Specification of area for BW-REQ/Periodic Ranging.
                            Number of symbols."
        ::= { necWimaxBsUlmapEntry 7 }

    necWimaxBsUlmapBwreqSubchanNumber OBJECT-TYPE
        SYNTAX              Integer32 (0..35)
        MAX-ACCESS          read-write
        STATUS              current
        DESCRIPTION         "Specification of area for BW-REQ/Periodic Ranging.
                            Number of sub-channels."
        ::= { necWimaxBsUlmapEntry 8 }

    necWimaxBsUlmapRangingSymStart OBJECT-TYPE
        SYNTAX              Integer32 (0..47)
        MAX-ACCESS          read-write
        STATUS              current
        DESCRIPTION         "Specification of area for Initial Ranging/Handover
                            Ranging. The position of starting symbol."
        ::= { necWimaxBsUlmapEntry 9 }

    necWimaxBsUlmapRangingSubchanStart OBJECT-TYPE
        SYNTAX              Integer32 (0..35)
        MAX-ACCESS          read-write
        STATUS              current
        DESCRIPTION         "Specification of area for Initial Ranging/Handover
                            Ranging. The position of starting sub-channel."
        ::= { necWimaxBsUlmapEntry 10 }

    necWimaxBsUlmapRangingSymNumber OBJECT-TYPE
        SYNTAX              Integer32 (0..47)
        MAX-ACCESS          read-write
        STATUS              current
        DESCRIPTION         "Specification of area for Initial Ranging/Handover
                            Ranging. ?@?@ Number of symbols."
        ::= { necWimaxBsUlmapEntry 11 }

    necWimaxBsUlmapRangingSubchanNumber OBJECT-TYPE
        SYNTAX              Integer32 (0..35)
        MAX-ACCESS          read-write
        STATUS              current
        DESCRIPTION         "Specification of area for Initial Ranging/Handover
                            Ranging. Number of sub-channels."
        ::= { necWimaxBsUlmapEntry 12 }

    necWimaxBsUlmapHarqSymStart OBJECT-TYPE
        SYNTAX              Integer32 (0..47)
        MAX-ACCESS          read-write
        STATUS              current
        DESCRIPTION         "Arrangement of ACK/NACK area for HARQ. The position
                            of starting symbol."
        ::= { necWimaxBsUlmapEntry 13 }

    necWimaxBsUlmapHarqSubchanStart OBJECT-TYPE
        SYNTAX              Integer32 (0..35)
        MAX-ACCESS          read-write
        STATUS              current
        DESCRIPTION         "Arrangement of ACK/NACK area for HARQ. The position
                            of starting sub-channel."
        ::= { necWimaxBsUlmapEntry 14 }

    necWimaxBsUlmapHarqSymNumber OBJECT-TYPE
        SYNTAX              Integer32 (0..47)
        MAX-ACCESS          read-write
        STATUS              current
        DESCRIPTION         "Arrangement of ACK/NACK area for HARQ. Number
                            of symbols."
        ::= { necWimaxBsUlmapEntry 15 }

    necWimaxBsUlmapHarqSubchanNumber OBJECT-TYPE
        SYNTAX              Integer32 (0..35)
        MAX-ACCESS          read-write
        STATUS              current
        DESCRIPTION         "Arrangement of ACK/NACK area for HARQ. Number
                            of sub-channels."
        ::= { necWimaxBsUlmapEntry 16 }

    necWimaxBsUlmapPerRngBackoffStart OBJECT-TYPE
        SYNTAX              Integer32 (0..15)
        MAX-ACCESS          read-write
        STATUS              current
        DESCRIPTION         "Initial backoff window size for periodic ranging
                            contention, expressed as a power of 2. Range:
                            0..15 (the highest order bits shall be unused
                            and set to 0).DEFVAL { 0 }"
        ::= { necWimaxBsUlmapEntry 17 }

    necWimaxBsUlmapPerRngBackoffEnd OBJECT-TYPE
        SYNTAX              Integer32 (0..15)
        MAX-ACCESS          read-write
        STATUS              current
        DESCRIPTION         "Final backoff window size for periodic ranging
                            contention, expressed as a power of 2. Range:
                            0..15 (the highest order bits shall be unused
                            and set to 0).DEFVAL { 15 }"
        ::= { necWimaxBsUlmapEntry 18 }

    necWimaxBsUlmapInitRngCodes OBJECT-TYPE
        SYNTAX              Integer32 (0..255)
        MAX-ACCESS          read-write
        STATUS              current
        DESCRIPTION         "Number of initial ranging CDMA codes. Possible
                            values are 0..255. The total number of wmanIfBsOfdmaInitRngCodes,
                            wmanIfBsOfdmaPeriodicRngCodes and wmanIfBsOfdmaBWReqCodes
                            shall be equal or less than 256.DEFVAL { 30 }"
        ::= { necWimaxBsUlmapEntry 19 }

    necWimaxBsUlmapPeriodicRngCodes OBJECT-TYPE
        SYNTAX              Integer32 (0..255)
        MAX-ACCESS          read-write
        STATUS              current
        DESCRIPTION         "Number of periodic ranging CDMA codes. Possible
                            values are 0..255. The total number of wmanIfBsOfdmaInitRngCodes,
                            wmanIfBsOfdmaPeriodicRngCodes and wmanIfBsOfdmaBWReqCodes
                            shall be equal or less than 256.DEFVAL { 30 }"
        ::= { necWimaxBsUlmapEntry 20 }

    necWimaxBsUlmapBWReqCodes OBJECT-TYPE
        SYNTAX              Integer32 (0..255)
        MAX-ACCESS          read-write
        STATUS              current
        DESCRIPTION         "Number of bandwidth request codes. Possible values
                            are 0..255. The total number of wmanIfBsOfdmaInitRngCodes,
                            wmanIfBsOfdmaPeriodicRngCodes and wmanIfBsOfdmaBWReqCodes
                            shall be equal or less than 256.DEFVAL { 30 }"
        ::= { necWimaxBsUlmapEntry 21 }

    necWimaxBsPowerControlTable OBJECT-TYPE
        SYNTAX              SEQUENCE OF NecWimaxBsPowerControlEntry
        MAX-ACCESS          not-accessible
        STATUS              current
        DESCRIPTION         "Basic station Power Control Mode"
        ::= { necWimaxBsOfdmaPhy 2 }

    necWimaxBsPowerControlEntry OBJECT-TYPE
        SYNTAX              NecWimaxBsPowerControlEntry
        MAX-ACCESS          not-accessible
        STATUS              current
        DESCRIPTION         "power control"
        INDEX               {
                                ifIndex
                            }
        ::= { necWimaxBsPowerControlTable 1 }

    NecWimaxBsPowerControlEntry ::= SEQUENCE {
        necWimaxBsPwrctrlDlCh
            OCTET STRING,
        necWimaxBsPwrctrlEirpOffset
            Integer32,
        necWimaxBsPwrctrlNIinterval
            Integer32,
        necWimaxBsPwrctrlMode
            INTEGER,
        necWimaxBsPwrctrlCqichRptInterval
            Integer32,
        necWimaxBsPwrctrlCqichUpdateInterval
            INTEGER,
        necWimaxBsPwrctrlReportFunc
            INTEGER,
        necWimaxBsPwrctrlCqichRptContents
            INTEGER,
        necWimaxBsPwrctrlRepRptInterval
            Integer32,
        necWimaxBsPwrctrlRateCtrlInterval
            Integer32,
        necWimaxBsPwrctrlClosedLoopWaitTimer
            Integer32,
        necWimaxBsPwrctrlThreshold
            Unsigned32,
        necWimaxBsPwrctrlLaUlEnable
            INTEGER,
        necWimaxBsPwrctrlCinrReuseFactor
            INTEGER,
        necWimaxBsPwrctrlDlPhyQuality
            INTEGER,
        necWimaxBsPwrctrlTxPower
            Integer32,
        necWimaxBsPwrctrAntennaGain
            Integer32,
        necWimaxBsPwrctrlTxPowerOffset
            Integer32,
        necWimaxBsPwrctrlOpenLoopModeChange
            INTEGER,
        necWimaxBsPwrctrlClosedLoopAdjust
            Integer32,
        necWimaxBsPwrctrlCinrPriority
            Integer32,
        necWimaxBsPwrctrlRssiRptInterval
            Integer32,
        necWimaxBsPwrctrlPathLossAdjust
            Integer32,
        necWimaxBsPwrctrlRssiAveraging
            Integer32,
        necWimaxBsPwrctrlDlChMatrixA
            OCTET STRING,
        necWimaxBsPwrctrlDlChMatrixB
            OCTET STRING,
        necWimaxBsPwrctrlMatrixCtrlInterval
            Integer32,
        necWimaxBsPwrctrlDlRateUp
            Integer32,
        necWimaxBsPwrctrlDlRateDown
            Integer32,
        necWimaxBsSubchannelisation
            INTEGER,
        necWimaxBsSubchLimit
            OCTET STRING,
        necWimaxBsSubchThreshold
            OCTET STRING,
        necWimaxBsPwrctrlLaDlEnable
            INTEGER,
        necWimaxBsPwrctrlRxGain
            Integer32,
        necWimaxBsPwrctrlRateCtrlOffset
            Integer32,
        necWimaxBsPwrctrlDlOuterLoopKeepTime
            Integer32,
        necWimaxBsPwrctrlDlOuterLoop
            INTEGER,
        necWimaxBsPwrctrlUlOuterLoop
            INTEGER,
        necWimaxBsPwrctrlDlRateCtrlInterval
            Integer32,
        necWimaxBsPwrctrlUlRateCtrlInterval
            Integer32,
        necWimaxBsPwrctrlUlRateUp
            Integer32,
        necWimaxBsPwrctrlUlRateDown
            Integer32,
        necWimaxBsPwrctrlUlMimoMinRate
            Integer32,
        necWimaxBsPwrctrlUlOuterLoopKeepTime
            Integer32,
        necWimaxBsPwrctrlDlRateBack
            Integer32,
        necWimaxBsPwrctrlUlRateBack
            Integer32
    }

    necWimaxBsPwrctrlDlCh OBJECT-TYPE
        SYNTAX              OCTET STRING (SIZE(10))
        MAX-ACCESS          read-write
        STATUS              current
        DESCRIPTION         "This object indicates necessary CN value (-128-127dB)
                            for downlink. It is assumed array forms the following
                            in each MCS. [0]QPSK 1/2 x4 (Default = -2) [1]QPSK
                            1/2 x2 (Default = 1) [2]QPSK 1/2 (Default = 4)
                            [3]QPSK 3/4 (Default = 8) [4]16QAM 1/2 (Default
                            = 10) [5]16QAM 3/4 (Default = 14) [6]64QAM 1/2
                            (Default = 20) [7]64QAM 2/3 (Default = 24) [8]64QAM
                            3/4 (Default = 28) [9]64QAM 5/6 (Default = 32)"
        ::= { necWimaxBsPowerControlEntry 1 }

    necWimaxBsPwrctrlEirpOffset OBJECT-TYPE
        SYNTAX              Integer32 (-128..127)
        MAX-ACCESS          read-write
        STATUS              current
        DESCRIPTION         "This object indicates the offset value of the
                            Open electric power control. The unit is 0.25dB
                            (-32-31.75dB)."
        ::= { necWimaxBsPowerControlEntry 2 }

    necWimaxBsPwrctrlNIinterval OBJECT-TYPE
        SYNTAX              Integer32 (0..255)
        MAX-ACCESS          read-write
        STATUS              current
        DESCRIPTION         "This object indicates the interval (unit of the
                            frame) that puts UL N+I extended IE on DL-MAP
                            and transmits."
        ::= { necWimaxBsPowerControlEntry 3 }

    necWimaxBsPwrctrlMode OBJECT-TYPE
        SYNTAX              INTEGER {
                                noPowerControl( 0 ),
                                openLoop( 1 ),
                                closedLoop( 2 ),
                                openAndClose( 3 )
                            }
        MAX-ACCESS          read-write
        STATUS              current
        DESCRIPTION         "0:no PowerControl 1:open loop power control 2:closed
                            loop power control 3: open and closed loop power
                            control"
        ::= { necWimaxBsPowerControlEntry 4 }

    necWimaxBsPwrctrlCqichRptInterval OBJECT-TYPE
        SYNTAX              Integer32 (0..3)
        MAX-ACCESS          read-write
        STATUS              current
        DESCRIPTION         "This object indicates the report interbal for
                            CQICH and Feedback header. It reports every 2p
                            frame. Where, this object is assumed to be p."
        ::= { necWimaxBsPowerControlEntry 6 }

    necWimaxBsPwrctrlCqichUpdateInterval OBJECT-TYPE
        SYNTAX              INTEGER {
                                v40( 40 ),
                                v80( 80 ),
                                v160( 160 ),
                                v320( 320 ),
                                v640( 640 )
                            }
        MAX-ACCESS          read-write
        STATUS              current
        DESCRIPTION         "This object indicates the cycle when CQICH Allocation
                            IE is transmitted. (specification of number of
                            frames)"
        ::= { necWimaxBsPowerControlEntry 7 }

    necWimaxBsPwrctrlReportFunc OBJECT-TYPE
        SYNTAX              INTEGER {
                                repReqRsp( 0 ),
                                cqich( 1 ),
                                none( 2 )
                            }
        MAX-ACCESS          read-write
        STATUS              current
        DESCRIPTION         "This object decides which function to use as a
                            measurement function."
        ::= { necWimaxBsPowerControlEntry 8 }

    necWimaxBsPwrctrlCqichRptContents OBJECT-TYPE
        SYNTAX              INTEGER {
                                mean( 0 ),
                                meanStdDeviation( 1 )
                            }
        MAX-ACCESS          read-write
        STATUS              current
        DESCRIPTION         "This object specifies the type of CINR report
                            directed MS."
        ::= { necWimaxBsPowerControlEntry 9 }

    necWimaxBsPwrctrlRepRptInterval OBJECT-TYPE
        SYNTAX              Integer32 (0..255)
        MAX-ACCESS          read-write
        STATUS              current
        DESCRIPTION         "This object indicates the Report demand interval
                            for REP-REQ/RSP."
        ::= { necWimaxBsPowerControlEntry 10 }

    necWimaxBsPwrctrlRateCtrlInterval OBJECT-TYPE
        SYNTAX              Integer32 (1..1024)
        MAX-ACCESS          read-write
        STATUS              current
        DESCRIPTION         "This object indicates the Rate control execution
                            interval. It applies to both Downlink/Uplink.
                            Unit: Frame"
        ::= { necWimaxBsPowerControlEntry 11 }

    necWimaxBsPwrctrlClosedLoopWaitTimer OBJECT-TYPE
        SYNTAX              Integer32 (0..255)
        MAX-ACCESS          read-write
        STATUS              current
        DESCRIPTION         "This object indicates the Closed loop power control
                            control waiting time. Unit: Frame"
        ::= { necWimaxBsPowerControlEntry 12 }

    necWimaxBsPwrctrlThreshold OBJECT-TYPE
        SYNTAX              Unsigned32 (0..100)
        MAX-ACCESS          read-write
        STATUS              current
        DESCRIPTION         "Threshold"
        ::= { necWimaxBsPowerControlEntry 13 }

    necWimaxBsPwrctrlLaUlEnable OBJECT-TYPE
        SYNTAX              INTEGER {
                                disable( 0 ),
                                enable( 1 )
                            }
        MAX-ACCESS          read-write
        STATUS              current
        DESCRIPTION         "Threshold"
        ::= { necWimaxBsPowerControlEntry 14 }

    necWimaxBsPwrctrlCinrReuseFactor OBJECT-TYPE
        SYNTAX              INTEGER {
                                reuseFactor1( 0 ),
                                reuseFactor3( 1 )
                            }
        MAX-ACCESS          read-write
        STATUS              current
        DESCRIPTION         "Reuse configuration of CINR Mesurment that uses
                            preamble."
        ::= { necWimaxBsPowerControlEntry 15 }

    necWimaxBsPwrctrlDlPhyQuality OBJECT-TYPE
        SYNTAX              INTEGER {
                                ineffective( 0 ),
                                effective( 1 )
                            }
        MAX-ACCESS          read-write
        STATUS              current
        DESCRIPTION         "CINR of each MS is obtained by REP-REQ/RSP."
        ::= { necWimaxBsPowerControlEntry 16 }

    necWimaxBsPwrctrlTxPower OBJECT-TYPE
        SYNTAX              Integer32 (-128..127)
        MAX-ACCESS          read-write
        STATUS              current
        DESCRIPTION         "The device transmission output of BS. Default
                            = 33."
        ::= { necWimaxBsPowerControlEntry 17 }

    necWimaxBsPwrctrAntennaGain OBJECT-TYPE
        SYNTAX              Integer32 (0..255)
        MAX-ACCESS          read-write
        STATUS              current
        DESCRIPTION         "Antenna gain of BS."
        ::= { necWimaxBsPowerControlEntry 18 }

    necWimaxBsPwrctrlTxPowerOffset OBJECT-TYPE
        SYNTAX              Integer32 (-31..31)
        MAX-ACCESS          read-write
        STATUS              current
        DESCRIPTION         "This value is set to i32BsEIRP"
        ::= { necWimaxBsPowerControlEntry 19 }

    necWimaxBsPwrctrlOpenLoopModeChange OBJECT-TYPE
        SYNTAX              INTEGER {
                                retention( 1 ),
                                reset( 2 )
                            }
        MAX-ACCESS          read-write
        STATUS              current
        DESCRIPTION         "This value is set to [Power control mode change]
                            of PMC-RSP"
        ::= { necWimaxBsPowerControlEntry 20 }

    necWimaxBsPwrctrlClosedLoopAdjust OBJECT-TYPE
        SYNTAX              Integer32 (-128..127)
        UNITS               "0.25dB"
        MAX-ACCESS          read-write
        STATUS              current
        DESCRIPTION         "This value is used for adjustment of Closed Loop
                            Power Control Calculation"
        ::= { necWimaxBsPowerControlEntry 21 }

    necWimaxBsPwrctrlCinrPriority OBJECT-TYPE
        SYNTAX              Integer32 (0..65535)
        MAX-ACCESS          read-write
        STATUS              current
        DESCRIPTION         "CINR measurement priority"
        ::= { necWimaxBsPowerControlEntry 22 }

    necWimaxBsPwrctrlRssiRptInterval OBJECT-TYPE
        SYNTAX              Integer32 (0..60)
        MAX-ACCESS          read-write
        STATUS              current
        DESCRIPTION         "Request Report Interval for REP-REQ/RSP"
        ::= { necWimaxBsPowerControlEntry 23 }

    necWimaxBsPwrctrlPathLossAdjust OBJECT-TYPE
        SYNTAX              Integer32 (-128..127)
        MAX-ACCESS          read-write
        STATUS              current
        DESCRIPTION         "The value to adjust PATH LOSS"
        ::= { necWimaxBsPowerControlEntry 24 }

    necWimaxBsPwrctrlRssiAveraging OBJECT-TYPE
        SYNTAX              Integer32 (0..15)
        MAX-ACCESS          read-write
        STATUS              current
        DESCRIPTION         "averaging parameter for REP-REQ TLV type1.1"
        ::= { necWimaxBsPowerControlEntry 25 }

    necWimaxBsPwrctrlDlChMatrixA OBJECT-TYPE
        SYNTAX              OCTET STRING (SIZE(10))
        MAX-ACCESS          read-write
        STATUS              current
        DESCRIPTION         "This object indicates necessary CN value (-128-127dB)
                            for MatrixA downlink. It is assumed array forms
                            the following in each MCS. [0]QPSK 1/2 x4 (Default
                            = -2) [1]QPSK 1/2 x2 (Default = 1) [2]QPSK 1/2
                            (Default = 4) [3]QPSK 3/4 (Default = 8) [4]16QAM
                            1/2 (Default = 10) [5]16QAM 3/4 (Default = 14)
                            [6]64QAM 1/2 (Default = 20) [7]64QAM 2/3 (Default
                            = 24) [8]64QAM 3/4 (Default = 28) [9]64QAM 5/6
                            (Default = 32)"
        ::= { necWimaxBsPowerControlEntry 26 }

    necWimaxBsPwrctrlDlChMatrixB OBJECT-TYPE
        SYNTAX              OCTET STRING (SIZE(10))
        MAX-ACCESS          read-write
        STATUS              current
        DESCRIPTION         "This object indicates necessary CN value (-128-127dB)
                            for MatrixB downlink. It is assumed array forms
                            the following in each MCS. [0]QPSK 1/2 x4 (Default
                            = -2) [1]QPSK 1/2 x2 (Default = 1) [2]QPSK 1/2
                            (Default = 4) [3]QPSK 3/4 (Default = 8) [4]16QAM
                            1/2 (Default = 10) [5]16QAM 3/4 (Default = 14)
                            [6]64QAM 1/2 (Default = 20) [7]64QAM 2/3 (Default
                            = 24) [8]64QAM 3/4 (Default = 28) [9]64QAM 5/6
                            (Default = 32)"
        ::= { necWimaxBsPowerControlEntry 27 }

    necWimaxBsPwrctrlMatrixCtrlInterval OBJECT-TYPE
        SYNTAX              Integer32 (0..65535)
        UNITS               "frames"
        MAX-ACCESS          read-write
        STATUS              current
        DESCRIPTION         "This object indicates the Matrix control interval."
        ::= { necWimaxBsPowerControlEntry 28 }

    necWimaxBsPwrctrlDlRateUp OBJECT-TYPE
        SYNTAX              Integer32 (0..65535)
        MAX-ACCESS          read-write
        STATUS              current
        DESCRIPTION         "threshold count for rate up. downlink"
        ::= { necWimaxBsPowerControlEntry 29 }

    necWimaxBsPwrctrlDlRateDown OBJECT-TYPE
        SYNTAX              Integer32 (0..255)
        MAX-ACCESS          read-write
        STATUS              current
        DESCRIPTION         "threshold count for rate down. downlink"
        ::= { necWimaxBsPowerControlEntry 30 }

    necWimaxBsSubchannelisation OBJECT-TYPE
        SYNTAX              INTEGER {
                                disable( 0 ),
                                enableOnlyBeforeEntry( 1 ),
                                enableOnlyAfterEntry( 2 ),
                                enable( 3 )
                            }
        MAX-ACCESS          read-write
        STATUS              current
        DESCRIPTION         "this mib indicates whether subchannelisation is
                            used"
        ::= { necWimaxBsPowerControlEntry 31 }

    necWimaxBsSubchLimit OBJECT-TYPE
        SYNTAX              OCTET STRING (SIZE(4))
        MAX-ACCESS          read-write
        STATUS              current
        DESCRIPTION         "limit value for subchannelisation. octet0:before
                            entry octet1:class1(after entry) octet2:class2(after
                            entry) octet3:class3(after entry) default value
                            is 4-8-4-2"
        ::= { necWimaxBsPowerControlEntry 32 }

    necWimaxBsSubchThreshold OBJECT-TYPE
        SYNTAX              OCTET STRING (SIZE(3 | 4))
        MAX-ACCESS          read-write
        STATUS              current
        DESCRIPTION         "threshold value for subchannelisation. octet0:class1(after
                            entry) octet1:class2(after entry) octet2:class3(after
                            entry) default value is 0x54-57-5a"
        ::= { necWimaxBsPowerControlEntry 33 }

    necWimaxBsPwrctrlLaDlEnable OBJECT-TYPE
        SYNTAX              INTEGER {
                                disable( 0 ),
                                enable( 1 )
                            }
        MAX-ACCESS          read-write
        STATUS              current
        DESCRIPTION         "Down Link Link Adaptation enable/disable flag"
        ::= { necWimaxBsPowerControlEntry 34 }

    necWimaxBsPwrctrlRxGain OBJECT-TYPE
        SYNTAX              Integer32 (0..127)
        MAX-ACCESS          read-write
        STATUS              current
        DESCRIPTION         "Rx Gain"
        ::= { necWimaxBsPowerControlEntry 35 }

    necWimaxBsPwrctrlRateCtrlOffset OBJECT-TYPE
        SYNTAX              Integer32 (0..65535)
        MAX-ACCESS          read-write
        STATUS              current
        DESCRIPTION         "This object indicates the rate control offset."
        ::= { necWimaxBsPowerControlEntry 36 }

    necWimaxBsPwrctrlDlOuterLoopKeepTime OBJECT-TYPE
        SYNTAX              Integer32 (0..65535)
        MAX-ACCESS          read-write
        STATUS              current
        DESCRIPTION         "Outerloop keep timer. downlink"
        ::= { necWimaxBsPowerControlEntry 37 }

    necWimaxBsPwrctrlDlOuterLoop OBJECT-TYPE
        SYNTAX              INTEGER {
                                disable( 0 ),
                                enable( 1 )
                            }
        MAX-ACCESS          read-write
        STATUS              current
        DESCRIPTION         "This item indicates outer loop enable or disable
                            in case of down link link adaptation is enable."
        ::= { necWimaxBsPowerControlEntry 38 }

    necWimaxBsPwrctrlUlOuterLoop OBJECT-TYPE
        SYNTAX              INTEGER {
                                disable( 0 ),
                                enable( 1 )
                            }
        MAX-ACCESS          read-write
        STATUS              current
        DESCRIPTION         "This item indicates outer loop enable or disable
                            in case of uplink link link adaptation is enable."
        ::= { necWimaxBsPowerControlEntry 39 }

    necWimaxBsPwrctrlDlRateCtrlInterval OBJECT-TYPE
        SYNTAX              Integer32 (1..1024)
        MAX-ACCESS          read-write
        STATUS              current
        DESCRIPTION         "This object indicates the Rate control execution
                            interval. It applies to Downlink. Unit: Frame"
        ::= { necWimaxBsPowerControlEntry 40 }

    necWimaxBsPwrctrlUlRateCtrlInterval OBJECT-TYPE
        SYNTAX              Integer32 (1..1024)
        MAX-ACCESS          read-write
        STATUS              current
        DESCRIPTION         "This object indicates the Rate control execution
                            interval. It applies to Uplink. Unit: Frame"
        ::= { necWimaxBsPowerControlEntry 41 }

    necWimaxBsPwrctrlUlRateUp OBJECT-TYPE
        SYNTAX              Integer32 (0..65535)
        MAX-ACCESS          read-write
        STATUS              current
        DESCRIPTION         "threshold count for rate up. uplink"
        ::= { necWimaxBsPowerControlEntry 42 }

    necWimaxBsPwrctrlUlRateDown OBJECT-TYPE
        SYNTAX              Integer32 (0..255)
        MAX-ACCESS          read-write
        STATUS              current
        DESCRIPTION         "threshold count for rate down. uplink"
        ::= { necWimaxBsPowerControlEntry 43 }

    necWimaxBsPwrctrlUlMimoMinRate OBJECT-TYPE
        SYNTAX              Integer32 (0..3)
        MAX-ACCESS          read-write
        STATUS              current
        DESCRIPTION         "minimun physical rate for uplink-MIMO"
        ::= { necWimaxBsPowerControlEntry 44 }

    necWimaxBsPwrctrlUlOuterLoopKeepTime OBJECT-TYPE
        SYNTAX              Integer32 (0..65535)
        MAX-ACCESS          read-write
        STATUS              current
        DESCRIPTION         "Outerloop keep timer. uplink"
        ::= { necWimaxBsPowerControlEntry 45 }

    necWimaxBsPwrctrlDlRateBack OBJECT-TYPE
        SYNTAX              Integer32 (0..255)
        MAX-ACCESS          read-write
        STATUS              current
        DESCRIPTION         "This parameter is used DL-LA with outer loop."
        ::= { necWimaxBsPowerControlEntry 46 }

    necWimaxBsPwrctrlUlRateBack OBJECT-TYPE
        SYNTAX              Integer32 (0..255)
        MAX-ACCESS          read-write
        STATUS              current
        DESCRIPTION         "This parameter is used UL-LA with outer loop."
        ::= { necWimaxBsPowerControlEntry 47 }

    necWimaxBsHwAdjustTable OBJECT-TYPE
        SYNTAX              SEQUENCE OF NecWimaxBsHwAdjustEntry
        MAX-ACCESS          not-accessible
        STATUS              current
        DESCRIPTION         "H"
        ::= { necWimaxBsOfdmaPhy 3 }

    necWimaxBsHwAdjustEntry OBJECT-TYPE
        SYNTAX              NecWimaxBsHwAdjustEntry
        MAX-ACCESS          not-accessible
        STATUS              current
        DESCRIPTION         "H"
        INDEX               {
                                ifIndex
                            }
        ::= { necWimaxBsHwAdjustTable 1 }

    NecWimaxBsHwAdjustEntry ::= SEQUENCE {
        necWimaxHwAdjustGtb1Int
            Integer32,
        necWimaxHwAdjustGtb2Int
            Integer32,
        necWimaxHwAdjustGtb3Int
            Integer32,
        necWimaxHwAdjustRssi
            Integer32,
        necWimaxHwAdjustCinr
            Integer32,
        necWimaxHwAdjustNIAverage
            Integer32,
        necWimaxHwAdjustPowerMergin
            Integer32,
        necWimaxHwAdjustUlBusrtPwrOffset
            Integer32,
        necWimaxHwAdjustOduNoiseFloor
            Unsigned32
    }

    necWimaxHwAdjustGtb1Int OBJECT-TYPE
        SYNTAX              Integer32 (0..4999)
        MAX-ACCESS          read-write
        STATUS              current
        DESCRIPTION         "For GTB1 interrupt positioning."
        ::= { necWimaxBsHwAdjustEntry 1 }

    necWimaxHwAdjustGtb2Int OBJECT-TYPE
        SYNTAX              Integer32 (0..4999)
        MAX-ACCESS          read-write
        STATUS              current
        DESCRIPTION         "For GTB2 interrupt positioning."
        ::= { necWimaxBsHwAdjustEntry 2 }

    necWimaxHwAdjustGtb3Int OBJECT-TYPE
        SYNTAX              Integer32 (0..4999)
        MAX-ACCESS          read-write
        STATUS              current
        DESCRIPTION         "For GTB3 interrupt positioning."
        ::= { necWimaxBsHwAdjustEntry 3 }

    necWimaxHwAdjustRssi OBJECT-TYPE
        SYNTAX              Integer32 (-32768..32767)
        MAX-ACCESS          read-write
        STATUS              current
        DESCRIPTION         "For RSSI correction value adjustment. Unit (0.25dB)."
        ::= { necWimaxBsHwAdjustEntry 4 }

    necWimaxHwAdjustCinr OBJECT-TYPE
        SYNTAX              Integer32 (-32768..32767)
        MAX-ACCESS          read-write
        STATUS              current
        DESCRIPTION         "For CINR correction value adjustment. Unit (0.25dB)."
        ::= { necWimaxBsHwAdjustEntry 5 }

    necWimaxHwAdjustNIAverage OBJECT-TYPE
        SYNTAX              Integer32 (0..15)
        MAX-ACCESS          read-write
        STATUS              current
        DESCRIPTION         "Averaging factor(a) used by leveling N+I value."
        ::= { necWimaxBsHwAdjustEntry 6 }

    necWimaxHwAdjustPowerMergin OBJECT-TYPE
        SYNTAX              Integer32 (-128..127)
        MAX-ACCESS          read-write
        STATUS              current
        DESCRIPTION         "Adjustment value when reserve strength electric
                            power is calculated by multi-go up rate processing.
                            Unit 0.5dB."
        ::= { necWimaxBsHwAdjustEntry 7 }

    necWimaxHwAdjustUlBusrtPwrOffset OBJECT-TYPE
        SYNTAX              Integer32 (0..7)
        MAX-ACCESS          read-write
        STATUS              current
        DESCRIPTION         "Only the set value raises the transmission power
                            of UL Burst including the MAC management message
                            (operation by MS). Unit: 0.5dB."
        ::= { necWimaxBsHwAdjustEntry 8 }

    necWimaxHwAdjustOduNoiseFloor OBJECT-TYPE
        SYNTAX              Unsigned32 (0..100)
        MAX-ACCESS          read-write
        STATUS              current
        DESCRIPTION         "odu-noise-floor"
        ::= { necWimaxBsHwAdjustEntry 9 }

    necWimaxBsAirStatUlTable OBJECT-TYPE
        SYNTAX              SEQUENCE OF NecWimaxBsAirStatUlEntry
        MAX-ACCESS          not-accessible
        STATUS              current
        DESCRIPTION         "UL AIR STAT status Table"
        ::= { necWimaxBsOfdmaPhy 4 }

    necWimaxBsAirStatUlEntry OBJECT-TYPE
        SYNTAX              NecWimaxBsAirStatUlEntry
        MAX-ACCESS          not-accessible
        STATUS              current
        DESCRIPTION         "Please replace this text with your description."
        INDEX               {
                                ifIndex,
                                necWimaxBsAirStatMsmac
                            }
        ::= { necWimaxBsAirStatUlTable 1 }

    NecWimaxBsAirStatUlEntry ::= SEQUENCE {
        necWimaxBsAirStatMsmac
            MacAddress,
        necWimaxBsAirStatUlFecCode
            INTEGER,
        necWimaxBsAirStatUlRssi
            Integer32,
        necWimaxBsAirStatUlCinr
            Integer32
    }

    necWimaxBsAirStatMsmac OBJECT-TYPE
        SYNTAX              MacAddress
        MAX-ACCESS          not-accessible
        STATUS              current
        DESCRIPTION         "MS MAC Address for AIR Stat"
        ::= { necWimaxBsAirStatUlEntry 1 }

    necWimaxBsAirStatUlFecCode OBJECT-TYPE
        SYNTAX              INTEGER {
                                qpskcc12( 0 ),
                                qpskcc34( 1 ),
                                qam16cc12( 2 ),
                                qam16cc34( 3 ),
                                qam64cc12( 4 ),
                                qam64cc23( 5 ),
                                qam64cc34( 6 ),
                                qpskctc12( 13 ),
                                qpskctc34( 15 ),
                                qam16ctc12( 16 ),
                                qam16ctc34( 17 ),
                                qam64ctc12( 18 ),
                                qam64ctc23( 19 ),
                                qam64ctc34( 20 ),
                                qam64ctc56( 21 )
                            }
        MAX-ACCESS          read-only
        STATUS              current
        DESCRIPTION         "UL FEC CODE"
        ::= { necWimaxBsAirStatUlEntry 2 }

    necWimaxBsAirStatUlRssi OBJECT-TYPE
        SYNTAX              Integer32
        MAX-ACCESS          read-only
        STATUS              current
        DESCRIPTION         "Uplink RSSI"
        ::= { necWimaxBsAirStatUlEntry 3 }

    necWimaxBsAirStatUlCinr OBJECT-TYPE
        SYNTAX              Integer32
        MAX-ACCESS          read-only
        STATUS              current
        DESCRIPTION         "Uplink Physical CINR"
        ::= { necWimaxBsAirStatUlEntry 4 }

    necWimaxBsAirStatDlTable OBJECT-TYPE
        SYNTAX              SEQUENCE OF NecWimaxBsAirStatDlEntry
        MAX-ACCESS          not-accessible
        STATUS              current
        DESCRIPTION         "DL AIR STAT status Table"
        ::= { necWimaxBsOfdmaPhy 5 }

    necWimaxBsAirStatDlEntry OBJECT-TYPE
        SYNTAX              NecWimaxBsAirStatDlEntry
        MAX-ACCESS          not-accessible
        STATUS              current
        DESCRIPTION         "Please replace this text with your description."
        INDEX               {
                                ifIndex,
                                necWimaxBsAirStatMsmac
                            }
        ::= { necWimaxBsAirStatDlTable 1 }

    NecWimaxBsAirStatDlEntry ::= SEQUENCE {
        necWimaxBsAirStatDlFecCode
            INTEGER,
        necWimaxBsAirStatDlRepetition
            Integer32,
        necWimaxBsAirStatDlMatrixMode
            INTEGER,
        necWimaxBsAirStatDlZoneCinr
            Integer32,
        necWimaxBsAirStatDlPreambleCinr
            Integer32,
        necWimaxBsAirStatDlZoneEffectiveCinr
            Integer32,
        necWimaxBsAirStatDlRssi
            Integer32,
        necWimaxBsAirStatDlPathLoss
            Integer32
    }

    necWimaxBsAirStatDlFecCode OBJECT-TYPE
        SYNTAX              INTEGER {
                                qpskcc12( 0 ),
                                qpskcc34( 1 ),
                                qam16cc12( 2 ),
                                qam16cc34( 3 ),
                                qam64cc12( 4 ),
                                qam64cc23( 5 ),
                                qam64cc34( 6 ),
                                qpskctc12( 13 ),
                                qpskctc34( 15 ),
                                qam16ctc12( 16 ),
                                qam16ctc34( 17 ),
                                qam64ctc12( 18 ),
                                qam64ctc23( 19 ),
                                qam64ctc34( 20 ),
                                qam64ctc56( 21 )
                            }
        MAX-ACCESS          read-only
        STATUS              current
        DESCRIPTION         "UL FEC CODE"
        ::= { necWimaxBsAirStatDlEntry 2 }

    necWimaxBsAirStatDlRepetition OBJECT-TYPE
        SYNTAX              Integer32 (1..6)
        MAX-ACCESS          read-only
        STATUS              current
        DESCRIPTION         "Number of Repetitions (valid when FEC CODE = QPSK)"
        ::= { necWimaxBsAirStatDlEntry 3 }

    necWimaxBsAirStatDlMatrixMode OBJECT-TYPE
        SYNTAX              INTEGER {
                                none( 0 ),
                                matrixA( 1 ),
                                matrixB( 2 )
                            }
        MAX-ACCESS          read-only
        STATUS              current
        DESCRIPTION         "valid only MIMO supported"
        ::= { necWimaxBsAirStatDlEntry 4 }

    necWimaxBsAirStatDlZoneCinr OBJECT-TYPE
        SYNTAX              Integer32
        MAX-ACCESS          read-only
        STATUS              current
        DESCRIPTION         "Downlink Zone Specific Physical CINR"
        ::= { necWimaxBsAirStatDlEntry 5 }

    necWimaxBsAirStatDlPreambleCinr OBJECT-TYPE
        SYNTAX              Integer32
        MAX-ACCESS          read-only
        STATUS              current
        DESCRIPTION         "Downlink Preamble Physical CINR"
        ::= { necWimaxBsAirStatDlEntry 6 }

    necWimaxBsAirStatDlZoneEffectiveCinr OBJECT-TYPE
        SYNTAX              Integer32
        MAX-ACCESS          read-only
        STATUS              current
        DESCRIPTION         "Downlink Zone Specific Effective CINR"
        ::= { necWimaxBsAirStatDlEntry 7 }

    necWimaxBsAirStatDlRssi OBJECT-TYPE
        SYNTAX              Integer32
        MAX-ACCESS          read-only
        STATUS              current
        DESCRIPTION         "Downlink RSSI"
        ::= { necWimaxBsAirStatDlEntry 8 }

    necWimaxBsAirStatDlPathLoss OBJECT-TYPE
        SYNTAX              Integer32
        MAX-ACCESS          read-only
        STATUS              current
        DESCRIPTION         "Downlink path loss"
        ::= { necWimaxBsAirStatDlEntry 9 }

    necWimaxBsPkmObjects OBJECT IDENTIFIER ::= { necWimaxBsIfObjects 3 }

    necWimaxBsPkmV1Objects OBJECT IDENTIFIER ::= { necWimaxBsPkmObjects 1 }

    necWimaxBsPkmConfigTable OBJECT-TYPE
        SYNTAX              SEQUENCE OF NecWimaxBsPkmConfigEntry
        MAX-ACCESS          not-accessible
        STATUS              current
        DESCRIPTION         "This table contains the configuration of the PKM
                            attributes that are to be used for BS and SS."
        ::= { necWimaxBsPkmV1Objects 1 }

    necWimaxBsPkmConfigEntry OBJECT-TYPE
        SYNTAX              NecWimaxBsPkmConfigEntry
        MAX-ACCESS          not-accessible
        STATUS              current
        DESCRIPTION         "Each entry contains objects that define the PKM
                            attributes of each BS wireless interface, and
                            all SSs that are connected with such BS. The
                            table is indexed by ifIndex that is associated
                            with the BS sector."
        INDEX               {
                                ifIndex
                            }
        ::= { necWimaxBsPkmConfigTable 1 }

    NecWimaxBsPkmConfigEntry ::= SEQUENCE {
        necWimaxBsPkmEapStartAllow
            INTEGER
    }

    necWimaxBsPkmEapStartAllow OBJECT-TYPE
        SYNTAX              INTEGER {
                                discardEapStart( 0 ),
                                allowdEapStart( 1 )
                            }
        MAX-ACCESS          read-write
        STATUS              current
        DESCRIPTION         "EAP Start allow flag"
        ::= { necWimaxBsPkmConfigEntry 1 }

    necWimaxBsIfStatusTable OBJECT-TYPE
        SYNTAX              SEQUENCE OF NecWimaxBsIfStatusEntry
        MAX-ACCESS          not-accessible
        STATUS              current
        DESCRIPTION         "The status of transmission."
        ::= { necWimaxBsIfObjects 4 }

    necWimaxBsIfStatusEntry OBJECT-TYPE
        SYNTAX              NecWimaxBsIfStatusEntry
        MAX-ACCESS          not-accessible
        STATUS              current
        DESCRIPTION         "This table is indexed by ifIndex."
        INDEX               {
                                ifIndex
                            }
        ::= { necWimaxBsIfStatusTable 1 }

    NecWimaxBsIfStatusEntry ::= SEQUENCE {
        necWimaxBsBlockageAdminStatus
            INTEGER,
        necWimaxBsBlockageOperationStatus
            INTEGER,
        necWimaxBsCarrierAdminStatus
            INTEGER,
        necWimaxBsCarrierOperationStatus
            INTEGER,
        necWimaxBsNetBlockageAdminStatus
            INTEGER,
        necWimaxBsNetCarrierAdminStatus
            INTEGER
    }

    necWimaxBsBlockageAdminStatus OBJECT-TYPE
        SYNTAX              INTEGER {
                                open( 0 ),
                                close( 1 ),
                                make( 2 )
                            }
        MAX-ACCESS          read-write
        STATUS              current
        DESCRIPTION         "It indicate the status of the blockage's control."
        ::= { necWimaxBsIfStatusEntry 1 }

    necWimaxBsBlockageOperationStatus OBJECT-TYPE
        SYNTAX              INTEGER {
                                open( 0 ),
                                close( 1 ),
                                make( 2 )
                            }
        MAX-ACCESS          read-only
        STATUS              current
        DESCRIPTION         "It indicate the status of the blockage's operation."
        ::= { necWimaxBsIfStatusEntry 2 }

    necWimaxBsCarrierAdminStatus OBJECT-TYPE
        SYNTAX              INTEGER {
                                txoff( 0 ),
                                txon( 1 )
                            }
        MAX-ACCESS          read-write
        STATUS              current
        DESCRIPTION         "It indicate the status of the carrier control."
        ::= { necWimaxBsIfStatusEntry 3 }

    necWimaxBsCarrierOperationStatus OBJECT-TYPE
        SYNTAX              INTEGER {
                                txoff( 0 ),
                                txon( 1 ),
                                learning( 2 )
                            }
        MAX-ACCESS          read-only
        STATUS              current
        DESCRIPTION         "It indicate the status of the carrier operation."
        ::= { necWimaxBsIfStatusEntry 4 }

    necWimaxBsNetBlockageAdminStatus OBJECT-TYPE
        SYNTAX              INTEGER {
                                open( 0 ),
                                close( 1 )
                            }
        MAX-ACCESS          read-write
        STATUS              current
        DESCRIPTION         "It indicate the status of the network blockage's
                            control."
        ::= { necWimaxBsIfStatusEntry 5 }

    necWimaxBsNetCarrierAdminStatus OBJECT-TYPE
        SYNTAX              INTEGER {
                                txoff( 0 ),
                                txon( 1 )
                            }
        MAX-ACCESS          read-write
        STATUS              current
        DESCRIPTION         "It indicate the status of the carrier control."
        ::= { necWimaxBsIfStatusEntry 6 }

    necWimaxBsIfTable OBJECT-TYPE
        SYNTAX              SEQUENCE OF NecWimaxBsIfEntry
        MAX-ACCESS          not-accessible
        STATUS              current
        DESCRIPTION         "BS configurations"
        ::= { necWimaxBsIfObjects 5 }

    necWimaxBsIfEntry OBJECT-TYPE
        SYNTAX              NecWimaxBsIfEntry
        MAX-ACCESS          not-accessible
        STATUS              current
        DESCRIPTION         "configurations"
        INDEX               {
                                ifIndex
                            }
        ::= { necWimaxBsIfTable 1 }

    NecWimaxBsIfEntry ::= SEQUENCE {
        necWimaxBsConfLinkMon
            INTEGER,
        necWimaxBsConfLinkHealthCheck
            INTEGER,
        necWimaxBsConfAswgwOamPortTx
            Integer32,
        necWimaxBsConfAswgwOamPortRx
            Integer32,
        necWimaxBsConfAuthgwId
            OCTET STRING,
        necWimaxBsConfAuthgwIp
            IpAddress,
        necWimaxBsConfAuthgwPort
            Integer32,
        necWimaxBsConfAsngwId
            OCTET STRING,
        necWimaxBsConfAsngwDpIp
            IpAddress,
        necWimaxBsConfAsngwDpPort
            Integer32,
        necWimaxBsConfAsngwEpIp
            IpAddress,
        necWimaxBsConfAsngwEpPort
            Integer32,
        necWimaxBsConfAsngwRxPort
            Integer32,
        necWimaxBsConfAsngwTimer
            Integer32,
        necWimaxBsConfAsngwRetry
            Integer32
    }

    necWimaxBsConfLinkMon OBJECT-TYPE
        SYNTAX              INTEGER {
                                disable( 0 ),
                                enable( 1 )
                            }
        MAX-ACCESS          read-write
        STATUS              current
        DESCRIPTION         "This indicates which R6 link monitor On or Off"
        ::= { necWimaxBsIfEntry 2 }

    necWimaxBsConfLinkHealthCheck OBJECT-TYPE
        SYNTAX              INTEGER {
                                disable( 0 ),
                                enable( 1 )
                            }
        MAX-ACCESS          read-write
        STATUS              current
        DESCRIPTION         "This indicates which R6 link health cheak message
                            and wakeup indication is On or Off"
        ::= { necWimaxBsIfEntry 3 }

    necWimaxBsConfAswgwOamPortTx OBJECT-TYPE
        SYNTAX              Integer32 (1..65535)
        MAX-ACCESS          read-write
        STATUS              current
        DESCRIPTION         "ASNGW Tx Port for OAM"
        ::= { necWimaxBsIfEntry 4 }

    necWimaxBsConfAswgwOamPortRx OBJECT-TYPE
        SYNTAX              Integer32 (1..65535)
        MAX-ACCESS          read-write
        STATUS              current
        DESCRIPTION         "ASNGW Rx Port for OAM"
        ::= { necWimaxBsIfEntry 5 }

    necWimaxBsConfAuthgwId OBJECT-TYPE
        SYNTAX              OCTET STRING (SIZE(4))
        MAX-ACCESS          read-write
        STATUS              current
        DESCRIPTION         "identifer of authgw"
        ::= { necWimaxBsIfEntry 6 }

    necWimaxBsConfAuthgwIp OBJECT-TYPE
        SYNTAX              IpAddress
        MAX-ACCESS          read-write
        STATUS              current
        DESCRIPTION         "IP address of authgw"
        ::= { necWimaxBsIfEntry 7 }

    necWimaxBsConfAuthgwPort OBJECT-TYPE
        SYNTAX              Integer32 (0..65535)
        MAX-ACCESS          read-write
        STATUS              current
        DESCRIPTION         "port noumber of authgw"
        ::= { necWimaxBsIfEntry 8 }

    necWimaxBsConfAsngwId OBJECT-TYPE
        SYNTAX              OCTET STRING (SIZE(4))
        MAX-ACCESS          read-write
        STATUS              current
        DESCRIPTION         "identifer of ASN GW"
        ::= { necWimaxBsIfEntry 9 }

    necWimaxBsConfAsngwDpIp OBJECT-TYPE
        SYNTAX              IpAddress
        MAX-ACCESS          read-write
        STATUS              current
        DESCRIPTION         "IP address of ASNGW DP"
        ::= { necWimaxBsIfEntry 10 }

    necWimaxBsConfAsngwDpPort OBJECT-TYPE
        SYNTAX              Integer32 (0..65535)
        MAX-ACCESS          read-write
        STATUS              current
        DESCRIPTION         "port number of ASNGW DP"
        ::= { necWimaxBsIfEntry 11 }

    necWimaxBsConfAsngwEpIp OBJECT-TYPE
        SYNTAX              IpAddress
        MAX-ACCESS          read-write
        STATUS              current
        DESCRIPTION         "IP address of ASNGW EP"
        ::= { necWimaxBsIfEntry 12 }

    necWimaxBsConfAsngwEpPort OBJECT-TYPE
        SYNTAX              Integer32 (0..65535)
        MAX-ACCESS          read-write
        STATUS              current
        DESCRIPTION         "port number of ASNGW EP"
        ::= { necWimaxBsIfEntry 13 }

    necWimaxBsConfAsngwRxPort OBJECT-TYPE
        SYNTAX              Integer32 (0..65535)
        MAX-ACCESS          read-write
        STATUS              current
        DESCRIPTION         "Rx port number of ASN GW connection"
        ::= { necWimaxBsIfEntry 14 }

    necWimaxBsConfAsngwTimer OBJECT-TYPE
        SYNTAX              Integer32 (1..3600)
        MAX-ACCESS          read-write
        STATUS              current
        DESCRIPTION         "retry timer of ASN GW connection. defval = 2."
        ::= { necWimaxBsIfEntry 15 }

    necWimaxBsConfAsngwRetry OBJECT-TYPE
        SYNTAX              Integer32 (0..10)
        MAX-ACCESS          read-write
        STATUS              current
        DESCRIPTION         "retry count of ASN GW connection. defval = 3."
        ::= { necWimaxBsIfEntry 16 }

    necWimaxBsLicenseTable OBJECT-TYPE
        SYNTAX              SEQUENCE OF NecWimaxBsLicenseEntry
        MAX-ACCESS          not-accessible
        STATUS              current
        DESCRIPTION         "License information and License install control"
        ::= { necWimaxBsIfObjects 6 }

    necWimaxBsLicenseEntry OBJECT-TYPE
        SYNTAX              NecWimaxBsLicenseEntry
        MAX-ACCESS          not-accessible
        STATUS              current
        DESCRIPTION         "License information and control for this CHC"
        INDEX               {
                                ifIndex
                            }
        ::= { necWimaxBsLicenseTable 1 }

    NecWimaxBsLicenseEntry ::= SEQUENCE {
        necWimaxBsLicenseSubscriber
            Integer32,
        necWimaxBsLicenseUlThroughput
            Integer32,
        necWimaxBsLicenseDlThroughput
            Integer32,
        necWimaxBsLicenseHoOptimization
            BITS,
        necWimaxBsLicenseFunctions
            BITS,
        necWimaxBsLicenseUpdateAction
            TruthValue,
        necWimaxBsLicenseUpdateStatus
            INTEGER
    }

    necWimaxBsLicenseSubscriber OBJECT-TYPE
        SYNTAX              Integer32 (1..96)
        MAX-ACCESS          read-only
        STATUS              current
        DESCRIPTION         "MAX Subscriber"
        ::= { necWimaxBsLicenseEntry 1 }

    necWimaxBsLicenseUlThroughput OBJECT-TYPE
        SYNTAX              Integer32 (0..100)
        MAX-ACCESS          read-only
        STATUS              current
        DESCRIPTION         "MAX Throughput for Uplink, represented by %"
        ::= { necWimaxBsLicenseEntry 2 }

    necWimaxBsLicenseDlThroughput OBJECT-TYPE
        SYNTAX              Integer32 (0..100)
        MAX-ACCESS          read-only
        STATUS              current
        DESCRIPTION         "MAX Throughput for Downlink, represented by %"
        ::= { necWimaxBsLicenseEntry 3 }

    necWimaxBsLicenseHoOptimization OBJECT-TYPE
        SYNTAX              BITS {
                                optHo( 3 ),
                                withReAuthAndTekUpdate( 4 ),
                                withTekUpdate( 5 )
                            }
        MAX-ACCESS          read-only
        STATUS              current
        DESCRIPTION         "Permitted handover optimization pattern. Corresponded
                            Bit 1=ON, 0=OFF. BIt#3 : Optimized HO BIT#4 :
                            Optimized HO with Re-Authentication and TEK update
                            BIT#5 : Optimized HO with TEK update"
        ::= { necWimaxBsLicenseEntry 4 }

    necWimaxBsLicenseFunctions OBJECT-TYPE
        SYNTAX              BITS {
                                msInitHo( 0 ),
                                matrixA( 1 ),
                                matrixB( 2 ),
                                ulMimo( 3 ),
                                harq( 4 ),
                                arq( 5 ),
                                segment( 6 ),
                                fusc( 7 ),
                                negativeVolumeCount( 8 ),
                                sleepMode( 9 ),
                                pagingService( 10 )
                            }
        MAX-ACCESS          read-only
        STATUS              current
        DESCRIPTION         "Lisenced Functions. Corresponded Bit 1=ON, 0=OFF.
                            BIt#0 : MS initiated HO BIT#1 : Matrix A (DL
                            MIMO) BIT#2 : Matrix B (DL MIMO) BIT#3 : UL MIMO
                            BIT#4 : HARQ BIT#5 : ARQ BIT#6 : Segment BIT#7
                            : FUSC BIT#8 : Negative Volume Count BIT#9 :
                            Sleep Mode BIT#10 : Paging Service"
        ::= { necWimaxBsLicenseEntry 5 }

    necWimaxBsLicenseUpdateAction OBJECT-TYPE
        SYNTAX              TruthValue
        MAX-ACCESS          read-write
        STATUS              current
        DESCRIPTION         "To start license update. SET to ture(1) . In case
                            of GET this MIB always return false(2). Setting
                            false(2) results no action and response is always
                            OK."
        ::= { necWimaxBsLicenseEntry 6 }

    necWimaxBsLicenseUpdateStatus OBJECT-TYPE
        SYNTAX              INTEGER {
                                init( 0 ),
                                verifying( 2 ),
                                verificationCompleted( 3 ),
                                verificationFailed( 4 ),
                                validating( 5 ),
                                validationCompleted( 6 ),
                                validationFailed( 7 )
                            }
        MAX-ACCESS          read-only
        STATUS              current
        DESCRIPTION         "License File Updating Status"
        ::= { necWimaxBsLicenseEntry 7 }

    necWimaxBsInitParamTable OBJECT-TYPE
        SYNTAX              SEQUENCE OF NecWimaxBsInitParamEntry
        MAX-ACCESS          not-accessible
        STATUS              current
        DESCRIPTION         "Initial parameter install control"
        ::= { necWimaxBsIfObjects 7 }

    necWimaxBsInitParamEntry OBJECT-TYPE
        SYNTAX              NecWimaxBsInitParamEntry
        MAX-ACCESS          not-accessible
        STATUS              current
        DESCRIPTION         "Initial parameter install control for this CHC"
        INDEX               {
                                ifIndex
                            }
        ::= { necWimaxBsInitParamTable 1 }

    NecWimaxBsInitParamEntry ::= SEQUENCE {
        necWimaxBsInitParamUpdateAction
            INTEGER,
        necWimaxBsInitParamNewVersion
            OCTET STRING,
        necWimaxBsInitParamCurrentVersion
            OCTET STRING,
        necWimaxBsInitParamOldVersion
            OCTET STRING
    }

    necWimaxBsInitParamUpdateAction OBJECT-TYPE
        SYNTAX              INTEGER {
                                noAction( 0 ),
                                reconfig( 1 ),
                                rollback( 2 )
                            }
        MAX-ACCESS          read-write
        STATUS              current
        DESCRIPTION         "Set reconfig(1) to start initial parameter re-configuration,
                            Set rollback(2) to start initial parameter rollbaking.
                            In case of GET this MIB always return noAction(0).
                            Setting noAction(0) results no action and response
                            is always OK."
        ::= { necWimaxBsInitParamEntry 1 }

    necWimaxBsInitParamNewVersion OBJECT-TYPE
        SYNTAX              OCTET STRING (SIZE(0..32))
        MAX-ACCESS          read-only
        STATUS              current
        DESCRIPTION         "New Initial Parameter's version"
        ::= { necWimaxBsInitParamEntry 2 }

    necWimaxBsInitParamCurrentVersion OBJECT-TYPE
        SYNTAX              OCTET STRING (SIZE(0..32))
        MAX-ACCESS          read-only
        STATUS              current
        DESCRIPTION         "Current Initial Parameter's version"
        ::= { necWimaxBsInitParamEntry 3 }

    necWimaxBsInitParamOldVersion OBJECT-TYPE
        SYNTAX              OCTET STRING (SIZE(0..32))
        MAX-ACCESS          read-only
        STATUS              current
        DESCRIPTION         "Old Initial Parameter's version"
        ::= { necWimaxBsInitParamEntry 4 }

    necWimaxBsIfmObjects OBJECT IDENTIFIER ::= { necWimaxBsIfMib 2 }

    necWimaxBsIfmCm OBJECT IDENTIFIER ::= { necWimaxBsIfmObjects 1 }

    necWimaxBsIfmCapabilities OBJECT IDENTIFIER ::= { necWimaxBsIfmCm 1 }

    necWimaxBsIfmBasicCapabilitiesTable OBJECT-TYPE
        SYNTAX              SEQUENCE OF NecWimaxBsIfmBasicCapabilitiesEntry
        MAX-ACCESS          not-accessible
        STATUS              current
        DESCRIPTION         "capabilities of BS mobility function"
        ::= { necWimaxBsIfmCapabilities 1 }

    necWimaxBsIfmBasicCapabilitiesEntry OBJECT-TYPE
        SYNTAX              NecWimaxBsIfmBasicCapabilitiesEntry
        MAX-ACCESS          not-accessible
        STATUS              current
        DESCRIPTION         "indexed by ifIndex"
        INDEX               {
                                ifIndex
                            }
        ::= { necWimaxBsIfmBasicCapabilitiesTable 1 }

    NecWimaxBsIfmBasicCapabilitiesEntry ::= SEQUENCE {
        necWimaxBsIfmCapHoTrigValue
            Integer32,
        necWimaxBsIfmCapHoTrigDuration
            Integer32,
        necWimaxBsIfmCapHoIndTimer
            Integer32,
        necWimaxBsIfmCapHoTrigFunction
            Integer32
    }

    necWimaxBsIfmCapHoTrigValue OBJECT-TYPE
        SYNTAX              Integer32
        MAX-ACCESS          read-only
        STATUS              current
        DESCRIPTION         "reference trigger value"
        ::= { necWimaxBsIfmBasicCapabilitiesEntry 1 }

    necWimaxBsIfmCapHoTrigDuration OBJECT-TYPE
        SYNTAX              Integer32
        UNITS               "ms"
        MAX-ACCESS          read-only
        STATUS              current
        DESCRIPTION         "trigger average duration"
        ::= { necWimaxBsIfmBasicCapabilitiesEntry 2 }

    necWimaxBsIfmCapHoIndTimer OBJECT-TYPE
        SYNTAX              Integer32
        UNITS               "s"
        MAX-ACCESS          read-only
        STATUS              current
        DESCRIPTION         "Time that HO starting request is not allowed after
                            HO-RSP is recieved at BS initiated HO."
        ::= { necWimaxBsIfmBasicCapabilitiesEntry 3 }

    necWimaxBsIfmCapHoTrigFunction OBJECT-TYPE
        SYNTAX              Integer32
        MAX-ACCESS          read-only
        STATUS              current
        DESCRIPTION         "Trigger condition of metric. 0x0: Reserved 0x1:
                            Metric of neighbor BS is greater than absolute
                            value 0x2: Metric of neighbor BS is less than
                            absolute value 0x3: Metric of neighbor BS is
                            greater than serving BS metric by relative value
                            0x4: Metric of neighbor BS is less than serving
                            BS metric by relative value 0x5: Metric of serving
                            BS greater than absolute value 0x6: Metric of
                            serving BS less than absolute value 0x7: Reserved"
        ::= { necWimaxBsIfmBasicCapabilitiesEntry 4 }

    necWimaxBsIfmCapabilitiesConfigTable OBJECT-TYPE
        SYNTAX              SEQUENCE OF NecWimaxBsIfmCapabilitiesConfigEntry
        MAX-ACCESS          not-accessible
        STATUS              current
        DESCRIPTION         "configured capabilities of BS mobility function"
        ::= { necWimaxBsIfmCapabilities 2 }

    necWimaxBsIfmCapabilitiesConfigEntry OBJECT-TYPE
        SYNTAX              NecWimaxBsIfmCapabilitiesConfigEntry
        MAX-ACCESS          not-accessible
        STATUS              current
        DESCRIPTION         "indexed by ifIndex"
        INDEX               {
                                ifIndex
                            }
        ::= { necWimaxBsIfmCapabilitiesConfigTable 1 }

    NecWimaxBsIfmCapabilitiesConfigEntry ::= SEQUENCE {
        necWimaxBsIfmCapCfgHoTrigValue
            Integer32,
        necWimaxBsIfmCapCfgHoTrigDuration
            Integer32,
        necWimaxBsIfmCapCfgHoIndTimer
            Integer32,
        necWimaxBsIfmCapCfgHoTrigFunction
            Integer32
    }

    necWimaxBsIfmCapCfgHoTrigValue OBJECT-TYPE
        SYNTAX              Integer32 (0..255)
        MAX-ACCESS          read-write
        STATUS              current
        DESCRIPTION         "reference trigger value"
        ::= { necWimaxBsIfmCapabilitiesConfigEntry 1 }

    necWimaxBsIfmCapCfgHoTrigDuration OBJECT-TYPE
        SYNTAX              Integer32 (0..255)
        UNITS               "frames"
        MAX-ACCESS          read-write
        STATUS              current
        DESCRIPTION         "trigger average duration"
        ::= { necWimaxBsIfmCapabilitiesConfigEntry 2 }

    necWimaxBsIfmCapCfgHoIndTimer OBJECT-TYPE
        SYNTAX              Integer32
        UNITS               "s"
        MAX-ACCESS          read-only
        STATUS              current
        DESCRIPTION         "Time that HO starting request is not allowed after
                            HO-RSP is recieved at BS initiated HO."
        ::= { necWimaxBsIfmCapabilitiesConfigEntry 3 }

    necWimaxBsIfmCapCfgHoTrigFunction OBJECT-TYPE
        SYNTAX              Integer32 (0..7)
        MAX-ACCESS          read-write
        STATUS              current
        DESCRIPTION         "Trigger condition of metric. 0x0: Reserved 0x1:
                            Metric of neighbor BS is greater than absolute
                            value 0x2: Metric of neighbor BS is less than
                            absolute value 0x3: Metric of neighbor BS is
                            greater than serving BS metric by relative value
                            0x4: Metric of neighbor BS is less than serving
                            BS metric by relative value 0x5: Metric of serving
                            BS greater than absolute value 0x6: Metric of
                            serving BS less than absolute value 0x7: Reserved"
        ::= { necWimaxBsIfmCapabilitiesConfigEntry 4 }

    necWimaxBsIfmConfigurationsTable OBJECT-TYPE
        SYNTAX              SEQUENCE OF NecWimaxBsIfmConfigurationsEntry
        MAX-ACCESS          not-accessible
        STATUS              current
        DESCRIPTION         "configurations of mobility function"
        ::= { necWimaxBsIfmCm 2 }

    necWimaxBsIfmConfigurationsEntry OBJECT-TYPE
        SYNTAX              NecWimaxBsIfmConfigurationsEntry
        MAX-ACCESS          not-accessible
        STATUS              current
        DESCRIPTION         "indexed by ifIndex"
        INDEX               {
                                ifIndex
                            }
        ::= { necWimaxBsIfmConfigurationsTable 1 }

    NecWimaxBsIfmConfigurationsEntry ::= SEQUENCE {
        necWimaxBsIfmReqDuration
            Integer32,
        necWimaxBsIfmPagingRetry
            Integer32,
        necWimaxBsIfmMobPagAdvTransmitCount
            Integer32
    }

    necWimaxBsIfmReqDuration OBJECT-TYPE
        SYNTAX              Integer32 (0..255)
        MAX-ACCESS          read-write
        STATUS              current
        DESCRIPTION         "wait time after DREG-CMD required MS initiate
                            idle mode"
        ::= { necWimaxBsIfmConfigurationsEntry 2 }

    necWimaxBsIfmPagingRetry OBJECT-TYPE
        SYNTAX              Integer32 (0..16)
        MAX-ACCESS          read-write
        STATUS              current
        DESCRIPTION         "max retry count of MOB-PAG-ADV"
        ::= { necWimaxBsIfmConfigurationsEntry 3 }

    necWimaxBsIfmMobPagAdvTransmitCount OBJECT-TYPE
        SYNTAX              Integer32 (0..255)
        UNITS               "flame"
        MAX-ACCESS          read-write
        STATUS              current
        DESCRIPTION         "advance transmit timing of MOB-PAG-ADV"
        ::= { necWimaxBsIfmConfigurationsEntry 4 }

    necWimaxBsMobHoObjects OBJECT IDENTIFIER ::= { necWimaxBsIfmObjects 2 }

    necWimaxBsMobHcConfigurationsTable OBJECT-TYPE
        SYNTAX              SEQUENCE OF NecWimaxBsMobHcConfigurationsEntry
        MAX-ACCESS          not-accessible
        STATUS              current
        DESCRIPTION         "configurations of mobirity handover functoin"
        ::= { necWimaxBsMobHoObjects 1 }

    necWimaxBsMobHcConfigurationsEntry OBJECT-TYPE
        SYNTAX              NecWimaxBsMobHcConfigurationsEntry
        MAX-ACCESS          not-accessible
        STATUS              current
        DESCRIPTION         "indexed by ifIndex."
        INDEX               {
                                ifIndex
                            }
        ::= { necWimaxBsMobHcConfigurationsTable 1 }

    NecWimaxBsMobHcConfigurationsEntry ::= SEQUENCE {
        necWimaxBsMobHcCfgHoMode
            INTEGER,
        necWimaxBsMobHcCfgUnsGrantHoind
            INTEGER,
        necWimaxBsMobHcCfgFastRanging
            INTEGER,
        necWimaxBsMobHcCfgActTime
            Integer32,
        necWimaxBsMobHcCfgT55
            Integer32,
        necWimaxBsMobHcCfgRscRetain
            INTEGER,
        necWimaxBsMobHcCfgTgtBsSelection
            INTEGER,
        necWimaxBsMobHcCfgRecmdTgtBs
            OCTET STRING,
        necWimaxBsMobHcCfgThrsldFixed
            Integer32,
        necWimaxBsMobHcCfgThrsldAuto
            Integer32,
        necWimaxBsMobHcCfgPreRegAging
            Unsigned32,
        necWimaxBsMobHcCfgCidUpdateType
            INTEGER,
        necWimaxBsMobHcCfgSysRscRetainTime
            Integer32,
        necWimaxBsMobHcCfgFaIndex
            Integer32,
        necWimaxBsMobNbrAdvFragmentSize
            Integer32
    }

    necWimaxBsMobHcCfgHoMode OBJECT-TYPE
        SYNTAX              INTEGER {
                                msInit( 0 ),
                                bsInit( 1 )
                            }
        MAX-ACCESS          read-write
        STATUS              current
        DESCRIPTION         "HO mode. MS-initiate or BS-initiate"
        ::= { necWimaxBsMobHcConfigurationsEntry 1 }

    necWimaxBsMobHcCfgUnsGrantHoind OBJECT-TYPE
        SYNTAX              INTEGER {
                                noUnsAllocHoind( 0 ),
                                unsAllocHoind( 1 )
                            }
        MAX-ACCESS          read-write
        STATUS              current
        DESCRIPTION         "UNS Alloc for HO-IND or not"
        ::= { necWimaxBsMobHcConfigurationsEntry 2 }

    necWimaxBsMobHcCfgFastRanging OBJECT-TYPE
        SYNTAX              INTEGER {
                                noFastRanging( 0 ),
                                fastRanging( 1 )
                            }
        MAX-ACCESS          read-write
        STATUS              current
        DESCRIPTION         "do Fast Ranging or not at HO re-entry"
        ::= { necWimaxBsMobHcConfigurationsEntry 3 }

    necWimaxBsMobHcCfgActTime OBJECT-TYPE
        SYNTAX              Integer32 (0..255)
        MAX-ACCESS          read-write
        STATUS              current
        DESCRIPTION         "actoin time for target BS"
        ::= { necWimaxBsMobHcConfigurationsEntry 4 }

    necWimaxBsMobHcCfgT55 OBJECT-TYPE
        SYNTAX              Integer32 (0..65535)
        UNITS               "frames"
        MAX-ACCESS          read-write
        STATUS              current
        DESCRIPTION         "T55(defval=200)"
        ::= { necWimaxBsMobHcConfigurationsEntry 5 }

    necWimaxBsMobHcCfgRscRetain OBJECT-TYPE
        SYNTAX              INTEGER {
                                release( 0 ),
                                retain( 1 )
                            }
        MAX-ACCESS          read-write
        STATUS              current
        DESCRIPTION         "indicate serving BS retain connection information
                            after HO. 0:release connection information, 1:retain
                            connection information"
        ::= { necWimaxBsMobHcConfigurationsEntry 6 }

    necWimaxBsMobHcCfgTgtBsSelection OBJECT-TYPE
        SYNTAX              INTEGER {
                                auto( 0 ),
                                fixed( 1 )
                            }
        MAX-ACCESS          read-write
        STATUS              current
        DESCRIPTION         "target BS selection method"
        ::= { necWimaxBsMobHcConfigurationsEntry 7 }

    necWimaxBsMobHcCfgRecmdTgtBs OBJECT-TYPE
        SYNTAX              OCTET STRING (SIZE(6))
        MAX-ACCESS          read-write
        STATUS              current
        DESCRIPTION         "Recommended Neighbor BS in case of fixed BS selection"
        ::= { necWimaxBsMobHcConfigurationsEntry 8 }

    necWimaxBsMobHcCfgThrsldFixed OBJECT-TYPE
        SYNTAX              Integer32 (-128..127)
        UNITS               "0.5dB"
        MAX-ACCESS          read-write
        STATUS              current
        DESCRIPTION         "(IMMIDIATE) threshold DL CINR to trigger BS initiate
                            HO in case of fixed BS selection."
        ::= { necWimaxBsMobHcConfigurationsEntry 9 }

    necWimaxBsMobHcCfgThrsldAuto OBJECT-TYPE
        SYNTAX              Integer32 (-128..127)
        UNITS               "0.5dB"
        MAX-ACCESS          read-write
        STATUS              current
        DESCRIPTION         "(IMMIDIATE) threshold CINR to select target BSs
                            for BS initiate HO in case of auto BS selection."
        ::= { necWimaxBsMobHcConfigurationsEntry 10 }

    necWimaxBsMobHcCfgPreRegAging OBJECT-TYPE
        SYNTAX              Unsigned32
        MAX-ACCESS          read-write
        STATUS              current
        DESCRIPTION         "aging timer for DP-DREG transmittion between PRE-REG
                            and DP-REG. value 0 means no aging"
        ::= { necWimaxBsMobHcConfigurationsEntry 11 }

    necWimaxBsMobHcCfgCidUpdateType OBJECT-TYPE
        SYNTAX              INTEGER {
                                normal( 0 ),
                                compressed( 1 )
                            }
        MAX-ACCESS          read-write
        STATUS              current
        DESCRIPTION         "switch normal CID update and compressed CID update"
        ::= { necWimaxBsMobHcConfigurationsEntry 12 }

    necWimaxBsMobHcCfgSysRscRetainTime OBJECT-TYPE
        SYNTAX              Integer32 (0..65535)
        MAX-ACCESS          read-write
        STATUS              current
        DESCRIPTION         "use this value in case of no Resource-Retain-Time
                            TLV of this value = 0"
        ::= { necWimaxBsMobHcConfigurationsEntry 13 }

    necWimaxBsMobHcCfgFaIndex OBJECT-TYPE
        SYNTAX              Integer32 (0..255)
        MAX-ACCESS          read-write
        STATUS              current
        DESCRIPTION         "FA Index corresponding to Frequency is set. Default
                            = 0"
        ::= { necWimaxBsMobHcConfigurationsEntry 14 }

    necWimaxBsMobNbrAdvFragmentSize OBJECT-TYPE
        SYNTAX              Integer32 (0..65535)
        MAX-ACCESS          read-write
        STATUS              current
        DESCRIPTION         "MOB_NBR_ADV message max size"
        ::= { necWimaxBsMobHcConfigurationsEntry 15 }

    necWimaxBsMobScanObjects OBJECT IDENTIFIER ::= { necWimaxBsIfmObjects 3 }

    necWimaxBsMobScConfigurationsTable OBJECT-TYPE
        SYNTAX              SEQUENCE OF NecWimaxBsMobScConfigurationsEntry
        MAX-ACCESS          not-accessible
        STATUS              current
        DESCRIPTION         "Please replace this text with your description."
        ::= { necWimaxBsMobScanObjects 1 }

    necWimaxBsMobScConfigurationsEntry OBJECT-TYPE
        SYNTAX              NecWimaxBsMobScConfigurationsEntry
        MAX-ACCESS          not-accessible
        STATUS              current
        DESCRIPTION         "indexed by ifIndex"
        INDEX               {
                                ifIndex
                            }
        ::= { necWimaxBsMobScConfigurationsTable 1 }

    NecWimaxBsMobScConfigurationsEntry ::= SEQUENCE {
        necWimaxBsMobScCnfRptMode
            INTEGER,
        necWimaxBsMobScCnfRptPeriod
            Integer32,
        necWimaxBsMobScCnfRptMetric
            BITS,
        necWimaxBsMobScCnfDuration
            Integer32,
        necWimaxBsMobScCnfInterleavingInterval
            Integer32,
        necWimaxBsMobScCnfIteratoin
            Integer32,
        necWimaxBsMobScCnfTrigValReq
            Integer32,
        necWimaxBsMobScCnfTrigAveDurationReq
            Integer32,
        necWimaxBsMobScCnfTrigTypeReq
            INTEGER,
        necWimaxBsMobScCnfTrigFuncReq
            INTEGER,
        necWimaxBsMobScCnfTrigValRep
            Integer32,
        necWimaxBsMobScCnfTrigAveDurationRep
            Integer32,
        necWimaxBsMobScCnfTrigTypeRep
            INTEGER,
        necWimaxBsMobScCnfTrigFuncRep
            INTEGER,
        necWimaxBsMobScCnfSleepReact
            INTEGER
    }

    necWimaxBsMobScCnfRptMode OBJECT-TYPE
        SYNTAX              INTEGER {
                                none( 0 ),
                                periodic( 1 ),
                                eventtrigger( 2 )
                            }
        MAX-ACCESS          read-write
        STATUS              current
        DESCRIPTION         "(IMMIDIATE) reporting method of scan result"
        ::= { necWimaxBsMobScConfigurationsEntry 1 }

    necWimaxBsMobScCnfRptPeriod OBJECT-TYPE
        SYNTAX              Integer32 (1..255)
        MAX-ACCESS          read-write
        STATUS              current
        DESCRIPTION         "(IMMIDIATE) reporting period of scan result"
        ::= { necWimaxBsMobScConfigurationsEntry 2 }

    necWimaxBsMobScCnfRptMetric OBJECT-TYPE
        SYNTAX              BITS {
                                cinrmean( 0 ),
                                rssimean( 1 ),
                                delay( 2 ),
                                rtd( 3 )
                            }
        MAX-ACCESS          read-write
        STATUS              current
        DESCRIPTION         "(IMMIDIATE) reporting metrics of scan result"
        ::= { necWimaxBsMobScConfigurationsEntry 3 }

    necWimaxBsMobScCnfDuration OBJECT-TYPE
        SYNTAX              Integer32 (0..255)
        MAX-ACCESS          read-write
        STATUS              current
        DESCRIPTION         "(IMMIDIATE) scan duration"
        ::= { necWimaxBsMobScConfigurationsEntry 4 }

    necWimaxBsMobScCnfInterleavingInterval OBJECT-TYPE
        SYNTAX              Integer32 (0..255)
        MAX-ACCESS          read-write
        STATUS              current
        DESCRIPTION         "(IMMIDIATE) scan interlaving interval"
        ::= { necWimaxBsMobScConfigurationsEntry 5 }

    necWimaxBsMobScCnfIteratoin OBJECT-TYPE
        SYNTAX              Integer32 (0..255)
        MAX-ACCESS          read-write
        STATUS              current
        DESCRIPTION         "(IMMIDIATE) scan iteratoin"
        ::= { necWimaxBsMobScConfigurationsEntry 6 }

    necWimaxBsMobScCnfTrigValReq OBJECT-TYPE
        SYNTAX              Integer32 (0..255)
        MAX-ACCESS          read-write
        STATUS              current
        DESCRIPTION         "reference trigger value SCN-REQ"
        ::= { necWimaxBsMobScConfigurationsEntry 7 }

    necWimaxBsMobScCnfTrigAveDurationReq OBJECT-TYPE
        SYNTAX              Integer32 (0..255)
        UNITS               "frames"
        MAX-ACCESS          read-write
        STATUS              current
        DESCRIPTION         "duration for mean calculation SCN-REQ"
        ::= { necWimaxBsMobScConfigurationsEntry 8 }

    necWimaxBsMobScCnfTrigTypeReq OBJECT-TYPE
        SYNTAX              INTEGER {
                                cinr( 0 ),
                                rssi( 1 ),
                                rtd( 2 )
                            }
        MAX-ACCESS          read-write
        STATUS              current
        DESCRIPTION         "metric type to trigger HO SCN-REQ"
        ::= { necWimaxBsMobScConfigurationsEntry 9 }

    necWimaxBsMobScCnfTrigFuncReq OBJECT-TYPE
        SYNTAX              INTEGER {
                                neighborGreaterAbsolute( 1 ),
                                neighborLessAbsolute( 2 ),
                                neighborGreaterServing( 3 ),
                                neighborLessServing( 4 ),
                                servingGreaterAbsolute( 5 ),
                                servingLessAbsolute( 6 )
                            }
        MAX-ACCESS          read-write
        STATUS              current
        DESCRIPTION         "metric trigger function HO SCN-REQ"
        ::= { necWimaxBsMobScConfigurationsEntry 10 }

    necWimaxBsMobScCnfTrigValRep OBJECT-TYPE
        SYNTAX              Integer32 (0..255)
        MAX-ACCESS          read-write
        STATUS              current
        DESCRIPTION         "reference trigger value SCN-REP"
        ::= { necWimaxBsMobScConfigurationsEntry 11 }

    necWimaxBsMobScCnfTrigAveDurationRep OBJECT-TYPE
        SYNTAX              Integer32 (0..255)
        UNITS               "frames"
        MAX-ACCESS          read-write
        STATUS              current
        DESCRIPTION         "duration for mean calculation SCN-REP"
        ::= { necWimaxBsMobScConfigurationsEntry 12 }

    necWimaxBsMobScCnfTrigTypeRep OBJECT-TYPE
        SYNTAX              INTEGER {
                                cinr( 0 ),
                                rssi( 1 ),
                                rtd( 2 )
                            }
        MAX-ACCESS          read-write
        STATUS              current
        DESCRIPTION         "metric type to trigger HO SCN-REP"
        ::= { necWimaxBsMobScConfigurationsEntry 13 }

    necWimaxBsMobScCnfTrigFuncRep OBJECT-TYPE
        SYNTAX              INTEGER {
                                neighborGreaterAbsolute( 1 ),
                                neighborLessAbsolute( 2 ),
                                neighborGreaterServing( 3 ),
                                neighborLessServing( 4 ),
                                servingGreaterAbsolute( 5 ),
                                servingLessAbsolute( 6 )
                            }
        MAX-ACCESS          read-write
        STATUS              current
        DESCRIPTION         "metric trigger function HO SCN-REP"
        ::= { necWimaxBsMobScConfigurationsEntry 14 }

    necWimaxBsMobScCnfSleepReact OBJECT-TYPE
        SYNTAX              INTEGER {
                                disable( 0 ),
                                enable( 1 )
                            }
        MAX-ACCESS          read-write
        STATUS              current
        DESCRIPTION         "This indicate if Sleep Mode Reactivation is addmitted
                            or not after SCAN completed"
        ::= { necWimaxBsMobScConfigurationsEntry 15 }

    necWimaxBsMobSleepModeObjects OBJECT IDENTIFIER ::= { necWimaxBsIfmObjects 4 }

    necWimaxBsMobSmConfigurationsTable OBJECT-TYPE
        SYNTAX              SEQUENCE OF NecWimaxBsMobSmConfigurationsEntry
        MAX-ACCESS          not-accessible
        STATUS              current
        DESCRIPTION         "sleep mode configurations"
        ::= { necWimaxBsMobSleepModeObjects 1 }

    necWimaxBsMobSmConfigurationsEntry OBJECT-TYPE
        SYNTAX              NecWimaxBsMobSmConfigurationsEntry
        MAX-ACCESS          not-accessible
        STATUS              current
        DESCRIPTION         "indexed by ifIndex"
        INDEX               {
                                ifIndex
                            }
        ::= { necWimaxBsMobSmConfigurationsTable 1 }

    NecWimaxBsMobSmConfigurationsEntry ::= SEQUENCE {
        necWimaxBsMobSmCnfTrfIndRequired
            INTEGER,
        necWimaxBsMobSmCnfTrafficTriggeredWakening
            INTEGER,
        necWimaxBsMobSmCnfTrfIndSlpidFormat
            INTEGER,
        necWimaxBsMobSmCnfEnabledActionTriggered
            Integer32,
        necWimaxBsMobSmCnfReqDuration
            Integer32
    }

    necWimaxBsMobSmCnfTrfIndRequired OBJECT-TYPE
        SYNTAX              INTEGER {
                                required1( 0 ),
                                required2( 1 )
                            }
        MAX-ACCESS          read-write
        STATUS              current
        DESCRIPTION         "indicate MOB-TRF-IND is required or not value
                            meaning is unknown"
        ::= { necWimaxBsMobSmConfigurationsEntry 1 }

    necWimaxBsMobSmCnfTrafficTriggeredWakening OBJECT-TYPE
        SYNTAX              INTEGER {
                                notdeactivate( 0 ),
                                deactivate( 1 )
                            }
        MAX-ACCESS          read-write
        STATUS              current
        DESCRIPTION         "0 = Power Saving Class shall not be deactivated
                            if traffic appears at the connection as per 6.3.19.2.
                            1 = Power Saving Class shall be deactivated if
                            traffic appears at the connection as 6.3.19.2."
        ::= { necWimaxBsMobSmConfigurationsEntry 2 }

    necWimaxBsMobSmCnfTrfIndSlpidFormat OBJECT-TYPE
        SYNTAX              INTEGER {
                                bitmap( 0 ),
                                list( 1 )
                            }
        MAX-ACCESS          read-write
        STATUS              current
        DESCRIPTION         "format of MOB-TRF-IND SLPID"
        ::= { necWimaxBsMobSmConfigurationsEntry 3 }

    necWimaxBsMobSmCnfEnabledActionTriggered OBJECT-TYPE
        SYNTAX              Integer32 (0..7)
        MAX-ACCESS          read-write
        STATUS              current
        DESCRIPTION         "Enabled action in Sleep Mode. BIT#0:MOB_SCN-REP
                            BIT#1:MOB_MSHO-REQ BIT#2:MOB_SCN-REQ"
        ::= { necWimaxBsMobSmConfigurationsEntry 4 }

    necWimaxBsMobSmCnfReqDuration OBJECT-TYPE
        SYNTAX              Integer32 (0..255)
        UNITS               "frames"
        MAX-ACCESS          read-write
        STATUS              current
        DESCRIPTION         "MOB_SLP-REQ retry interval"
        ::= { necWimaxBsMobSmConfigurationsEntry 5 }

    necWimaxBsMobConfigurationsTable OBJECT-TYPE
        SYNTAX              SEQUENCE OF NecWimaxBsMobConfigurationsEntry
        MAX-ACCESS          not-accessible
        STATUS              current
        DESCRIPTION         "configuration of mobility function"
        ::= { necWimaxBsIfmObjects 5 }

    necWimaxBsMobConfigurationsEntry OBJECT-TYPE
        SYNTAX              NecWimaxBsMobConfigurationsEntry
        MAX-ACCESS          not-accessible
        STATUS              current
        DESCRIPTION         "indexed by ifIndex"
        INDEX               {
                                ifIndex
                            }
        ::= { necWimaxBsMobConfigurationsTable 1 }

    NecWimaxBsMobConfigurationsEntry ::= SEQUENCE {
        necWimaxBsMobCfgComMonTimer
            Unsigned32
    }

    necWimaxBsMobCfgComMonTimer OBJECT-TYPE
        SYNTAX              Unsigned32
        MAX-ACCESS          read-write
        STATUS              current
        DESCRIPTION         "timer value to disconnect MS which does not communicate.
                            the value 0 means no monitoring"
        ::= { necWimaxBsMobConfigurationsEntry 1 }

    necWimaxBsPmObjects OBJECT IDENTIFIER ::= { necWimaxBsIfmObjects 6 }

    necWimaxBsPmThroughputTable OBJECT-TYPE
        SYNTAX              SEQUENCE OF NecWimaxBsPmThroughputEntry
        MAX-ACCESS          not-accessible
        STATUS              current
        DESCRIPTION         "throughput"
        ::= { necWimaxBsPmObjects 1 }

    necWimaxBsPmThroughputEntry OBJECT-TYPE
        SYNTAX              NecWimaxBsPmThroughputEntry
        MAX-ACCESS          not-accessible
        STATUS              current
        DESCRIPTION         "indexed by ifIndex"
        INDEX               {
                                ifIndex
                            }
        ::= { necWimaxBsPmThroughputTable 1 }

    NecWimaxBsPmThroughputEntry ::= SEQUENCE {
        necWimaxBsPmCurrentDlThroughputPdu
            Integer32,
        necWimaxBsPmCurrentDlThroughputSdu
            Integer32,
        necWimaxBsPmCurrentDlThroughputIp
            Integer32,
        necWimaxBsPmCurrentUlThroughputPdu
            Integer32,
        necWimaxBsPmCurrentUlThroughputSdu
            Integer32,
        necWimaxBsPmCurrentUlThroughputIp
            Integer32,
        necWimaxBsPmDlThroughputPduCounter
            Counter64,
        necWimaxBsPmDlThroughputSduCounter
            Counter64,
        necWimaxBsPmDlThroughputIpCounter
            Counter64,
        necWimaxBsPmUlThroughputPduCounter
            Counter64,
        necWimaxBsPmUlThroughputSduCounter
            Counter64,
        necWimaxBsPmUlThroughputIpCounter
            Counter64,
        necWimaxBsThroughputResetCounter
            INTEGER
    }

    necWimaxBsPmCurrentDlThroughputPdu OBJECT-TYPE
        SYNTAX              Integer32
        MAX-ACCESS          read-only
        STATUS              current
        DESCRIPTION         "Current downlink throughput of Phy."
        ::= { necWimaxBsPmThroughputEntry 1 }

    necWimaxBsPmCurrentDlThroughputSdu OBJECT-TYPE
        SYNTAX              Integer32
        MAX-ACCESS          read-only
        STATUS              current
        DESCRIPTION         "Current downlink throughput of MAC."
        ::= { necWimaxBsPmThroughputEntry 2 }

    necWimaxBsPmCurrentDlThroughputIp OBJECT-TYPE
        SYNTAX              Integer32
        MAX-ACCESS          read-only
        STATUS              current
        DESCRIPTION         "Current downlink throughput of IP."
        ::= { necWimaxBsPmThroughputEntry 3 }

    necWimaxBsPmCurrentUlThroughputPdu OBJECT-TYPE
        SYNTAX              Integer32
        MAX-ACCESS          read-only
        STATUS              current
        DESCRIPTION         "Current uplink throughput of PHY."
        ::= { necWimaxBsPmThroughputEntry 4 }

    necWimaxBsPmCurrentUlThroughputSdu OBJECT-TYPE
        SYNTAX              Integer32
        MAX-ACCESS          read-only
        STATUS              current
        DESCRIPTION         "Current uplink throughput of MAC."
        ::= { necWimaxBsPmThroughputEntry 5 }

    necWimaxBsPmCurrentUlThroughputIp OBJECT-TYPE
        SYNTAX              Integer32
        MAX-ACCESS          read-only
        STATUS              current
        DESCRIPTION         "Current uplink throughput of IP."
        ::= { necWimaxBsPmThroughputEntry 6 }

    necWimaxBsPmDlThroughputPduCounter OBJECT-TYPE
        SYNTAX              Counter64
        MAX-ACCESS          read-only
        STATUS              current
        DESCRIPTION         "Cumulative downlink throughput of PHY."
        ::= { necWimaxBsPmThroughputEntry 7 }

    necWimaxBsPmDlThroughputSduCounter OBJECT-TYPE
        SYNTAX              Counter64
        MAX-ACCESS          read-only
        STATUS              current
        DESCRIPTION         "Cumulative downlink throughput of SDU."
        ::= { necWimaxBsPmThroughputEntry 8 }

    necWimaxBsPmDlThroughputIpCounter OBJECT-TYPE
        SYNTAX              Counter64
        MAX-ACCESS          read-only
        STATUS              current
        DESCRIPTION         "Cumulative downlink throughput of IP."
        ::= { necWimaxBsPmThroughputEntry 9 }

    necWimaxBsPmUlThroughputPduCounter OBJECT-TYPE
        SYNTAX              Counter64
        MAX-ACCESS          read-only
        STATUS              current
        DESCRIPTION         "Cumulative uplink throughput of PHY."
        ::= { necWimaxBsPmThroughputEntry 10 }

    necWimaxBsPmUlThroughputSduCounter OBJECT-TYPE
        SYNTAX              Counter64
        MAX-ACCESS          read-only
        STATUS              current
        DESCRIPTION         "Cumulative uplink throughput of MAC."
        ::= { necWimaxBsPmThroughputEntry 11 }

    necWimaxBsPmUlThroughputIpCounter OBJECT-TYPE
        SYNTAX              Counter64
        MAX-ACCESS          read-only
        STATUS              current
        DESCRIPTION         "Cumulative uplink throughput of Ip."
        ::= { necWimaxBsPmThroughputEntry 12 }

    necWimaxBsThroughputResetCounter OBJECT-TYPE
        SYNTAX              INTEGER {
                                null( 0 ),
                                resetCounter( 1 )
                            }
        MAX-ACCESS          read-write
        STATUS              current
        DESCRIPTION         "reset ALL Throughput Counter."
        ::= { necWimaxBsPmThroughputEntry 13 }

    necWimaxBsPmRrmTable OBJECT-TYPE
        SYNTAX              SEQUENCE OF NecWimaxBsPmRrmEntry
        MAX-ACCESS          not-accessible
        STATUS              current
        DESCRIPTION         "Empty information on band."
        ::= { necWimaxBsPmObjects 2 }

    necWimaxBsPmRrmEntry OBJECT-TYPE
        SYNTAX              NecWimaxBsPmRrmEntry
        MAX-ACCESS          not-accessible
        STATUS              current
        DESCRIPTION         "indexed by ifIndex."
        INDEX               {
                                ifIndex
                            }
        ::= { necWimaxBsPmRrmTable 1 }

    NecWimaxBsPmRrmEntry ::= SEQUENCE {
        necWimaxBsPmRrmDl
            Integer32,
        necWimaxBsPmRrmUl
            Integer32,
        necWimaxBsPmReservDl
            Integer32,
        necWimaxBsPmReservUl
            Integer32,
        necWimaxBsPmUsedBandDlUgs
            Integer32,
        necWimaxBsPmUsedBandDlErtvr
            Integer32,
        necWimaxBsPmUsedBandDlRtvr
            Integer32,
        necWimaxBsPmUsedBandDlNrtvr
            Integer32,
        necWimaxBsPmUsedBandDlBe
            Integer32,
        necWimaxBsPmUsedBandUlUgs
            Integer32,
        necWimaxBsPmUsedBandUlErtps
            Integer32,
        necWimaxBsPmUsedBandUlRtps
            Integer32,
        necWimaxBsPmUsedBandUlNrtps
            Integer32,
        necWimaxBsPmUsedBandUlBe
            Integer32,
        necWimaxBsPmReservDlUgs
            Integer32,
        necWimaxBsPmReservDlErtvr
            Integer32,
        necWimaxBsPmReservDlRtvr
            Integer32,
        necWimaxBsPmReservDlNrtvr
            Integer32,
        necWimaxBsPmReservUlUgs
            Integer32,
        necWimaxBsPmReservUlErtps
            Integer32,
        necWimaxBsPmReservUlRtps
            Integer32,
        necWimaxBsPmReservUlNrtps
            Integer32
    }

    necWimaxBsPmRrmDl OBJECT-TYPE
        SYNTAX              Integer32
        MAX-ACCESS          read-only
        STATUS              current
        DESCRIPTION         "Empty band information on Downlink."
        ::= { necWimaxBsPmRrmEntry 1 }

    necWimaxBsPmRrmUl OBJECT-TYPE
        SYNTAX              Integer32
        MAX-ACCESS          read-only
        STATUS              current
        DESCRIPTION         "Empty band information on Uplink."
        ::= { necWimaxBsPmRrmEntry 2 }

    necWimaxBsPmReservDl OBJECT-TYPE
        SYNTAX              Integer32 (0..100)
        MAX-ACCESS          read-only
        STATUS              current
        DESCRIPTION         "Reserved band information on Downlink. represent
                            by %"
        ::= { necWimaxBsPmRrmEntry 3 }

    necWimaxBsPmReservUl OBJECT-TYPE
        SYNTAX              Integer32 (0..100)
        MAX-ACCESS          read-only
        STATUS              current
        DESCRIPTION         "Reserved band information on Uplink. represent
                            by %"
        ::= { necWimaxBsPmRrmEntry 4 }

    necWimaxBsPmUsedBandDlUgs OBJECT-TYPE
        SYNTAX              Integer32 (0..100)
        MAX-ACCESS          read-only
        STATUS              current
        DESCRIPTION         "Used band information on Downlink UGS. represent
                            by %"
        ::= { necWimaxBsPmRrmEntry 5 }

    necWimaxBsPmUsedBandDlErtvr OBJECT-TYPE
        SYNTAX              Integer32 (0..100)
        MAX-ACCESS          read-only
        STATUS              current
        DESCRIPTION         "Used band information on Downlink ERTVR. represent
                            by %"
        ::= { necWimaxBsPmRrmEntry 6 }

    necWimaxBsPmUsedBandDlRtvr OBJECT-TYPE
        SYNTAX              Integer32 (0..100)
        MAX-ACCESS          read-only
        STATUS              current
        DESCRIPTION         "Used band information on Downlink RTVR. represent
                            by %"
        ::= { necWimaxBsPmRrmEntry 7 }

    necWimaxBsPmUsedBandDlNrtvr OBJECT-TYPE
        SYNTAX              Integer32 (0..100)
        MAX-ACCESS          read-only
        STATUS              current
        DESCRIPTION         "Used band information on Downlink NRTVR. represent
                            by %"
        ::= { necWimaxBsPmRrmEntry 8 }

    necWimaxBsPmUsedBandDlBe OBJECT-TYPE
        SYNTAX              Integer32 (0..100)
        MAX-ACCESS          read-only
        STATUS              current
        DESCRIPTION         "Used band information on Downlink BE. represent
                            by %"
        ::= { necWimaxBsPmRrmEntry 9 }

    necWimaxBsPmUsedBandUlUgs OBJECT-TYPE
        SYNTAX              Integer32 (0..100)
        MAX-ACCESS          read-only
        STATUS              current
        DESCRIPTION         "Used band information on Uplink UGS. represent
                            by %"
        ::= { necWimaxBsPmRrmEntry 10 }

    necWimaxBsPmUsedBandUlErtps OBJECT-TYPE
        SYNTAX              Integer32 (0..100)
        MAX-ACCESS          read-only
        STATUS              current
        DESCRIPTION         "Used band information on Uplink ertPS. represent
                            by %"
        ::= { necWimaxBsPmRrmEntry 11 }

    necWimaxBsPmUsedBandUlRtps OBJECT-TYPE
        SYNTAX              Integer32 (0..100)
        MAX-ACCESS          read-only
        STATUS              current
        DESCRIPTION         "Used band information on Uplink rtPS. represent
                            by %"
        ::= { necWimaxBsPmRrmEntry 12 }

    necWimaxBsPmUsedBandUlNrtps OBJECT-TYPE
        SYNTAX              Integer32 (0..100)
        MAX-ACCESS          read-only
        STATUS              current
        DESCRIPTION         "Used band information on Uplink nrtPS. represent
                            by %"
        ::= { necWimaxBsPmRrmEntry 13 }

    necWimaxBsPmUsedBandUlBe OBJECT-TYPE
        SYNTAX              Integer32 (0..100)
        MAX-ACCESS          read-only
        STATUS              current
        DESCRIPTION         "Used band information on Uplink BE. represent
                            by %"
        ::= { necWimaxBsPmRrmEntry 14 }

    necWimaxBsPmReservDlUgs OBJECT-TYPE
        SYNTAX              Integer32 (0..100)
        MAX-ACCESS          read-only
        STATUS              current
        DESCRIPTION         "Reserved band information on Downlink UGS. represent
                            by %"
        ::= { necWimaxBsPmRrmEntry 15 }

    necWimaxBsPmReservDlErtvr OBJECT-TYPE
        SYNTAX              Integer32 (0..100)
        MAX-ACCESS          read-only
        STATUS              current
        DESCRIPTION         "Reserved band information on Downlink ERTVR. represent
                            by %"
        ::= { necWimaxBsPmRrmEntry 16 }

    necWimaxBsPmReservDlRtvr OBJECT-TYPE
        SYNTAX              Integer32 (0..100)
        MAX-ACCESS          read-only
        STATUS              current
        DESCRIPTION         "Reserved band information on Downlink RTVR. represent
                            by %"
        ::= { necWimaxBsPmRrmEntry 17 }

    necWimaxBsPmReservDlNrtvr OBJECT-TYPE
        SYNTAX              Integer32 (0..100)
        MAX-ACCESS          read-only
        STATUS              current
        DESCRIPTION         "Reserved band information on Downlink NRTVR. represent
                            by %"
        ::= { necWimaxBsPmRrmEntry 18 }

    necWimaxBsPmReservUlUgs OBJECT-TYPE
        SYNTAX              Integer32 (0..100)
        MAX-ACCESS          read-only
        STATUS              current
        DESCRIPTION         "Reserved band information on Uplink UGS. represent
                            by %"
        ::= { necWimaxBsPmRrmEntry 19 }

    necWimaxBsPmReservUlErtps OBJECT-TYPE
        SYNTAX              Integer32 (0..100)
        MAX-ACCESS          read-only
        STATUS              current
        DESCRIPTION         "Reserved band information on Uplink ertPS. represent
                            by %"
        ::= { necWimaxBsPmRrmEntry 20 }

    necWimaxBsPmReservUlRtps OBJECT-TYPE
        SYNTAX              Integer32 (0..100)
        MAX-ACCESS          read-only
        STATUS              current
        DESCRIPTION         "Reserved band information on Uplink rtPS. represent
                            by %"
        ::= { necWimaxBsPmRrmEntry 21 }

    necWimaxBsPmReservUlNrtps OBJECT-TYPE
        SYNTAX              Integer32 (0..100)
        MAX-ACCESS          read-only
        STATUS              current
        DESCRIPTION         "Reserved band information on Uplink nrtPS. represent
                            by %"
        ::= { necWimaxBsPmRrmEntry 22 }

    necWimaxBsPmStatTable OBJECT-TYPE
        SYNTAX              SEQUENCE OF NecWimaxBsPmStatEntry
        MAX-ACCESS          not-accessible
        STATUS              current
        DESCRIPTION         "Statistics Information"
        ::= { necWimaxBsPmObjects 3 }

    necWimaxBsPmStatEntry OBJECT-TYPE
        SYNTAX              NecWimaxBsPmStatEntry
        MAX-ACCESS          not-accessible
        STATUS              current
        DESCRIPTION         "Please replace this text with your description."
        INDEX               {
                                ifIndex
                            }
        ::= { necWimaxBsPmStatTable 1 }

    NecWimaxBsPmStatEntry ::= SEQUENCE {
        necWimaxBsStatMsNo
            Integer32,
        necWimaxBsStatUlSduUsr
            Counter64,
        necWimaxBsStatUlSduManage
            Counter64,
        necWimaxBsStatUlPdu
            Counter64,
        necWimaxBsStatUlSignaling
            Counter64,
        necWimaxBsStatUlCrcError
            Counter64,
        necWimaxBsStatUlDecryptError
            Counter64,
        necWimaxBsStatDlSduUsr
            Counter64,
        necWimaxBsStatDlSduManage
            Counter64,
        necWimaxBsStatDlPdu
            Counter64,
        necWimaxBsStatDlDiscardedSdu
            Counter64,
        necWimaxBsStatDlArqRetry
            Counter64,
        necWimaxBsStatDlArqRetryOver
            Counter64,
        necWimaxBsStatDlHarqRetry
            Counter64,
        necWimaxBsStatDlHarqRetryOver
            Counter64,
        necWimaxBsStatResetCounter
            INTEGER,
        necWimaxBsStatUlHarqRetry
            Counter64,
        necWimaxBsStatUlHarqRetryOver
            Counter64
    }

    necWimaxBsStatMsNo OBJECT-TYPE
        SYNTAX              Integer32
        MAX-ACCESS          read-only
        STATUS              current
        DESCRIPTION         "Number of entried MS"
        ::= { necWimaxBsPmStatEntry 1 }

    necWimaxBsStatUlSduUsr OBJECT-TYPE
        SYNTAX              Counter64
        MAX-ACCESS          read-only
        STATUS              current
        DESCRIPTION         "Received(Uplink) SDU Number for User Data"
        ::= { necWimaxBsPmStatEntry 2 }

    necWimaxBsStatUlSduManage OBJECT-TYPE
        SYNTAX              Counter64
        MAX-ACCESS          read-only
        STATUS              current
        DESCRIPTION         "Received(Uplink) SDU Number for Management Data"
        ::= { necWimaxBsPmStatEntry 3 }

    necWimaxBsStatUlPdu OBJECT-TYPE
        SYNTAX              Counter64
        MAX-ACCESS          read-only
        STATUS              current
        DESCRIPTION         "Received(Uplink) PDU Number"
        ::= { necWimaxBsPmStatEntry 4 }

    necWimaxBsStatUlSignaling OBJECT-TYPE
        SYNTAX              Counter64
        MAX-ACCESS          read-only
        STATUS              current
        DESCRIPTION         "Received(Uplink) MAC Singaling Header Number"
        ::= { necWimaxBsPmStatEntry 5 }

    necWimaxBsStatUlCrcError OBJECT-TYPE
        SYNTAX              Counter64
        MAX-ACCESS          read-only
        STATUS              current
        DESCRIPTION         "Received(Uplink) CRC Error Number"
        ::= { necWimaxBsPmStatEntry 6 }

    necWimaxBsStatUlDecryptError OBJECT-TYPE
        SYNTAX              Counter64
        MAX-ACCESS          read-only
        STATUS              current
        DESCRIPTION         "Received(Uplink) Decryption Error Number"
        ::= { necWimaxBsPmStatEntry 7 }

    necWimaxBsStatDlSduUsr OBJECT-TYPE
        SYNTAX              Counter64
        MAX-ACCESS          read-only
        STATUS              current
        DESCRIPTION         "Transmitted(Downlink) SDU Number for User Data"
        ::= { necWimaxBsPmStatEntry 8 }

    necWimaxBsStatDlSduManage OBJECT-TYPE
        SYNTAX              Counter64
        MAX-ACCESS          read-only
        STATUS              current
        DESCRIPTION         "Transmitted(Downlink) SDU Number for Management
                            Data"
        ::= { necWimaxBsPmStatEntry 9 }

    necWimaxBsStatDlPdu OBJECT-TYPE
        SYNTAX              Counter64
        MAX-ACCESS          read-only
        STATUS              current
        DESCRIPTION         "Transmitted(Downlink) PDU Number"
        ::= { necWimaxBsPmStatEntry 10 }

    necWimaxBsStatDlDiscardedSdu OBJECT-TYPE
        SYNTAX              Counter64
        MAX-ACCESS          read-only
        STATUS              current
        DESCRIPTION         "Transmitted(Downlink) Discarded SDU Number"
        ::= { necWimaxBsPmStatEntry 11 }

    necWimaxBsStatDlArqRetry OBJECT-TYPE
        SYNTAX              Counter64
        MAX-ACCESS          read-only
        STATUS              current
        DESCRIPTION         "Transmitted(Downlink) ARQ Retry Number"
        ::= { necWimaxBsPmStatEntry 12 }

    necWimaxBsStatDlArqRetryOver OBJECT-TYPE
        SYNTAX              Counter64
        MAX-ACCESS          read-only
        STATUS              current
        DESCRIPTION         "Transmitted(Downlink) ARQ Retryover Number"
        ::= { necWimaxBsPmStatEntry 13 }

    necWimaxBsStatDlHarqRetry OBJECT-TYPE
        SYNTAX              Counter64
        MAX-ACCESS          read-only
        STATUS              current
        DESCRIPTION         "Transmitted(Downlink) HARQ Retry Number"
        ::= { necWimaxBsPmStatEntry 14 }

    necWimaxBsStatDlHarqRetryOver OBJECT-TYPE
        SYNTAX              Counter64
        MAX-ACCESS          read-only
        STATUS              current
        DESCRIPTION         "Transmitted(Downlink) HARQ Retryover Number"
        ::= { necWimaxBsPmStatEntry 15 }

    necWimaxBsStatResetCounter OBJECT-TYPE
        SYNTAX              INTEGER {
                                null( 0 ),
                                resetCounter( 1 )
                            }
        MAX-ACCESS          read-write
        STATUS              current
        DESCRIPTION         "reset all statistics counter"
        ::= { necWimaxBsPmStatEntry 16 }

    necWimaxBsStatUlHarqRetry OBJECT-TYPE
        SYNTAX              Counter64
        MAX-ACCESS          read-only
        STATUS              current
        DESCRIPTION         "Recieved(Uplink) HARQ Retry Number"
        ::= { necWimaxBsPmStatEntry 17 }

    necWimaxBsStatUlHarqRetryOver OBJECT-TYPE
        SYNTAX              Counter64
        MAX-ACCESS          read-only
        STATUS              current
        DESCRIPTION         "Recieved(Uplink) HARQ Retryover Number"
        ::= { necWimaxBsPmStatEntry 18 }

    necWimaxBsPmServiceFlowTable OBJECT-TYPE
        SYNTAX              SEQUENCE OF NecWimaxBsPmServiceFlowEntry
        MAX-ACCESS          not-accessible
        STATUS              current
        DESCRIPTION         "Statistics Information for SF"
        ::= { necWimaxBsPmObjects 4 }

    necWimaxBsPmServiceFlowEntry OBJECT-TYPE
        SYNTAX              NecWimaxBsPmServiceFlowEntry
        MAX-ACCESS          not-accessible
        STATUS              current
        DESCRIPTION         "Please replace this text with your description."
        INDEX               {
                                ifIndex
                            }
        ::= { necWimaxBsPmServiceFlowTable 1 }

    NecWimaxBsPmServiceFlowEntry ::= SEQUENCE {
        necWimaxBsPmSfCreateCount
            Counter32,
        necWimaxBsPmSfCreateFailCount
            Counter32,
        necWimaxBsPmSfDeleteCount
            Counter32,
        necWimaxBsPmSfPermitCount
            Counter32,
        necWimaxBsPmSfRejectCount
            Counter32,
        necWimaxBsPmSfResetCounter
            INTEGER
    }

    necWimaxBsPmSfCreateCount OBJECT-TYPE
        SYNTAX              Counter32
        MAX-ACCESS          read-only
        STATUS              current
        DESCRIPTION         "counter of creation of SF"
        ::= { necWimaxBsPmServiceFlowEntry 1 }

    necWimaxBsPmSfCreateFailCount OBJECT-TYPE
        SYNTAX              Counter32
        MAX-ACCESS          read-only
        STATUS              current
        DESCRIPTION         "counter of fail to create SF"
        ::= { necWimaxBsPmServiceFlowEntry 2 }

    necWimaxBsPmSfDeleteCount OBJECT-TYPE
        SYNTAX              Counter32
        MAX-ACCESS          read-only
        STATUS              current
        DESCRIPTION         "counter of deleted SF"
        ::= { necWimaxBsPmServiceFlowEntry 3 }

    necWimaxBsPmSfPermitCount OBJECT-TYPE
        SYNTAX              Counter32
        MAX-ACCESS          read-only
        STATUS              current
        DESCRIPTION         "counter of permitted SF with Admission Control"
        ::= { necWimaxBsPmServiceFlowEntry 4 }

    necWimaxBsPmSfRejectCount OBJECT-TYPE
        SYNTAX              Counter32
        MAX-ACCESS          read-only
        STATUS              current
        DESCRIPTION         "counter of rejected SF with Admission Control"
        ::= { necWimaxBsPmServiceFlowEntry 5 }

    necWimaxBsPmSfResetCounter OBJECT-TYPE
        SYNTAX              INTEGER {
                                null( 0 ),
                                resetCounter( 1 )
                            }
        MAX-ACCESS          read-write
        STATUS              current
        DESCRIPTION         "reset all statistics counter"
        ::= { necWimaxBsPmServiceFlowEntry 6 }

    necWimaxBsPmHandOverTable OBJECT-TYPE
        SYNTAX              SEQUENCE OF NecWimaxBsPmHandOverEntry
        MAX-ACCESS          not-accessible
        STATUS              current
        DESCRIPTION         "Statistics Information for HandOver"
        ::= { necWimaxBsPmObjects 5 }

    necWimaxBsPmHandOverEntry OBJECT-TYPE
        SYNTAX              NecWimaxBsPmHandOverEntry
        MAX-ACCESS          not-accessible
        STATUS              current
        DESCRIPTION         "Please replace this text with your description."
        INDEX               {
                                ifIndex
                            }
        ::= { necWimaxBsPmHandOverTable 1 }

    NecWimaxBsPmHandOverEntry ::= SEQUENCE {
        necWimaxBsPmHoMshoReqCount
            Counter32,
        necWimaxBsPmHoBshoRspCount
            Counter32,
        necWimaxBsPmHoHoIndCount
            Counter32,
        necWimaxBsPmHoCfmType1Count
            Counter32,
        necWimaxBsPmHoCfmType2Count
            Counter32,
        necWimaxBsPmHoRngReqCount
            Counter32,
        necWimaxBsPmHoRngRspCount
            Counter32,
        necWimaxBsPmHoKeyCountUpdateCount
            Counter32,
        necWimaxBsPmHoResetCounter
            INTEGER
    }

    necWimaxBsPmHoMshoReqCount OBJECT-TYPE
        SYNTAX              Counter32
        MAX-ACCESS          read-only
        STATUS              current
        DESCRIPTION         "counter of recieved MOB_MSHO-REQ by Serving BS"
        ::= { necWimaxBsPmHandOverEntry 1 }

    necWimaxBsPmHoBshoRspCount OBJECT-TYPE
        SYNTAX              Counter32
        MAX-ACCESS          read-only
        STATUS              current
        DESCRIPTION         "counter of transmitted MOB_BSHO-RSP by Serving
                            BS"
        ::= { necWimaxBsPmHandOverEntry 2 }

    necWimaxBsPmHoHoIndCount OBJECT-TYPE
        SYNTAX              Counter32
        MAX-ACCESS          read-only
        STATUS              current
        DESCRIPTION         "counter of recieved MOB_HO-IND by Serving BS"
        ::= { necWimaxBsPmHandOverEntry 3 }

    necWimaxBsPmHoCfmType1Count OBJECT-TYPE
        SYNTAX              Counter32
        MAX-ACCESS          read-only
        STATUS              current
        DESCRIPTION         "counter of recieved HO-CFM(HO Confirm type1) by
                            Target BS"
        ::= { necWimaxBsPmHandOverEntry 4 }

    necWimaxBsPmHoCfmType2Count OBJECT-TYPE
        SYNTAX              Counter32
        MAX-ACCESS          read-only
        STATUS              current
        DESCRIPTION         "counter of recieved HO-CFM(HO Calcel type2) by
                            Target BS"
        ::= { necWimaxBsPmHandOverEntry 5 }

    necWimaxBsPmHoRngReqCount OBJECT-TYPE
        SYNTAX              Counter32
        MAX-ACCESS          read-only
        STATUS              current
        DESCRIPTION         "counter of recieved RNG-REQ(Re-Entry) by Target
                            BS"
        ::= { necWimaxBsPmHandOverEntry 6 }

    necWimaxBsPmHoRngRspCount OBJECT-TYPE
        SYNTAX              Counter32
        MAX-ACCESS          read-only
        STATUS              current
        DESCRIPTION         "counter of transmitted RNG-RSP(Re-Entry) by Target
                            BS"
        ::= { necWimaxBsPmHandOverEntry 7 }

    necWimaxBsPmHoKeyCountUpdateCount OBJECT-TYPE
        SYNTAX              Counter32
        MAX-ACCESS          read-only
        STATUS              current
        DESCRIPTION         "counter of recieved CMAC_Key_Count_Ack by Target
                            BS"
        ::= { necWimaxBsPmHandOverEntry 8 }

    necWimaxBsPmHoResetCounter OBJECT-TYPE
        SYNTAX              INTEGER {
                                null( 0 ),
                                resetCounter( 1 )
                            }
        MAX-ACCESS          read-write
        STATUS              current
        DESCRIPTION         "reset all statistics counter"
        ::= { necWimaxBsPmHandOverEntry 9 }

    necWimaxBsPmCongestionTable OBJECT-TYPE
        SYNTAX              SEQUENCE OF NecWimaxBsPmCongestionEntry
        MAX-ACCESS          not-accessible
        STATUS              current
        DESCRIPTION         "Statistics Information for Congestion"
        ::= { necWimaxBsPmObjects 6 }

    necWimaxBsPmCongestionEntry OBJECT-TYPE
        SYNTAX              NecWimaxBsPmCongestionEntry
        MAX-ACCESS          not-accessible
        STATUS              current
        DESCRIPTION         "all CHC"
        INDEX               {
                                ifIndex
                            }
        ::= { necWimaxBsPmCongestionTable 1 }

    NecWimaxBsPmCongestionEntry ::= SEQUENCE {
        necWimaxBsPmCongestionCount
            Counter32,
        necWimaxBsPmCongestionResetCounter
            INTEGER
    }

    necWimaxBsPmCongestionCount OBJECT-TYPE
        SYNTAX              Counter32
        MAX-ACCESS          read-only
        STATUS              current
        DESCRIPTION         "congestion detected count"
        ::= { necWimaxBsPmCongestionEntry 1 }

    necWimaxBsPmCongestionResetCounter OBJECT-TYPE
        SYNTAX              INTEGER {
                                null( 0 ),
                                resetCounter( 1 )
                            }
        MAX-ACCESS          read-write
        STATUS              current
        DESCRIPTION         "reset all congestion counter"
        ::= { necWimaxBsPmCongestionEntry 2 }

    necWimaxBsPmPagingTable OBJECT-TYPE
        SYNTAX              SEQUENCE OF NecWimaxBsPmPagingEntry
        MAX-ACCESS          not-accessible
        STATUS              current
        DESCRIPTION         "Statistics Information for Paging"
        ::= { necWimaxBsPmObjects 7 }

    necWimaxBsPmPagingEntry OBJECT-TYPE
        SYNTAX              NecWimaxBsPmPagingEntry
        MAX-ACCESS          not-accessible
        STATUS              current
        DESCRIPTION         "all CHC"
        INDEX               {
                                ifIndex
                            }
        ::= { necWimaxBsPmPagingTable 1 }

    NecWimaxBsPmPagingEntry ::= SEQUENCE {
        necWimaxBsPmMobPagAdvCount
            Counter32,
        necWimaxBsPmPagingResetCounter
            INTEGER
    }

    necWimaxBsPmMobPagAdvCount OBJECT-TYPE
        SYNTAX              Counter32
        MAX-ACCESS          read-only
        STATUS              current
        DESCRIPTION         "counter of MOB_PAG-ADV transmition"
        ::= { necWimaxBsPmPagingEntry 1 }

    necWimaxBsPmPagingResetCounter OBJECT-TYPE
        SYNTAX              INTEGER {
                                null( 0 ),
                                resetCounter( 1 )
                            }
        MAX-ACCESS          read-write
        STATUS              current
        DESCRIPTION         "reset all paging counter"
        ::= { necWimaxBsPmPagingEntry 2 }

    necWimaxBsPmNwentryTable OBJECT-TYPE
        SYNTAX              SEQUENCE OF NecWimaxBsPmNwentryEntry
        MAX-ACCESS          not-accessible
        STATUS              current
        DESCRIPTION         "Statistics Information for Network Entry"
        ::= { necWimaxBsPmObjects 8 }

    necWimaxBsPmNwentryEntry OBJECT-TYPE
        SYNTAX              NecWimaxBsPmNwentryEntry
        MAX-ACCESS          not-accessible
        STATUS              current
        DESCRIPTION         "all CHC"
        INDEX               {
                                ifIndex
                            }
        ::= { necWimaxBsPmNwentryTable 1 }

    NecWimaxBsPmNwentryEntry ::= SEQUENCE {
        necWimaxBsPmNwentrySuccess
            Counter32,
        necWimaxBsPmNwentryFail
            Counter32,
        necWimaxBsPmNwentryFailMsNumOver
            Counter32,
        necWimaxBsPmNwentryFailAuthErr
            Counter32,
        necWimaxBsPmNwentryFailAdmissionErr
            Counter32,
        necWimaxBsPmNwentryFailOther
            Counter32,
        necWimaxBsPmNwentryResetCounter
            INTEGER
    }

    necWimaxBsPmNwentrySuccess OBJECT-TYPE
        SYNTAX              Counter32
        MAX-ACCESS          read-only
        STATUS              current
        DESCRIPTION         "counter of succeded Network Entry"
        ::= { necWimaxBsPmNwentryEntry 1 }

    necWimaxBsPmNwentryFail OBJECT-TYPE
        SYNTAX              Counter32
        MAX-ACCESS          read-only
        STATUS              current
        DESCRIPTION         "counter of failed network entry"
        ::= { necWimaxBsPmNwentryEntry 2 }

    necWimaxBsPmNwentryFailMsNumOver OBJECT-TYPE
        SYNTAX              Counter32
        MAX-ACCESS          read-only
        STATUS              current
        DESCRIPTION         "counter of failed network entry because of MAX
                            MS number over"
        ::= { necWimaxBsPmNwentryEntry 3 }

    necWimaxBsPmNwentryFailAuthErr OBJECT-TYPE
        SYNTAX              Counter32
        MAX-ACCESS          read-only
        STATUS              current
        DESCRIPTION         "counter of failed network entry because of authentication
                            error"
        ::= { necWimaxBsPmNwentryEntry 4 }

    necWimaxBsPmNwentryFailAdmissionErr OBJECT-TYPE
        SYNTAX              Counter32
        MAX-ACCESS          read-only
        STATUS              current
        DESCRIPTION         "counter of failed network entry because of admittion
                            error"
        ::= { necWimaxBsPmNwentryEntry 5 }

    necWimaxBsPmNwentryFailOther OBJECT-TYPE
        SYNTAX              Counter32
        MAX-ACCESS          read-only
        STATUS              current
        DESCRIPTION         "counter of failed network entry because of other
                            reason"
        ::= { necWimaxBsPmNwentryEntry 6 }

    necWimaxBsPmNwentryResetCounter OBJECT-TYPE
        SYNTAX              INTEGER {
                                null( 0 ),
                                resetCounter( 1 )
                            }
        MAX-ACCESS          read-write
        STATUS              current
        DESCRIPTION         "reset all network entry counter"
        ::= { necWimaxBsPmNwentryEntry 7 }

    necWimaxBsPmSleepMode OBJECT IDENTIFIER ::= { necWimaxBsPmObjects 9 }

    necWimaxBsPmSleepTable OBJECT-TYPE
        SYNTAX              SEQUENCE OF NecWimaxBsPmSleepEntry
        MAX-ACCESS          not-accessible
        STATUS              current
        DESCRIPTION         "Statistics Information for Sleep Mode"
        ::= { necWimaxBsPmSleepMode 1 }

    necWimaxBsPmSleepEntry OBJECT-TYPE
        SYNTAX              NecWimaxBsPmSleepEntry
        MAX-ACCESS          not-accessible
        STATUS              current
        DESCRIPTION         "all CHC"
        INDEX               {
                                ifIndex
                            }
        ::= { necWimaxBsPmSleepTable 1 }

    NecWimaxBsPmSleepEntry ::= SEQUENCE {
        necWimaxBsPmSleepMsNum
            Integer32
    }

    necWimaxBsPmSleepMsNum OBJECT-TYPE
        SYNTAX              Integer32
        MAX-ACCESS          read-only
        STATUS              current
        DESCRIPTION         "MS number in sleep mode"
        ::= { necWimaxBsPmSleepEntry 1 }

    necWimaxBsSsPmSleepTable OBJECT-TYPE
        SYNTAX              SEQUENCE OF NecWimaxBsSsPmSleepEntry
        MAX-ACCESS          not-accessible
        STATUS              current
        DESCRIPTION         "sleep mode statistics by MS"
        ::= { necWimaxBsPmSleepMode 2 }

    necWimaxBsSsPmSleepEntry OBJECT-TYPE
        SYNTAX              NecWimaxBsSsPmSleepEntry
        MAX-ACCESS          not-accessible
        STATUS              current
        DESCRIPTION         "indexed by ifIndex and msmac"
        INDEX               {
                                ifIndex,
                                necWimaxBsSsPmMacAddress
                            }
        ::= { necWimaxBsSsPmSleepTable 1 }

    NecWimaxBsSsPmSleepEntry ::= SEQUENCE {
        necWimaxBsSsPmSleepPscNum
            Integer32
    }

    necWimaxBsSsPmSleepPscNum OBJECT-TYPE
        SYNTAX              Integer32
        MAX-ACCESS          read-only
        STATUS              current
        DESCRIPTION         "PSC number for each MS in sleep mode"
        ::= { necWimaxBsSsPmSleepEntry 1 }

    necWimaxBsSsPscPmSleepTable OBJECT-TYPE
        SYNTAX              SEQUENCE OF NecWimaxBsSsPscPmSleepEntry
        MAX-ACCESS          not-accessible
        STATUS              current
        DESCRIPTION         "sleep mode statistics by MS and PSC"
        ::= { necWimaxBsPmSleepMode 3 }

    necWimaxBsSsPscPmSleepEntry OBJECT-TYPE
        SYNTAX              NecWimaxBsSsPscPmSleepEntry
        MAX-ACCESS          not-accessible
        STATUS              current
        DESCRIPTION         "indexed by ifIndex and msmac and PSC"
        INDEX               {
                                ifIndex,
                                necWimaxBsSsPmMacAddress,
                                necWimaxBsSleepPsc
                            }
        ::= { necWimaxBsSsPscPmSleepTable 1 }

    NecWimaxBsSsPscPmSleepEntry ::= SEQUENCE {
        necWimaxBsSleepPsc
            Integer32,
        necWimaxBsSsPscPmSleepWindowSize
            Unsigned32,
        necWimaxBsSsPscPmListeningWindowSize
            Integer32
    }

    necWimaxBsSleepPsc OBJECT-TYPE
        SYNTAX              Integer32 (1..650000000)
        MAX-ACCESS          read-only
        STATUS              current
        DESCRIPTION         "The PSC index for each MS in sleep mode"
        ::= { necWimaxBsSsPscPmSleepEntry 1 }

    necWimaxBsSsPscPmSleepWindowSize OBJECT-TYPE
        SYNTAX              Unsigned32
        MAX-ACCESS          read-only
        STATUS              current
        DESCRIPTION         "Sleep Window Size"
        ::= { necWimaxBsSsPscPmSleepEntry 2 }

    necWimaxBsSsPscPmListeningWindowSize OBJECT-TYPE
        SYNTAX              Integer32
        MAX-ACCESS          read-only
        STATUS              current
        DESCRIPTION         "Listening Window Size"
        ::= { necWimaxBsSsPscPmSleepEntry 3 }

    necWimaxBsRrmTable OBJECT-TYPE
        SYNTAX              SEQUENCE OF NecWimaxBsRrmEntry
        MAX-ACCESS          not-accessible
        STATUS              current
        DESCRIPTION         "Configuration parameter for RRM function"
        ::= { necWimaxBsIfmObjects 7 }

    necWimaxBsRrmEntry OBJECT-TYPE
        SYNTAX              NecWimaxBsRrmEntry
        MAX-ACCESS          not-accessible
        STATUS              current
        DESCRIPTION         "indexed by ifindex"
        INDEX               {
                                ifIndex
                            }
        ::= { necWimaxBsRrmTable 1 }

    NecWimaxBsRrmEntry ::= SEQUENCE {
        necWimaxBsRrmScReportChar
            Unsigned32,
        necWimaxBsRrmAveragingTime
            Integer32,
        necWimaxBsRrmScReportingPeriod
            Integer32,
        necWimaxBsRrmAbsoluteThreshold
            Integer32,
        necWimaxBsRrmRelativeThreshold
            Integer32,
        necWimaxBsRrmRcReportChar
            Unsigned32,
        necWimaxBsRrmRcReportingPeriod
            Integer32,
        necWimaxBsRrmScReqRetry
            Integer32,
        necWimaxBsRrmRcReqRetry
            Integer32,
        necWimaxBsRrmRcRptRetry
            Integer32,
        necWimaxBsRrmScReqInterval
            Integer32
    }

    necWimaxBsRrmScReportChar OBJECT-TYPE
        SYNTAX              Unsigned32 (0..15)
        MAX-ACCESS          read-write
        STATUS              current
        DESCRIPTION         "RRM Reporting Characteristics. this valus is set
                            to Spare_Capacity_Req"
        ::= { necWimaxBsRrmEntry 1 }

    necWimaxBsRrmAveragingTime OBJECT-TYPE
        SYNTAX              Integer32 (1..65535)
        UNITS               "100ms"
        MAX-ACCESS          read-write
        STATUS              current
        DESCRIPTION         "Interval of Available Radio Resouorce Measurement"
        ::= { necWimaxBsRrmEntry 2 }

    necWimaxBsRrmScReportingPeriod OBJECT-TYPE
        SYNTAX              Integer32 (10..65400)
        UNITS               "100ms"
        MAX-ACCESS          read-write
        STATUS              current
        DESCRIPTION         "RRM Reporting Period P. this value is set to Spare_Capacity_Req"
        ::= { necWimaxBsRrmEntry 3 }

    necWimaxBsRrmAbsoluteThreshold OBJECT-TYPE
        SYNTAX              Integer32 (0..100)
        MAX-ACCESS          read-write
        STATUS              current
        DESCRIPTION         "Threshold value (%) in case of RRM Reporting Carateristics(Spare_Capacity_Req)
                            BIT#2=1"
        ::= { necWimaxBsRrmEntry 4 }

    necWimaxBsRrmRelativeThreshold OBJECT-TYPE
        SYNTAX              Integer32 (0..100)
        MAX-ACCESS          read-write
        STATUS              current
        DESCRIPTION         "Threshold value (%) in case of RRM Reporting Carateristics(Spare_Capacity_Req)
                            BIT#1=1"
        ::= { necWimaxBsRrmEntry 5 }

    necWimaxBsRrmRcReportChar OBJECT-TYPE
        SYNTAX              Unsigned32 (0..1 | 8..9)
        MAX-ACCESS          read-write
        STATUS              current
        DESCRIPTION         "RRM Reporting Characteristics.RRM Reporting Characteristics.
                            this valus is set to Radio_Config_Upadate_Req"
        ::= { necWimaxBsRrmEntry 6 }

    necWimaxBsRrmRcReportingPeriod OBJECT-TYPE
        SYNTAX              Integer32 (10..65400)
        UNITS               "100ms"
        MAX-ACCESS          read-write
        STATUS              current
        DESCRIPTION         "RRM Reporting Period P. this value is set to Radio_Config_Update_Req"
        ::= { necWimaxBsRrmEntry 7 }

    necWimaxBsRrmScReqRetry OBJECT-TYPE
        SYNTAX              Integer32 (0..10)
        MAX-ACCESS          read-write
        STATUS              current
        DESCRIPTION         "Max rery count of Spare_Capacity_Req"
        ::= { necWimaxBsRrmEntry 8 }

    necWimaxBsRrmRcReqRetry OBJECT-TYPE
        SYNTAX              Integer32 (0..10)
        MAX-ACCESS          read-write
        STATUS              current
        DESCRIPTION         "Max rery count of Radio_Config_Update_Req"
        ::= { necWimaxBsRrmEntry 9 }

    necWimaxBsRrmRcRptRetry OBJECT-TYPE
        SYNTAX              Integer32 (0..10)
        MAX-ACCESS          read-write
        STATUS              current
        DESCRIPTION         "Max rery count of Radio_Config_Update_Rpt"
        ::= { necWimaxBsRrmEntry 10 }

    necWimaxBsRrmScReqInterval OBJECT-TYPE
        SYNTAX              Integer32 (0..255)
        UNITS               "min"
        MAX-ACCESS          read-write
        STATUS              current
        DESCRIPTION         "Spare_Capacity_Req transmit interval for dead
                            neighbor BS"
        ::= { necWimaxBsRrmEntry 11 }

    necWimaxBsNeighborTable OBJECT-TYPE
        SYNTAX              SEQUENCE OF NecWimaxBsNeighborEntry
        MAX-ACCESS          not-accessible
        STATUS              current
        DESCRIPTION         "Neighbor BS status information monitored by RRM
                            message exchange."
        ::= { necWimaxBsIfmObjects 8 }

    necWimaxBsNeighborEntry OBJECT-TYPE
        SYNTAX              NecWimaxBsNeighborEntry
        MAX-ACCESS          not-accessible
        STATUS              current
        DESCRIPTION         "indexed by ifIndex and neighborBsIndex"
        INDEX               {
                                ifIndex,
                                necWimaxBsNeighborBsIndex
                            }
        ::= { necWimaxBsNeighborTable 1 }

    NecWimaxBsNeighborEntry ::= SEQUENCE {
        necWimaxBsNeighborBsIndex
            Integer32,
        necWimaxBsNeighborBsid
            OCTET STRING,
        necWimaxBsNeighborBsStatus
            INTEGER
    }

    necWimaxBsNeighborBsIndex OBJECT-TYPE
        SYNTAX              Integer32 (1..650000000)
        MAX-ACCESS          not-accessible
        STATUS              current
        DESCRIPTION         "neighborBS index"
        ::= { necWimaxBsNeighborEntry 1 }

    necWimaxBsNeighborBsid OBJECT-TYPE
        SYNTAX              OCTET STRING (SIZE(6))
        MAX-ACCESS          read-only
        STATUS              current
        DESCRIPTION         "neighborBS's BSID"
        ::= { necWimaxBsNeighborEntry 2 }

    necWimaxBsNeighborBsStatus OBJECT-TYPE
        SYNTAX              INTEGER {
                                dead( 0 ),
                                alive( 1 )
                            }
        MAX-ACCESS          read-only
        STATUS              current
        DESCRIPTION         "neighborBS's status."
        ::= { necWimaxBsNeighborEntry 3 }

    necWimaxBsSsPmObjects OBJECT IDENTIFIER ::= { necWimaxBsIfMib 3 }

    necWimaxBsSsPmThroughputTable OBJECT-TYPE
        SYNTAX              SEQUENCE OF NecWimaxBsSsPmThroughputEntry
        MAX-ACCESS          not-accessible
        STATUS              current
        DESCRIPTION         "throughput"
        ::= { necWimaxBsSsPmObjects 1 }

    necWimaxBsSsPmThroughputEntry OBJECT-TYPE
        SYNTAX              NecWimaxBsSsPmThroughputEntry
        MAX-ACCESS          not-accessible
        STATUS              current
        DESCRIPTION         "indexed by ifIndex and msmac"
        INDEX               {
                                ifIndex,
                                necWimaxBsSsPmMacAddress
                            }
        ::= { necWimaxBsSsPmThroughputTable 1 }

    NecWimaxBsSsPmThroughputEntry ::= SEQUENCE {
        necWimaxBsSsPmDlThroughputPduCounter
            Counter64,
        necWimaxBsSsPmDlThroughputSduCounter
            Counter64,
        necWimaxBsSsPmDlThroughputIpCounter
            Counter64,
        necWimaxBsSsPmUlThroughputPduCounter
            Counter64,
        necWimaxBsSsPmUlThroughputSduCounter
            Counter64,
        necWimaxBsSsPmUlThroughputIpCounter
            Counter64,
        necWimaxBsSsPmThroughputResetCounter
            INTEGER
    }

    necWimaxBsSsPmDlThroughputPduCounter OBJECT-TYPE
        SYNTAX              Counter64
        MAX-ACCESS          read-only
        STATUS              current
        DESCRIPTION         "Cumulative downlink throughput of PHY."
        ::= { necWimaxBsSsPmThroughputEntry 7 }

    necWimaxBsSsPmDlThroughputSduCounter OBJECT-TYPE
        SYNTAX              Counter64
        MAX-ACCESS          read-only
        STATUS              current
        DESCRIPTION         "Cumulative downlink throughput of SDU."
        ::= { necWimaxBsSsPmThroughputEntry 8 }

    necWimaxBsSsPmDlThroughputIpCounter OBJECT-TYPE
        SYNTAX              Counter64
        MAX-ACCESS          read-only
        STATUS              current
        DESCRIPTION         "Cumulative downlink throughput of IP."
        ::= { necWimaxBsSsPmThroughputEntry 9 }

    necWimaxBsSsPmUlThroughputPduCounter OBJECT-TYPE
        SYNTAX              Counter64
        MAX-ACCESS          read-only
        STATUS              current
        DESCRIPTION         "Cumulative uplink throughput of PHY."
        ::= { necWimaxBsSsPmThroughputEntry 10 }

    necWimaxBsSsPmUlThroughputSduCounter OBJECT-TYPE
        SYNTAX              Counter64
        MAX-ACCESS          read-only
        STATUS              current
        DESCRIPTION         "Cumulative uplink throughput of MAC."
        ::= { necWimaxBsSsPmThroughputEntry 11 }

    necWimaxBsSsPmUlThroughputIpCounter OBJECT-TYPE
        SYNTAX              Counter64
        MAX-ACCESS          read-only
        STATUS              current
        DESCRIPTION         "Cumulative uplink throughput of Ip."
        ::= { necWimaxBsSsPmThroughputEntry 12 }

    necWimaxBsSsPmThroughputResetCounter OBJECT-TYPE
        SYNTAX              INTEGER {
                                null( 0 ),
                                resetCounter( 1 )
                            }
        MAX-ACCESS          read-write
        STATUS              current
        DESCRIPTION         "reset MS Throughput Counter."
        ::= { necWimaxBsSsPmThroughputEntry 13 }

    necWimaxBsSsPmOthersTable OBJECT-TYPE
        SYNTAX              SEQUENCE OF NecWimaxBsSsPmOthersEntry
        MAX-ACCESS          not-accessible
        STATUS              current
        DESCRIPTION         "This table contains other PM objects for each
                            MS."
        ::= { necWimaxBsSsPmObjects 2 }

    necWimaxBsSsPmOthersEntry OBJECT-TYPE
        SYNTAX              NecWimaxBsSsPmOthersEntry
        MAX-ACCESS          not-accessible
        STATUS              current
        DESCRIPTION         "This table provides one row for each MacAddress,
                            and is indexed by ifIndex, necWimaxBsSsPmMacAddress.
                            IfIndex is associated with the BS sector."
        INDEX               {
                                ifIndex,
                                necWimaxBsSsPmMacAddress
                            }
        ::= { necWimaxBsSsPmOthersTable 1 }

    NecWimaxBsSsPmOthersEntry ::= SEQUENCE {
        necWimaxBsSsPmPacketLossRate
            Integer32,
        necWimaxBsSsPmNumOfGre
            Unsigned32
    }

    necWimaxBsSsPmPacketLossRate OBJECT-TYPE
        SYNTAX              Integer32 (0..100)
        MAX-ACCESS          read-only
        STATUS              current
        DESCRIPTION         "MS packet loss rate represented by %"
        ::= { necWimaxBsSsPmOthersEntry 1 }

    necWimaxBsSsPmNumOfGre OBJECT-TYPE
        SYNTAX              Unsigned32
        MAX-ACCESS          read-only
        STATUS              current
        DESCRIPTION         "Num of GRE for each MS"
        ::= { necWimaxBsSsPmOthersEntry 2 }

    necWimaxBsSsPmStatTable OBJECT-TYPE
        SYNTAX              SEQUENCE OF NecWimaxBsSsPmStatEntry
        MAX-ACCESS          not-accessible
        STATUS              current
        DESCRIPTION         "This table contains PM stat for each MS."
        ::= { necWimaxBsSsPmObjects 3 }

    necWimaxBsSsPmStatEntry OBJECT-TYPE
        SYNTAX              NecWimaxBsSsPmStatEntry
        MAX-ACCESS          not-accessible
        STATUS              current
        DESCRIPTION         "This table provides one row for each MacAddress,
                            and is indexed by ifIndex, necWimaxBsSsPmMacAddress.
                            IfIndex is associated with the BS sector."
        INDEX               {
                                ifIndex,
                                necWimaxBsSsPmMacAddress
                            }
        ::= { necWimaxBsSsPmStatTable 1 }

    NecWimaxBsSsPmStatEntry ::= SEQUENCE {
        necWimaxBsSsPmMacAddress
            MacAddress,
        necWimaxBsSsPmStatUlSduUsr
            Counter64,
        necWimaxBsSsPmStatUlSduManage
            Counter64,
        necWimaxBsSsPmStatUlPdu
            Counter64,
        necWimaxBsSsPmStatUlSignaling
            Counter64,
        necWimaxBsSsPmStatUlCrcError
            Counter64,
        necWimaxBsSsPmStatUlDecryptError
            Counter64,
        necWimaxBsSsPmStatDlSduUsr
            Counter64,
        necWimaxBsSsPmStatDlSduManage
            Counter64,
        necWimaxBsSsPmStatDlPdu
            Counter64,
        necWimaxBsSsPmStatDlDiscardedSdu
            Counter64,
        necWimaxBsSsPmStatDlArqRetry
            Counter64,
        necWimaxBsSsPmStatDlArqRetryOver
            Counter64,
        necWimaxBsSsPmStatDlHarqRetry
            Counter64,
        necWimaxBsSsPmStatDlHarqRetryOver
            Counter64,
        necWimaxBsSsPmStatUlHarqRetry
            Counter64,
        necWimaxBsSsPmStatUlHarqRetryOver
            Counter64,
        necWimaxBsSsPmStatResetCounter
            INTEGER
    }

    necWimaxBsSsPmMacAddress OBJECT-TYPE
        SYNTAX              MacAddress
        MAX-ACCESS          not-accessible
        STATUS              current
        DESCRIPTION         "When this table is implemented on the basestation,
                            this object contains the SS Mac address, the
                            reported service flow was created for. On the
                            SS, the value returned is the SS's own Mac address."
        ::= { necWimaxBsSsPmStatEntry 1 }

    necWimaxBsSsPmStatUlSduUsr OBJECT-TYPE
        SYNTAX              Counter64
        MAX-ACCESS          read-only
        STATUS              current
        DESCRIPTION         "Received(Uplink) SDU Number for User Data"
        ::= { necWimaxBsSsPmStatEntry 2 }

    necWimaxBsSsPmStatUlSduManage OBJECT-TYPE
        SYNTAX              Counter64
        MAX-ACCESS          read-only
        STATUS              current
        DESCRIPTION         "Received(Uplink) SDU Number for Management Data"
        ::= { necWimaxBsSsPmStatEntry 3 }

    necWimaxBsSsPmStatUlPdu OBJECT-TYPE
        SYNTAX              Counter64
        MAX-ACCESS          read-only
        STATUS              current
        DESCRIPTION         "Received(Uplink) PDU Number"
        ::= { necWimaxBsSsPmStatEntry 4 }

    necWimaxBsSsPmStatUlSignaling OBJECT-TYPE
        SYNTAX              Counter64
        MAX-ACCESS          read-only
        STATUS              current
        DESCRIPTION         "Received(Uplink) MAC Singaling Header Number"
        ::= { necWimaxBsSsPmStatEntry 5 }

    necWimaxBsSsPmStatUlCrcError OBJECT-TYPE
        SYNTAX              Counter64
        MAX-ACCESS          read-only
        STATUS              current
        DESCRIPTION         "Received(Uplink) CRC Error Number"
        ::= { necWimaxBsSsPmStatEntry 6 }

    necWimaxBsSsPmStatUlDecryptError OBJECT-TYPE
        SYNTAX              Counter64
        MAX-ACCESS          read-only
        STATUS              current
        DESCRIPTION         "Received(Uplink) Decryption Error Number"
        ::= { necWimaxBsSsPmStatEntry 7 }

    necWimaxBsSsPmStatDlSduUsr OBJECT-TYPE
        SYNTAX              Counter64
        MAX-ACCESS          read-only
        STATUS              current
        DESCRIPTION         "Transmitted(Downlink) SDU Number for User Data"
        ::= { necWimaxBsSsPmStatEntry 8 }

    necWimaxBsSsPmStatDlSduManage OBJECT-TYPE
        SYNTAX              Counter64
        MAX-ACCESS          read-only
        STATUS              current
        DESCRIPTION         "Transmitted(Downlink) SDU Number for Management
                            Data"
        ::= { necWimaxBsSsPmStatEntry 9 }

    necWimaxBsSsPmStatDlPdu OBJECT-TYPE
        SYNTAX              Counter64
        MAX-ACCESS          read-only
        STATUS              current
        DESCRIPTION         "Transmitted(Downlink) PDU Number"
        ::= { necWimaxBsSsPmStatEntry 10 }

    necWimaxBsSsPmStatDlDiscardedSdu OBJECT-TYPE
        SYNTAX              Counter64
        MAX-ACCESS          read-only
        STATUS              current
        DESCRIPTION         "Transmitted(Downlink) Discarded SDU Number"
        ::= { necWimaxBsSsPmStatEntry 11 }

    necWimaxBsSsPmStatDlArqRetry OBJECT-TYPE
        SYNTAX              Counter64
        MAX-ACCESS          read-only
        STATUS              current
        DESCRIPTION         "Transmitted(Downlink) ARQ Retry Number"
        ::= { necWimaxBsSsPmStatEntry 12 }

    necWimaxBsSsPmStatDlArqRetryOver OBJECT-TYPE
        SYNTAX              Counter64
        MAX-ACCESS          read-only
        STATUS              current
        DESCRIPTION         "Transmitted(Downlink) ARQ Retryover Number"
        ::= { necWimaxBsSsPmStatEntry 13 }

    necWimaxBsSsPmStatDlHarqRetry OBJECT-TYPE
        SYNTAX              Counter64
        MAX-ACCESS          read-only
        STATUS              current
        DESCRIPTION         "Transmitted(Downlink) HARQ Retry Number"
        ::= { necWimaxBsSsPmStatEntry 14 }

    necWimaxBsSsPmStatDlHarqRetryOver OBJECT-TYPE
        SYNTAX              Counter64
        MAX-ACCESS          read-only
        STATUS              current
        DESCRIPTION         "Transmitted(Downlink) HARQ Retryover Number"
        ::= { necWimaxBsSsPmStatEntry 15 }

    necWimaxBsSsPmStatUlHarqRetry OBJECT-TYPE
        SYNTAX              Counter64
        MAX-ACCESS          read-only
        STATUS              current
        DESCRIPTION         "Recieved(Uplink) HARQ Retry Number"
        ::= { necWimaxBsSsPmStatEntry 17 }

    necWimaxBsSsPmStatUlHarqRetryOver OBJECT-TYPE
        SYNTAX              Counter64
        MAX-ACCESS          read-only
        STATUS              current
        DESCRIPTION         "Recieved(Uplink) HARQ Retryover Number"
        ::= { necWimaxBsSsPmStatEntry 18 }

    necWimaxBsSsPmStatResetCounter OBJECT-TYPE
        SYNTAX              INTEGER {
                                null( 0 ),
                                resetCounter( 1 )
                            }
        MAX-ACCESS          read-write
        STATUS              current
        DESCRIPTION         "reset MS Stat Counter."
        ::= { necWimaxBsSsPmStatEntry 19 }

    necWimaxBsCidPmObjects OBJECT IDENTIFIER ::= { necWimaxBsIfMib 4 }

    necWimaxBsCidPmThroughputTable OBJECT-TYPE
        SYNTAX              SEQUENCE OF NecWimaxBsCidPmThroughputEntry
        MAX-ACCESS          not-accessible
        STATUS              current
        DESCRIPTION         "throughput"
        ::= { necWimaxBsCidPmObjects 1 }

    necWimaxBsCidPmThroughputEntry OBJECT-TYPE
        SYNTAX              NecWimaxBsCidPmThroughputEntry
        MAX-ACCESS          not-accessible
        STATUS              current
        DESCRIPTION         "indexed by ifIndex and CID"
        INDEX               {
                                ifIndex,
                                necWimaxBsCidPmCid
                            }
        ::= { necWimaxBsCidPmThroughputTable 1 }

    NecWimaxBsCidPmThroughputEntry ::= SEQUENCE {
        necWimaxBsCidPmDlThroughputPduCounter
            Counter64,
        necWimaxBsCidPmDlThroughputSduCounter
            Counter64,
        necWimaxBsCidPmDlThroughputIpCounter
            Counter64,
        necWimaxBsCidPmUlThroughputPduCounter
            Counter64,
        necWimaxBsCidPmUlThroughputSduCounter
            Counter64,
        necWimaxBsCidPmUlThroughputIpCounter
            Counter64
    }

    necWimaxBsCidPmDlThroughputPduCounter OBJECT-TYPE
        SYNTAX              Counter64
        MAX-ACCESS          read-only
        STATUS              current
        DESCRIPTION         "Cumulative downlink throughput of PHY."
        ::= { necWimaxBsCidPmThroughputEntry 7 }

    necWimaxBsCidPmDlThroughputSduCounter OBJECT-TYPE
        SYNTAX              Counter64
        MAX-ACCESS          read-only
        STATUS              current
        DESCRIPTION         "Cumulative downlink throughput of SDU."
        ::= { necWimaxBsCidPmThroughputEntry 8 }

    necWimaxBsCidPmDlThroughputIpCounter OBJECT-TYPE
        SYNTAX              Counter64
        MAX-ACCESS          read-only
        STATUS              current
        DESCRIPTION         "Cumulative downlink throughput of IP."
        ::= { necWimaxBsCidPmThroughputEntry 9 }

    necWimaxBsCidPmUlThroughputPduCounter OBJECT-TYPE
        SYNTAX              Counter64
        MAX-ACCESS          read-only
        STATUS              current
        DESCRIPTION         "Cumulative uplink throughput of PHY."
        ::= { necWimaxBsCidPmThroughputEntry 10 }

    necWimaxBsCidPmUlThroughputSduCounter OBJECT-TYPE
        SYNTAX              Counter64
        MAX-ACCESS          read-only
        STATUS              current
        DESCRIPTION         "Cumulative uplink throughput of MAC."
        ::= { necWimaxBsCidPmThroughputEntry 11 }

    necWimaxBsCidPmUlThroughputIpCounter OBJECT-TYPE
        SYNTAX              Counter64
        MAX-ACCESS          read-only
        STATUS              current
        DESCRIPTION         "Cumulative uplink throughput of Ip."
        ::= { necWimaxBsCidPmThroughputEntry 12 }

    necWimaxBsCidPmNvcTable OBJECT-TYPE
        SYNTAX              SEQUENCE OF NecWimaxBsCidPmNvcEntry
        MAX-ACCESS          not-accessible
        STATUS              current
        DESCRIPTION         "negative volume count"
        ::= { necWimaxBsCidPmObjects 2 }

    necWimaxBsCidPmNvcEntry OBJECT-TYPE
        SYNTAX              NecWimaxBsCidPmNvcEntry
        MAX-ACCESS          not-accessible
        STATUS              current
        DESCRIPTION         "indexed by ifIndex and CID"
        INDEX               {
                                ifIndex,
                                necWimaxBsCidPmCid
                            }
        ::= { necWimaxBsCidPmNvcTable 1 }

    NecWimaxBsCidPmNvcEntry ::= SEQUENCE {
        necWimaxBsCidPmNvcDlOctet
            Counter64,
        necWimaxBsCidPmNvcDlOctetLoss
            Counter64,
        necWimaxBsCidPmNvcDlSdu
            Counter64,
        necWimaxBsCidPmNvcDlSduLoss
            Counter64,
        necWimaxBsCidPmNvcUlOctet
            Counter64,
        necWimaxBsCidPmNvcUlSdu
            Counter64
    }

    necWimaxBsCidPmNvcDlOctet OBJECT-TYPE
        SYNTAX              Counter64
        MAX-ACCESS          read-only
        STATUS              current
        DESCRIPTION         "downlink octet counts"
        ::= { necWimaxBsCidPmNvcEntry 1 }

    necWimaxBsCidPmNvcDlOctetLoss OBJECT-TYPE
        SYNTAX              Counter64
        MAX-ACCESS          read-only
        STATUS              current
        DESCRIPTION         "downlink octet counts loss"
        ::= { necWimaxBsCidPmNvcEntry 2 }

    necWimaxBsCidPmNvcDlSdu OBJECT-TYPE
        SYNTAX              Counter64
        MAX-ACCESS          read-only
        STATUS              current
        DESCRIPTION         "downlink SDU counts"
        ::= { necWimaxBsCidPmNvcEntry 3 }

    necWimaxBsCidPmNvcDlSduLoss OBJECT-TYPE
        SYNTAX              Counter64
        MAX-ACCESS          read-only
        STATUS              current
        DESCRIPTION         "downlink SDU counts loss"
        ::= { necWimaxBsCidPmNvcEntry 4 }

    necWimaxBsCidPmNvcUlOctet OBJECT-TYPE
        SYNTAX              Counter64
        MAX-ACCESS          read-only
        STATUS              current
        DESCRIPTION         "uplink octet counts"
        ::= { necWimaxBsCidPmNvcEntry 5 }

    necWimaxBsCidPmNvcUlSdu OBJECT-TYPE
        SYNTAX              Counter64
        MAX-ACCESS          read-only
        STATUS              current
        DESCRIPTION         "uplink SDU counts"
        ::= { necWimaxBsCidPmNvcEntry 6 }

    necWimaxBsCidPmStatTable OBJECT-TYPE
        SYNTAX              SEQUENCE OF NecWimaxBsCidPmStatEntry
        MAX-ACCESS          not-accessible
        STATUS              current
        DESCRIPTION         "This table contains PM stat for each CID."
        ::= { necWimaxBsCidPmObjects 3 }

    necWimaxBsCidPmStatEntry OBJECT-TYPE
        SYNTAX              NecWimaxBsCidPmStatEntry
        MAX-ACCESS          not-accessible
        STATUS              current
        DESCRIPTION         "This table provides one row for each CID, and
                            is indexed by ifIndex, necWimaxBsCidPmCid. IfIndex
                            is associated with the BS sector."
        INDEX               {
                                ifIndex,
                                necWimaxBsCidPmCid
                            }
        ::= { necWimaxBsCidPmStatTable 1 }

    NecWimaxBsCidPmStatEntry ::= SEQUENCE {
        necWimaxBsCidPmCid
            Integer32,
        necWimaxBsCidPmStatUlSduUsr
            Counter64,
        necWimaxBsCidPmStatUlSduManage
            Counter64,
        necWimaxBsCidPmStatUlPdu
            Counter64,
        necWimaxBsCidPmStatUlSignaling
            Counter64,
        necWimaxBsCidPmStatUlCrcError
            Counter64,
        necWimaxBsCidPmStatUlDecryptError
            Counter64,
        necWimaxBsCidPmStatDlSduUsr
            Counter64,
        necWimaxBsCidPmStatDlSduManage
            Counter64,
        necWimaxBsCidPmStatDlPdu
            Counter64,
        necWimaxBsCidPmStatDlDiscardedSdu
            Counter64,
        necWimaxBsCidPmStatDlArqRetry
            Counter64,
        necWimaxBsCidPmStatDlArqRetryOver
            Counter64,
        necWimaxBsCidPmStatDlHarqRetry
            Counter64,
        necWimaxBsCidPmStatDlHarqRetryOver
            Counter64,
        necWimaxBsCidPmStatUlHarqRetry
            Counter64,
        necWimaxBsCidPmStatUlHarqRetryOver
            Counter64
    }

    necWimaxBsCidPmCid OBJECT-TYPE
        SYNTAX              Integer32 (1..650000000)
        MAX-ACCESS          not-accessible
        STATUS              current
        DESCRIPTION         "A 16 bit channel identifier to identify the connection
                            being created by DSA."
        ::= { necWimaxBsCidPmStatEntry 1 }

    necWimaxBsCidPmStatUlSduUsr OBJECT-TYPE
        SYNTAX              Counter64
        MAX-ACCESS          read-only
        STATUS              current
        DESCRIPTION         "Received(Uplink) SDU Number for User Data"
        ::= { necWimaxBsCidPmStatEntry 2 }

    necWimaxBsCidPmStatUlSduManage OBJECT-TYPE
        SYNTAX              Counter64
        MAX-ACCESS          read-only
        STATUS              current
        DESCRIPTION         "Received(Uplink) SDU Number for Management Data"
        ::= { necWimaxBsCidPmStatEntry 3 }

    necWimaxBsCidPmStatUlPdu OBJECT-TYPE
        SYNTAX              Counter64
        MAX-ACCESS          read-only
        STATUS              current
        DESCRIPTION         "Received(Uplink) PDU Number"
        ::= { necWimaxBsCidPmStatEntry 4 }

    necWimaxBsCidPmStatUlSignaling OBJECT-TYPE
        SYNTAX              Counter64
        MAX-ACCESS          read-only
        STATUS              current
        DESCRIPTION         "Received(Uplink) MAC Singaling Header Number"
        ::= { necWimaxBsCidPmStatEntry 5 }

    necWimaxBsCidPmStatUlCrcError OBJECT-TYPE
        SYNTAX              Counter64
        MAX-ACCESS          read-only
        STATUS              current
        DESCRIPTION         "Received(Uplink) CRC Error Number"
        ::= { necWimaxBsCidPmStatEntry 6 }

    necWimaxBsCidPmStatUlDecryptError OBJECT-TYPE
        SYNTAX              Counter64
        MAX-ACCESS          read-only
        STATUS              current
        DESCRIPTION         "Received(Uplink) Decryption Error Number"
        ::= { necWimaxBsCidPmStatEntry 7 }

    necWimaxBsCidPmStatDlSduUsr OBJECT-TYPE
        SYNTAX              Counter64
        MAX-ACCESS          read-only
        STATUS              current
        DESCRIPTION         "Transmitted(Downlink) SDU Number for User Data"
        ::= { necWimaxBsCidPmStatEntry 8 }

    necWimaxBsCidPmStatDlSduManage OBJECT-TYPE
        SYNTAX              Counter64
        MAX-ACCESS          read-only
        STATUS              current
        DESCRIPTION         "Transmitted(Downlink) SDU Number for Management
                            Data"
        ::= { necWimaxBsCidPmStatEntry 9 }

    necWimaxBsCidPmStatDlPdu OBJECT-TYPE
        SYNTAX              Counter64
        MAX-ACCESS          read-only
        STATUS              current
        DESCRIPTION         "Transmitted(Downlink) PDU Number"
        ::= { necWimaxBsCidPmStatEntry 10 }

    necWimaxBsCidPmStatDlDiscardedSdu OBJECT-TYPE
        SYNTAX              Counter64
        MAX-ACCESS          read-only
        STATUS              current
        DESCRIPTION         "Transmitted(Downlink) Discarded SDU Number"
        ::= { necWimaxBsCidPmStatEntry 11 }

    necWimaxBsCidPmStatDlArqRetry OBJECT-TYPE
        SYNTAX              Counter64
        MAX-ACCESS          read-only
        STATUS              current
        DESCRIPTION         "Transmitted(Downlink) ARQ Retry Number"
        ::= { necWimaxBsCidPmStatEntry 12 }

    necWimaxBsCidPmStatDlArqRetryOver OBJECT-TYPE
        SYNTAX              Counter64
        MAX-ACCESS          read-only
        STATUS              current
        DESCRIPTION         "Transmitted(Downlink) ARQ Retryover Number"
        ::= { necWimaxBsCidPmStatEntry 13 }

    necWimaxBsCidPmStatDlHarqRetry OBJECT-TYPE
        SYNTAX              Counter64
        MAX-ACCESS          read-only
        STATUS              current
        DESCRIPTION         "Transmitted(Downlink) HARQ Retry Number"
        ::= { necWimaxBsCidPmStatEntry 14 }

    necWimaxBsCidPmStatDlHarqRetryOver OBJECT-TYPE
        SYNTAX              Counter64
        MAX-ACCESS          read-only
        STATUS              current
        DESCRIPTION         "Transmitted(Downlink) HARQ Retryover Number"
        ::= { necWimaxBsCidPmStatEntry 15 }

    necWimaxBsCidPmStatUlHarqRetry OBJECT-TYPE
        SYNTAX              Counter64
        MAX-ACCESS          read-only
        STATUS              current
        DESCRIPTION         "Recieved(Uplink) HARQ Retry Number"
        ::= { necWimaxBsCidPmStatEntry 17 }

    necWimaxBsCidPmStatUlHarqRetryOver OBJECT-TYPE
        SYNTAX              Counter64
        MAX-ACCESS          read-only
        STATUS              current
        DESCRIPTION         "Recieved(Uplink) HARQ Retryover Number"
        ::= { necWimaxBsCidPmStatEntry 18 }

    --
    --
    necWimaxBsIfMibConformance OBJECT IDENTIFIER ::= { necWimaxBsIfMib 5 }

    necWimaxBsIfMibGroups OBJECT IDENTIFIER ::= { necWimaxBsIfMibConformance 1 }

    necWimaxBsIfMibAllObjects OBJECT-GROUP
        OBJECTS {           
                        necWimaxBsCapFragmentSupport,
                        necWimaxBsCapHarqSupport,
                        necWimaxBsCapHarqPduSn,
                        necWimaxBsCapCfgFragmentSupport,
                        necWimaxBsCapCfgHarqSupport,
                        necWimaxBsCapCfgHarqPduSn,
                        necWimaxBsDlUlRatio,
                        necWimaxBsPermutation,
                        necWimaxBsFuscPermBase,
                        necWimaxBsFuscPrbsId,
                        necWimaxBsPreambleId,
                        necWimaxBsSegment,
                        necWimaxBsDlSubchannelBitmap,
                        necWimaxBsUlSubchannelBitmap,
                        necWimaxBsCompressedMap,
                        necWimaxBsDlMapRepitition,
                        necWimaxBsDcdUcdRepitition,
                        necWimaxBsAdmissionThreshold,
                        necWimaxBsMinPhyRateUgs,
                        necWimaxBsMinPhyRateErtps,
                        necWimaxBsMinPhyRateRtps,
                        necWimaxBsMinPhyRateNrtps,
                        necWimaxBsMinPhyRateBe,
                        necWimaxBsAgingTimeout,
                        necWimaxBsUlPuscRoration,
                        necWimaxBsPduSnWaitTime,
                        necWimaxBsBwMode,
                        necWimaxBsMimoEnable,
                        necWimaxBsMimoMatrixMode,
                        necWimaxBsMimoFeedbackCycle,
                        necWimaxBsSsEntryNo,
                        necWimaxBsDlMapEncodeType,
                        necWimaxBsFnRandseed,
                        necWimaxBsSduMaxDelay,
                        necWimaxBsMaxSf,
                        necWimaxBsFrameAdjustThreshold,
                        necWimaxBsFrameSyncMode,
                        necWimaxBsRxInitRangMax,
                        necWimaxBsRxHoRangMax,
                        necWimaxBsRfCableLength,
                        necWimaxBsOduAlarmControl,
                        necWimaxBsTimingGapOffset,
                        necWimaxBsSiiAdvInterval,
                        necWimaxBsGmsEnable,
                        necWimaxBsMacVersion,
                        necWimaxBsMulticastRepetitionCount,
                        necWimaxBsBcpIeTransmitCount,
                        necWimaxBsSegmentUl,
                        necWimaxBsCqichBwReq,
                        necWimaxBsFairnessMode,
                        necWimaxBsFairnessCounterResetPeriod,
                        necWimaxBsMimoUlHarq,
                        necWimaxBsUlMimoEnable,
                        necWimaxBsNumOfSegment,
                        necWimaxBsFairnessCountMode,
                        necWimaxBsAdmissionThresholdDl,
                        necWimaxBsAdmissionThresholdUl,
                        necWimaxBsCongestionThresholdDl,
                        necWimaxBsCongestionThresholdUl,
                        necWimaxBsProportionalShare,
                        necWimaxBsShareRateUlRtvr,
                        necWimaxBsShareRateUlNrtvr,
                        necWimaxBsShareRateUlBe,
                        necWimaxBsShareRateDlRtvr,
                        necWimaxBsShareRateDlNrtvr,
                        necWimaxBsShareRateDlBe,
                        necWimaxBsThroughputCapacityDl,
                        necWimaxBsThroughputCapacityUl,
                        necWimaxBsArqWindowSize,
                        necWimaxBsArqRetryTimerTx,
                        necWimaxBsArqRetryTimerRx,
                        necWimaxBsArqBlcokLifetime,
                        necWimaxBsArqSyncLossTimeout,
                        necWimaxBsArqDeliverInOrder,
                        necWimaxBsArqPurgeTimeout,
                        necWimaxBsArqBlockSize,
                        necWimaxBsArqAckProcTime,
                        necWimaxBsArqAckDelay,
                        necWimaxBsArqT22,
                        necWimaxBsArqT22retry,
                        necWimaxBsMeasurementControlMacAddress,
                        necWimaxBsMeasurementControlRowStatus,
                        necWimaxBsTimerT9,
                        necWimaxBsTimerT17,
                        necWimaxBsTimerT7,
                        necWimaxBsTimerT7retry,
                        necWimaxBsTimerT8,
                        necWimaxBsTimerT8retry,
                        necWimaxBsTimerT10,
                        necWimaxBsTimerEntryAgingTime,
                        necWimaxBsTimerR6T3,
                        necWimaxBsUlmapFeedbackSymStart,
                        necWimaxBsUlmapFeedbackSubchanStart,
                        necWimaxBsUlmapFeedbackSymNumber,
                        necWimaxBsUlmapFeedbackSubchanNumber,
                        necWimaxBsUlmapBwreqSymStart,
                        necWimaxBsUlmapBwreqSubchanStart,
                        necWimaxBsUlmapBwreqSymNumber,
                        necWimaxBsUlmapBwreqSubchanNumber,
                        necWimaxBsUlmapRangingSymStart,
                        necWimaxBsUlmapRangingSubchanStart,
                        necWimaxBsUlmapRangingSymNumber,
                        necWimaxBsUlmapRangingSubchanNumber,
                        necWimaxBsUlmapHarqSymStart,
                        necWimaxBsUlmapHarqSubchanStart,
                        necWimaxBsUlmapHarqSymNumber,
                        necWimaxBsUlmapHarqSubchanNumber,
                        necWimaxBsUlmapPerRngBackoffStart,
                        necWimaxBsUlmapPerRngBackoffEnd,
                        necWimaxBsUlmapInitRngCodes,
                        necWimaxBsUlmapPeriodicRngCodes,
                        necWimaxBsUlmapBWReqCodes,
                        necWimaxBsPwrctrlDlCh,
                        necWimaxBsPwrctrlEirpOffset,
                        necWimaxBsPwrctrlNIinterval,
                        necWimaxBsPwrctrlMode,
                        necWimaxBsPwrctrlCqichRptInterval,
                        necWimaxBsPwrctrlCqichUpdateInterval,
                        necWimaxBsPwrctrlReportFunc,
                        necWimaxBsPwrctrlCqichRptContents,
                        necWimaxBsPwrctrlRepRptInterval,
                        necWimaxBsPwrctrlRateCtrlInterval,
                        necWimaxBsPwrctrlClosedLoopWaitTimer,
                        necWimaxBsPwrctrlThreshold,
                        necWimaxBsPwrctrlLaUlEnable,
                        necWimaxBsPwrctrlCinrReuseFactor,
                        necWimaxBsPwrctrlDlPhyQuality,
                        necWimaxBsPwrctrlTxPower,
                        necWimaxBsPwrctrAntennaGain,
                        necWimaxBsPwrctrlTxPowerOffset,
                        necWimaxBsPwrctrlOpenLoopModeChange,
                        necWimaxBsPwrctrlClosedLoopAdjust,
                        necWimaxBsPwrctrlCinrPriority,
                        necWimaxBsPwrctrlRssiRptInterval,
                        necWimaxBsPwrctrlPathLossAdjust,
                        necWimaxBsPwrctrlRssiAveraging,
                        necWimaxBsPwrctrlDlChMatrixA,
                        necWimaxBsPwrctrlDlChMatrixB,
                        necWimaxBsPwrctrlMatrixCtrlInterval,
                        necWimaxBsPwrctrlDlRateUp,
                        necWimaxBsPwrctrlDlRateDown,
                        necWimaxBsSubchannelisation,
                        necWimaxBsSubchLimit,
                        necWimaxBsSubchThreshold,
                        necWimaxBsPwrctrlLaDlEnable,
                        necWimaxBsPwrctrlRxGain,
                        necWimaxBsPwrctrlRateCtrlOffset,
                        necWimaxBsPwrctrlDlOuterLoopKeepTime,
                        necWimaxBsPwrctrlDlOuterLoop,
                        necWimaxBsPwrctrlUlOuterLoop,
                        necWimaxBsPwrctrlDlRateCtrlInterval,
                        necWimaxBsPwrctrlUlRateCtrlInterval,
                        necWimaxBsPwrctrlUlRateUp,
                        necWimaxBsPwrctrlUlRateDown,
                        necWimaxBsPwrctrlUlMimoMinRate,
                        necWimaxBsPwrctrlUlOuterLoopKeepTime,
                        necWimaxBsPwrctrlDlRateBack,
                        necWimaxBsPwrctrlUlRateBack,
                        necWimaxHwAdjustGtb1Int,
                        necWimaxHwAdjustGtb2Int,
                        necWimaxHwAdjustGtb3Int,
                        necWimaxHwAdjustRssi,
                        necWimaxHwAdjustCinr,
                        necWimaxHwAdjustNIAverage,
                        necWimaxHwAdjustPowerMergin,
                        necWimaxHwAdjustUlBusrtPwrOffset,
                        necWimaxHwAdjustOduNoiseFloor,
                        necWimaxBsPkmEapStartAllow,
                        necWimaxBsBlockageAdminStatus,
                        necWimaxBsBlockageOperationStatus,
                        necWimaxBsCarrierAdminStatus,
                        necWimaxBsCarrierOperationStatus,
                        necWimaxBsNetBlockageAdminStatus,
                        necWimaxBsNetCarrierAdminStatus,
                        necWimaxBsConfLinkMon,
                        necWimaxBsConfLinkHealthCheck,
                        necWimaxBsConfAswgwOamPortTx,
                        necWimaxBsConfAswgwOamPortRx,
                        necWimaxBsConfAuthgwId,
                        necWimaxBsConfAuthgwIp,
                        necWimaxBsConfAuthgwPort,
                        necWimaxBsConfAsngwId,
                        necWimaxBsConfAsngwDpIp,
                        necWimaxBsConfAsngwDpPort,
                        necWimaxBsConfAsngwEpIp,
                        necWimaxBsConfAsngwEpPort,
                        necWimaxBsConfAsngwRxPort,
                        necWimaxBsConfAsngwTimer,
                        necWimaxBsConfAsngwRetry,
                        necWimaxBsLicenseSubscriber,
                        necWimaxBsLicenseUlThroughput,
                        necWimaxBsLicenseDlThroughput,
                        necWimaxBsLicenseHoOptimization,
                        necWimaxBsLicenseFunctions,
                        necWimaxBsLicenseUpdateAction,
                        necWimaxBsLicenseUpdateStatus,
                        necWimaxBsInitParamUpdateAction,
                        necWimaxBsInitParamNewVersion,
                        necWimaxBsInitParamCurrentVersion,
                        necWimaxBsInitParamOldVersion,
                        necWimaxBsIfmCapHoTrigValue,
                        necWimaxBsIfmCapHoTrigDuration,
                        necWimaxBsIfmCapHoIndTimer,
                        necWimaxBsIfmCapHoTrigFunction,
                        necWimaxBsIfmCapCfgHoTrigValue,
                        necWimaxBsIfmCapCfgHoTrigDuration,
                        necWimaxBsIfmCapCfgHoIndTimer,
                        necWimaxBsIfmCapCfgHoTrigFunction,
                        necWimaxBsIfmReqDuration,
                        necWimaxBsIfmPagingRetry,
                        necWimaxBsIfmMobPagAdvTransmitCount,
                        necWimaxBsMobHcCfgHoMode,
                        necWimaxBsMobHcCfgUnsGrantHoind,
                        necWimaxBsMobHcCfgFastRanging,
                        necWimaxBsMobHcCfgActTime,
                        necWimaxBsMobHcCfgT55,
                        necWimaxBsMobHcCfgRscRetain,
                        necWimaxBsMobHcCfgTgtBsSelection,
                        necWimaxBsMobHcCfgRecmdTgtBs,
                        necWimaxBsMobHcCfgThrsldFixed,
                        necWimaxBsMobHcCfgThrsldAuto,
                        necWimaxBsMobHcCfgPreRegAging,
                        necWimaxBsMobHcCfgCidUpdateType,
                        necWimaxBsMobHcCfgSysRscRetainTime,
                        necWimaxBsMobHcCfgFaIndex,
                        necWimaxBsMobNbrAdvFragmentSize,
                        necWimaxBsMobScCnfRptMode,
                        necWimaxBsMobScCnfRptPeriod,
                        necWimaxBsMobScCnfRptMetric,
                        necWimaxBsMobScCnfDuration,
                        necWimaxBsMobScCnfInterleavingInterval,
                        necWimaxBsMobScCnfIteratoin,
                        necWimaxBsMobScCnfTrigValReq,
                        necWimaxBsMobScCnfTrigAveDurationReq,
                        necWimaxBsMobScCnfTrigTypeReq,
                        necWimaxBsMobScCnfTrigFuncReq,
                        necWimaxBsMobScCnfTrigValRep,
                        necWimaxBsMobScCnfTrigAveDurationRep,
                        necWimaxBsMobScCnfTrigTypeRep,
                        necWimaxBsMobScCnfTrigFuncRep,
                        necWimaxBsMobScCnfSleepReact,
                        necWimaxBsMobSmCnfTrfIndRequired,
                        necWimaxBsMobSmCnfTrafficTriggeredWakening,
                        necWimaxBsMobSmCnfTrfIndSlpidFormat,
                        necWimaxBsMobSmCnfEnabledActionTriggered,
                        necWimaxBsMobSmCnfReqDuration,
                        necWimaxBsMobCfgComMonTimer,
                        necWimaxBsRrmScReportChar,
                        necWimaxBsRrmAveragingTime,
                        necWimaxBsRrmScReportingPeriod,
                        necWimaxBsRrmAbsoluteThreshold,
                        necWimaxBsRrmRelativeThreshold,
                        necWimaxBsRrmRcReportChar,
                        necWimaxBsRrmRcReportingPeriod,
                        necWimaxBsRrmScReqRetry,
                        necWimaxBsRrmRcReqRetry,
                        necWimaxBsRrmRcRptRetry,
                        necWimaxBsRrmScReqInterval,
                        necWimaxBsNeighborBsid,
                        necWimaxBsNeighborBsStatus
                }
        STATUS              current
        DESCRIPTION         "This automatically created object group contains
                            all those objects that do not belong to any other
                            OBJECT-GROUP"
        ::= { necWimaxBsIfMibGroups 1 }

    necWimaxBsIfMibPmObjects OBJECT-GROUP
        OBJECTS {           
                        necWimaxBsAirStatUlFecCode,
                        necWimaxBsAirStatUlRssi,
                        necWimaxBsAirStatUlCinr,
                        necWimaxBsAirStatDlFecCode,
                        necWimaxBsAirStatDlRepetition,
                        necWimaxBsAirStatDlMatrixMode,
                        necWimaxBsAirStatDlZoneCinr,
                        necWimaxBsAirStatDlPreambleCinr,
                        necWimaxBsAirStatDlZoneEffectiveCinr,
                        necWimaxBsAirStatDlRssi,
                        necWimaxBsAirStatDlPathLoss,
                        necWimaxBsPmCurrentDlThroughputPdu,
                        necWimaxBsPmCurrentDlThroughputSdu,
                        necWimaxBsPmCurrentDlThroughputIp,
                        necWimaxBsPmCurrentUlThroughputPdu,
                        necWimaxBsPmCurrentUlThroughputSdu,
                        necWimaxBsPmCurrentUlThroughputIp,
                        necWimaxBsPmDlThroughputPduCounter,
                        necWimaxBsPmDlThroughputSduCounter,
                        necWimaxBsPmDlThroughputIpCounter,
                        necWimaxBsPmUlThroughputPduCounter,
                        necWimaxBsPmUlThroughputSduCounter,
                        necWimaxBsPmUlThroughputIpCounter,
                        necWimaxBsThroughputResetCounter,
                        necWimaxBsPmRrmDl,
                        necWimaxBsPmRrmUl,
                        necWimaxBsPmReservDl,
                        necWimaxBsPmReservUl,
                        necWimaxBsPmUsedBandDlUgs,
                        necWimaxBsPmUsedBandDlErtvr,
                        necWimaxBsPmUsedBandDlRtvr,
                        necWimaxBsPmUsedBandDlNrtvr,
                        necWimaxBsPmUsedBandDlBe,
                        necWimaxBsPmUsedBandUlUgs,
                        necWimaxBsPmUsedBandUlErtps,
                        necWimaxBsPmUsedBandUlRtps,
                        necWimaxBsPmUsedBandUlNrtps,
                        necWimaxBsPmUsedBandUlBe,
                        necWimaxBsPmReservDlUgs,
                        necWimaxBsPmReservDlErtvr,
                        necWimaxBsPmReservDlRtvr,
                        necWimaxBsPmReservDlNrtvr,
                        necWimaxBsPmReservUlUgs,
                        necWimaxBsPmReservUlErtps,
                        necWimaxBsPmReservUlRtps,
                        necWimaxBsPmReservUlNrtps,
                        necWimaxBsStatMsNo,
                        necWimaxBsStatUlSduUsr,
                        necWimaxBsStatUlSduManage,
                        necWimaxBsStatUlPdu,
                        necWimaxBsStatUlSignaling,
                        necWimaxBsStatUlCrcError,
                        necWimaxBsStatUlDecryptError,
                        necWimaxBsStatDlSduUsr,
                        necWimaxBsStatDlSduManage,
                        necWimaxBsStatDlPdu,
                        necWimaxBsStatDlDiscardedSdu,
                        necWimaxBsStatDlArqRetry,
                        necWimaxBsStatDlArqRetryOver,
                        necWimaxBsStatDlHarqRetry,
                        necWimaxBsStatDlHarqRetryOver,
                        necWimaxBsStatResetCounter,
                        necWimaxBsStatUlHarqRetry,
                        necWimaxBsStatUlHarqRetryOver,
                        necWimaxBsPmSfCreateCount,
                        necWimaxBsPmSfCreateFailCount,
                        necWimaxBsPmSfDeleteCount,
                        necWimaxBsPmSfPermitCount,
                        necWimaxBsPmSfRejectCount,
                        necWimaxBsPmSfResetCounter,
                        necWimaxBsPmHoMshoReqCount,
                        necWimaxBsPmHoBshoRspCount,
                        necWimaxBsPmHoHoIndCount,
                        necWimaxBsPmHoCfmType1Count,
                        necWimaxBsPmHoCfmType2Count,
                        necWimaxBsPmHoRngReqCount,
                        necWimaxBsPmHoRngRspCount,
                        necWimaxBsPmHoKeyCountUpdateCount,
                        necWimaxBsPmHoResetCounter,
                        necWimaxBsPmCongestionCount,
                        necWimaxBsPmCongestionResetCounter,
                        necWimaxBsPmMobPagAdvCount,
                        necWimaxBsPmPagingResetCounter,
                        necWimaxBsPmNwentrySuccess,
                        necWimaxBsPmNwentryFail,
                        necWimaxBsPmNwentryFailMsNumOver,
                        necWimaxBsPmNwentryFailAuthErr,
                        necWimaxBsPmNwentryFailAdmissionErr,
                        necWimaxBsPmNwentryFailOther,
                        necWimaxBsPmNwentryResetCounter,
                        necWimaxBsPmSleepMsNum,
                        necWimaxBsSsPmSleepPscNum,
                        necWimaxBsSleepPsc,
                        necWimaxBsSsPscPmSleepWindowSize,
                        necWimaxBsSsPscPmListeningWindowSize,
                        necWimaxBsSsPmDlThroughputPduCounter,
                        necWimaxBsSsPmDlThroughputSduCounter,
                        necWimaxBsSsPmDlThroughputIpCounter,
                        necWimaxBsSsPmUlThroughputPduCounter,
                        necWimaxBsSsPmUlThroughputSduCounter,
                        necWimaxBsSsPmUlThroughputIpCounter,
                        necWimaxBsSsPmThroughputResetCounter,
                        necWimaxBsSsPmPacketLossRate,
                        necWimaxBsSsPmNumOfGre,
                        necWimaxBsSsPmStatUlSduUsr,
                        necWimaxBsSsPmStatUlSduManage,
                        necWimaxBsSsPmStatUlPdu,
                        necWimaxBsSsPmStatUlSignaling,
                        necWimaxBsSsPmStatUlCrcError,
                        necWimaxBsSsPmStatUlDecryptError,
                        necWimaxBsSsPmStatDlSduUsr,
                        necWimaxBsSsPmStatDlSduManage,
                        necWimaxBsSsPmStatDlPdu,
                        necWimaxBsSsPmStatDlDiscardedSdu,
                        necWimaxBsSsPmStatDlArqRetry,
                        necWimaxBsSsPmStatDlArqRetryOver,
                        necWimaxBsSsPmStatDlHarqRetry,
                        necWimaxBsSsPmStatDlHarqRetryOver,
                        necWimaxBsSsPmStatUlHarqRetry,
                        necWimaxBsSsPmStatUlHarqRetryOver,
                        necWimaxBsSsPmStatResetCounter,
                        necWimaxBsCidPmDlThroughputPduCounter,
                        necWimaxBsCidPmDlThroughputSduCounter,
                        necWimaxBsCidPmDlThroughputIpCounter,
                        necWimaxBsCidPmUlThroughputPduCounter,
                        necWimaxBsCidPmUlThroughputSduCounter,
                        necWimaxBsCidPmUlThroughputIpCounter,
                        necWimaxBsCidPmStatUlSduUsr,
                        necWimaxBsCidPmStatUlSduManage,
                        necWimaxBsCidPmStatUlPdu,
                        necWimaxBsCidPmStatUlSignaling,
                        necWimaxBsCidPmStatUlCrcError,
                        necWimaxBsCidPmStatUlDecryptError,
                        necWimaxBsCidPmStatDlSduUsr,
                        necWimaxBsCidPmStatDlSduManage,
                        necWimaxBsCidPmStatDlPdu,
                        necWimaxBsCidPmStatDlDiscardedSdu,
                        necWimaxBsCidPmStatDlArqRetry,
                        necWimaxBsCidPmStatDlArqRetryOver,
                        necWimaxBsCidPmStatDlHarqRetry,
                        necWimaxBsCidPmStatDlHarqRetryOver,
                        necWimaxBsCidPmStatUlHarqRetry,
                        necWimaxBsCidPmStatUlHarqRetryOver
                }
        STATUS              current
        DESCRIPTION         "These objects are related to performance monitor"
        ::= { necWimaxBsIfMibGroups 2 }


END
