WMAN-IF2-MIB DEFINITIONS ::= BEGIN
    IMPORTS
    MODULE-IDENTITY, OBJECT-TYPE, Unsigned32,
    Integer32, Counter64
        FROM SNMPv2-SMI
    TEXTUAL-CONVENTION, MacAddress, RowStatus,
    TruthValue, TimeStamp
        FROM SNMPv2-TC
    OBJECT-GROUP, MODULE-COMPLIANCE
        FROM SNMPv2-CONF
    ifIndex
        FROM IF-MIB;

    wmanIf2Mib MODULE-IDENTITY
        LAST-UPDATED        "200705220000Z"
        --May 22, 2007
        ORGANIZATION        "IEEE 802.16"
        CONTACT-INFO        "WG E-mail: stds-802-16@ieee.org       
                            WG Chair: Roger B.
                            Marks
                            Postal: NextWave Broadband,
                            Inc.
                            E-mail: r.b.marks@ieee.org
                            
                            TG Chair: Phillip
                            Barber
                            Postal: Huawei Technologies
                            Co., Ltd
                            E-mail: pbarber@futurewei.com
                            Editor: Joey Chou
                            Postal: Intel Corporation
                            5000 W. Chandler Blvd,
                            Chandler, AZ 85227,
                            USA
                            E-mail: joey.chou@intel.com"
        DESCRIPTION         "This material is from IEEE Std 802.16i Copyright
                            (c) 2007 IEEE. This MIB Module defines managed
                            objects for Subscriber Station and Base Station
                            based on IEEE Std 802.16-2004 and its amendment
                            IEEE Std 802.16e-2005. The MIB contains managed
                            objects that are common for both fixed and mobile
                            Broadband Wireless Networks."

        REVISION            "200705220000Z"
        DESCRIPTION         "Includes changes as per comment resolutions agreed
                            at the Portland meeting"
        REVISION            "200703280000Z"
        DESCRIPTION         "Includes changes as per comment resolutions agreed
                            at the Orlando meeting"
        REVISION            "200702100000Z"
        DESCRIPTION         "Includes changes as per comment resolutions agreed
                            at the London meeting"
        REVISION            "200605230000Z"
        DESCRIPTION         "The first revision of WMAN-IF2-MIB module that
                            is enhanced to support IEEE 802.16e-2005 standard."
        ::= { iso(1) std(0) iso8802(8802) wman(16) 2 }

    --Textual Conventions
    WmanIf2SfSchedulingType ::= TEXTUAL-CONVENTION
        STATUS              current
        DESCRIPTION         "The scheduling service provided by a SC for an
                            upstream service flow. If the parameter is omitted
                            from an upstream QOS Parameter Set, this object
                            takes the value of bestEffort (2). This parameter
                            must be reported as undefined (1) for downstream
                            QOS Parameter Sets. Modified by NEC to represet
                            not only upstream but downstream. So undefined (1)
                            must not be used."
        SYNTAX              INTEGER {
                                undefined( 1 ),
                                bestEffort( 2 ),
                                nonRealTimePollingService( 3 ),
                                realTimePollingService( 4 ),
                                extRealTimePollingService( 5 ),
                                unsolicitedGrantService( 6 )
                            }

    WmanIf2PhsRuleVerify ::= TEXTUAL-CONVENTION
        STATUS              current
        DESCRIPTION         "The value of this field indicates to the sending
                            entity whether or not the packet header contents
                            are to be verified prior to performing suppression.
                            If PHSV is enabled, the sender shall compare
                            the bytes in the packet header with the bytes
                            in the PHSF that are to be suppressed as indicated
                            by the PHSM."
        SYNTAX              INTEGER {
                                phsVerifyEnable( 0 ),
                                phsVerifyDisable( 1 )
                            }

    WmanIf2ClassifierBitMap ::= TEXTUAL-CONVENTION
        STATUS              current
        DESCRIPTION         "A bit of of this object is set to 1 if the parameter
                            indicated by the comment was present in the classifier
                            encoding, and 0 otherwise. Note: that BITS are
                            encoded most significant bit first, so that if
                            e.g. bits 6 and 7 are set, this object is encoded
                            as the octet string '030000'H."
        SYNTAX              BITS {
                                priority( 0 ),
                                ipTos( 1 ),
                                ipProtocol( 2 ),
                                ipMaskedSrcAddr( 3 ),
                                ipMaskedDestAddr( 4 ),
                                srcPort( 5 ),
                                destPort( 6 ),
                                destMacAddr( 7 ),
                                srcMacAddr( 8 ),
                                ethernetProtocol( 9 ),
                                userPriority( 10 ),
                                vlanId( 11 ),
                                ipv6FlowLabel( 12 ),
                                actionRule( 13 )
                            }

    WmanIf2SfState ::= TEXTUAL-CONVENTION
        STATUS              current
        DESCRIPTION         "Defines the state of a service flow."
        SYNTAX              INTEGER {
                                authorized( 1 ),
                                admitted( 2 ),
                                active( 3 )
                            }

    WmanIf2ServClassName ::= TEXTUAL-CONVENTION
        STATUS              current
        DESCRIPTION         "Defines the type of service class name."
        SYNTAX              OCTET STRING (SIZE(2..128))

    WmanIf2CsSpecification ::= TEXTUAL-CONVENTION
        STATUS              current
        DESCRIPTION         "Defines the types of convergence sublayer."
        SYNTAX              INTEGER {
                                reserved( 0 ),
                                packetIpV4( 1 ),
                                packetIpV6( 2 ),
                                packet802dot3Ethernet( 3 ),
                                packet802dot1QVlan( 4 ),
                                packetIpV4Over802dot3( 5 ),
                                packetIpV6Over802dot3( 6 ),
                                packetIpV4Over802dot1Q( 7 ),
                                packetIpV6Over802dot1Q( 8 ),
                                atm( 9 ),
                                packet802dot3EthernetRohcHc( 10 ),
                                packet802dot3EthernetEcrtpHc( 11 ),
                                packetIp2RohcHc( 12 ),
                                packetIp2EcrtpHc( 13 )
                            }

    WmanIf2MacVersion ::= TEXTUAL-CONVENTION
        STATUS              current
        DESCRIPTION         "Version number of IEEE 802.16."
        SYNTAX              INTEGER {
                                ieee802Dot16Of2001( 1 ),
                                ieee802Dot16cOf2002( 2 ),
                                ieee802Dot16aOf2003( 3 ),
                                ieee802Dot16Of2004( 4 ),
                                ieee802Dot16e( 5 ),
                                tbd( 6 )
                            }

    WmanIf2CidType ::= TEXTUAL-CONVENTION
        STATUS              current
        DESCRIPTION         "Type of CID."
        SYNTAX              Integer32 (0..65535)

    WmanIf2DataEncryptAlgId ::= TEXTUAL-CONVENTION
        STATUS              current
        DESCRIPTION         "Data encryption algorithm identifiers."
        SYNTAX              INTEGER {
                                none( 0 ),
                                des56BitCbcMode( 1 ),
                                aes128BitCcmMode( 2 ),
                                aes128BitCbcMode( 3 ),
                                aes128BitCtrMode( 128 )
                            }

    WmanIf2DataAuthAlgId ::= TEXTUAL-CONVENTION
        STATUS              current
        DESCRIPTION         "Data authentication algorithm identifiers."
        SYNTAX              INTEGER {
                                noDataAuthentication( 0 ),
                                aes128BitCcmMode( 1 )
                            }

    WmanIf2TekEncryptAlgId ::= TEXTUAL-CONVENTION
        STATUS              current
        DESCRIPTION         "TEK encryption algorithm identifiers."
        SYNTAX              INTEGER {
                                tripleDes128BitKey( 1 ),
                                rsa1024BitKey( 2 ),
                                aes128BitKeyEcbMode( 3 ),
                                aes128BitKeyWrap( 4 )
                            }

    WmanIf2PkmErrorCode ::= TEXTUAL-CONVENTION
        STATUS              current
        DESCRIPTION         "This error code provides further information about
                            an Authorization Reject, Key Reject, Authorization
                            Invalid, or TEK Invalid. 0 - no failure 1 - unauthorized
                            SS 2 - unauthorized SAID 3 - unsolicited 4 -
                            invalid key sequence 5 - key request authentication
                            failure The following are error code for permanent
                            authorization failure that indicates any reattempts
                            at authorization would continue to result in
                            Authorization Rejects. 6 - the BS does not have
                            the CA certificate belonging to the issuer of
                            an SS certificate 7 - SS certificate has an invalid
                            signature 8 - ASN.1 parsing failure during verification
                            of SS certificate 9 - SS certificate is on the
                            'hot list' 10 - inconsistencies between certificate
                            data and data in accompanying PKM attributes
                            11 - SS and BS have incompatible security capabilities"
        SYNTAX              INTEGER {
                                noFailure( 0 ),
                                unauthorizedSs( 1 ),
                                unauthorizedSaid( 2 ),
                                unsolicited( 3 ),
                                invalidKeySequence( 4 ),
                                keyReqAuthFailure( 5 ),
                                umknownManufactur( 6 ),
                                invalidSignature( 7 ),
                                asn1ParsingFailure( 8 ),
                                ssCaOnHotList( 9 ),
                                dataInconsistency( 10 ),
                                ssBsIncompatibleSc( 11 )
                            }

    WmanIf2SaType ::= TEXTUAL-CONVENTION
        STATUS              current
        DESCRIPTION         "The type of Security Association (SA)."
        SYNTAX              INTEGER {
                                primarySa( 0 ),
                                staticSa( 1 ),
                                dynamicSa( 2 )
                            }

    WmanIf2TekState ::= TEXTUAL-CONVENTION
        STATUS              current
        DESCRIPTION         "TEK State."
        SYNTAX              INTEGER {
                                start( 1 ),
                                opWait( 2 ),
                                opReauthWait( 3 ),
                                operational( 4 ),
                                rekeyWait( 5 ),
                                rekeyReauthWait( 6 )
                            }

    WmanIf2CertificateStat ::= TEXTUAL-CONVENTION
        STATUS              current
        DESCRIPTION         "The reason why a SS's certificate is deemed valid
                            or invalid: 0 - return unknown if the SS is running
                            PKM mode 1 - means the certificate is valid because
                            it chains to a valid certificate 2 - means the
                            certificate is valid because it has been provisioned
                            to be trusted 3 - means the certificate is invalid
                            because it has been provisioned to be untrusted.
                            4 - means the certificate is invalid because
                            it chains to an untrusted certificate. 5 - refer
                            to errors in parsing, validity periods, etc,
                            of SS certificate 6 - refer to errors in parsing,
                            validity periods, etc, of CA certificate"
        SYNTAX              INTEGER {
                                unknown( 0 ),
                                validSsChained( 1 ),
                                validSsTrusted( 2 ),
                                invalidSsUntrusted( 3 ),
                                invalidCAUntrusted( 4 ),
                                invalidSsOther( 5 ),
                                invalidCAOther( 6 )
                            }

    WmanIf2ChannelNumber ::= TEXTUAL-CONVENTION
        STATUS              current
        DESCRIPTION         "Physical channel number"
        SYNTAX              Integer32 (0..199)

    WmanIf2OfdmFecCodeType ::= TEXTUAL-CONVENTION
        STATUS              current
        DESCRIPTION         "FEC code type and modulation type"
        SYNTAX              INTEGER {
                                bpskCc1Over2( 0 ),
                                qpskRsCcCc1Over2( 1 ),
                                qpskRsCcCc3Over4( 2 ),
                                sixteenQamRsCcCc1Over2( 3 ),
                                sixteenQamRsCcCc3Over4( 4 ),
                                sixtyFourQamRsCcCc2Over3( 5 ),
                                sixtyFourQamRsCcCc3Over4( 6 ),
                                qpskBtc1Over2( 7 ),
                                qpskBtc3Over4( 8 ),
                                sixteenQamBtc3Over4( 9 ),
                                sixteenQamBtc4Over5( 10 ),
                                sixtyFourQamBtc2Over3( 11 ),
                                sixtyFourQamBtc5Over6( 12 ),
                                qpskCtc1Over2( 13 ),
                                qpskCtc2Over3( 14 ),
                                qpskCtc3Over4( 15 ),
                                sixteenQamCtc1Over2( 16 ),
                                sixteenQamCtc3Over4( 17 ),
                                sixtyFourQamCtc2Over3( 18 ),
                                sixtyFourQamCtc3Over4( 19 )
                            }

    WmanIf2OfdmaFecCodeType ::= TEXTUAL-CONVENTION
        STATUS              current
        DESCRIPTION         "FEC code type and modulation type"
        SYNTAX              INTEGER {
                                qpskCc1Over2( 0 ),
                                qpskCc3Over4( 1 ),
                                sixteenQamCc1Over2( 2 ),
                                sixteenQamCc3Over4( 3 ),
                                sixtyFourQamCc2Over3( 4 ),
                                sixtyFourQamCc3Over4( 5 ),
                                qpskBtc1Over2( 6 ),
                                qpskBtc2Over3( 7 ),
                                sixteenQamBtc3Over5( 8 ),
                                sixteenQamBtc4Over5( 9 ),
                                sixtyFourQamBtc5Over8( 10 ),
                                sixtyFourQamBtc4Over5( 11 ),
                                qpskCtc1Over2( 12 ),
                                qpskCtc2Over3( 13 ),
                                qpskCtc3Over4( 14 ),
                                sixteenQamCtc1Over2( 15 ),
                                sixteenQamCtc3Over4( 16 ),
                                sixtyFourQamCtc2Over3( 17 ),
                                sixtyFourQamCtc3Over4( 18 ),
                                sixtyFourQamCtc5Over6( 19 ),
                                qpskZtCc1Over2( 20 ),
                                qpskZtCc3Over4( 21 ),
                                sixteenQamZtCc1Over2( 22 ),
                                sixteenQamZtCc3Over4( 23 ),
                                sixtyFourQamZtCc2Over3( 24 ),
                                sixtyFourQamZtCc3Over4( 25 )
                            }

    WmanIf2OfdmaUcdFecCode ::= TEXTUAL-CONVENTION
        STATUS              current
        DESCRIPTION         "UCD FEC code type and modulation type"
        SYNTAX              INTEGER {
                                qpskCc1Over2( 0 ),
                                qpskCc3Over4( 1 ),
                                sixteenQamCc1Over2( 2 ),
                                sixteenQamCc3Over4( 3 ),
                                sixtyFourQamCc1Over2( 4 ),
                                sixtyFourQamCc2Over3( 5 ),
                                sixtyFourQamCc3Over4( 6 ),
                                qpskBtc1Over2( 7 ),
                                qpskBtc3Over4( 8 ),
                                sixteenQamBtc3Over5( 9 ),
                                sixteenQamBtc4Over5( 10 ),
                                sixtyFourQamBtc5Over8( 11 ),
                                sixtyFourQamBtc4Over5( 12 ),
                                qpskCtc1Over2( 13 ),
                                reserved( 14 ),
                                qpskCtc3Over4( 15 ),
                                sixteenQamCtc1Over2( 16 ),
                                sixteenQamCtc3Over4( 17 ),
                                sixtyFourQamCtc1Over2( 18 ),
                                sixtyFourQamCtc2Over3( 19 ),
                                sixtyFourQamCtc3Over4( 20 ),
                                sixtyFourQamCtc5Over6( 21 ),
                                qpskZtCc1Over2( 22 ),
                                qpskZtCc3Over4( 23 ),
                                sixteenQamZtCc1Over2( 24 ),
                                sixteenQamZtCc3Over4( 25 ),
                                sixtyFourQamZtCc1Over2( 26 ),
                                sixtyFourQamZtCc2Over3( 27 ),
                                sixtyFourQamZtCc3Over4( 28 ),
                                qpskLdpc1over2( 29 ),
                                qpskLdpc2over3A( 30 ),
                                qpskLdpc3over4A( 31 ),
                                sixteenQamLdpc1over2( 32 ),
                                sixteenQamLdpc2over3A( 33 ),
                                sixteenQamLdpc3over4A( 34 ),
                                sixtyFourQamLdpc1over2( 35 ),
                                sixtyFourQamLdpc2over3A( 36 ),
                                sixtyFourQamLdpc3over4A( 37 ),
                                qpskLdpc2over3B( 38 ),
                                qpskLdpc3over4B( 39 ),
                                sixteenQamLdpc2over3B( 40 ),
                                sixteenQamLdpc3over4B( 41 ),
                                sixtyFourQamLdpc2over3B( 42 ),
                                sixtyFourQamLdpc3over4B( 43 ),
                                qpskCcOptIntv1over2( 44 ),
                                qpskCcOptIntv3over4( 45 ),
                                sixteenQamCcOptIntv1over2( 46 ),
                                sixteenQamCcOptIntv3over4( 47 ),
                                sixtyFourQamCcOptIntv2over3( 48 ),
                                sixtyFourQamCcOptIntv3over4( 49 ),
                                qpskLdpc5over6( 50 ),
                                sixteenQamLdpc5over6( 51 ),
                                sixtyFourQamLdpc5over6( 52 )
                            }

    WmanIf2OfdmaDcdFecCode ::= TEXTUAL-CONVENTION
        STATUS              current
        DESCRIPTION         "DCD FEC code type and modulation type"
        SYNTAX              INTEGER {
                                qpskCc1Over2( 0 ),
                                qpskCc3Over4( 1 ),
                                sixteenQamCc1Over2( 2 ),
                                sixteenQamCc3Over4( 3 ),
                                sixtyFourQamCc1Over2( 4 ),
                                sixtyFourQamCc2Over3( 5 ),
                                sixtyFourQamCc3Over4( 6 ),
                                qpskBtc1Over2( 7 ),
                                qpskBtc3Over4Or2Over3( 8 ),
                                sixteenQamBtc3Over5( 9 ),
                                sixteenQamBtc4Over5( 10 ),
                                sixtyFourQamBtc2Over3Or5Over8( 11 ),
                                sixtyFourQamBtc5Over6Or4Over5( 12 ),
                                qpskCtc1Over2( 13 ),
                                reserved14( 14 ),
                                qpskCtc3Over4( 15 ),
                                sixteenQamCtc1Over2( 16 ),
                                sixteenQamCtc3Over4( 17 ),
                                sixtyFourQamCtc1Over2( 18 ),
                                sixtyFourQamCtc2Over3( 19 ),
                                sixtyFourQamCtc3Over4( 20 ),
                                sixtyFourQamCtc5Over6( 21 ),
                                qpskZtCc1Over2( 22 ),
                                qpskZtCc3Over4( 23 ),
                                sixteenQamZtCc1Over2( 24 ),
                                sixteenQamZtCc3Over4( 25 ),
                                sixtyFourQamZtCc1Over2( 26 ),
                                sixtyFourQamZtCc2Over3( 27 ),
                                sixtyFourQamZtCc3Over4( 28 ),
                                reserved29( 29 ),
                                reserved30( 30 ),
                                reserved31( 31 ),
                                reserved32( 32 ),
                                reserved33( 33 ),
                                reserved34( 34 ),
                                reserved35( 35 ),
                                reserved36( 36 ),
                                reserved37( 37 ),
                                reserved38( 38 ),
                                reserved39( 39 ),
                                reserved40( 40 ),
                                reserved41( 41 ),
                                reserved42( 42 ),
                                reserved43( 43 ),
                                qpskCcOptIntv1over2( 44 ),
                                qpskCcOptIntv3over4( 45 ),
                                sixteenQamCcOptIntv1over2( 46 ),
                                sixteenQamCcOptIntv3over4( 47 ),
                                sixtyFourQamCcOptIntv2over3( 48 ),
                                sixtyFourQamCcOptIntv3over4( 49 )
                            }

    --Textual convention for capabilities encodings
    WmanIf2NumOfCid ::= TEXTUAL-CONVENTION
        STATUS              current
        DESCRIPTION         "The object of this type shows the number of CIDs
                            that SS can support."
        SYNTAX              Integer32 (2..65535)

    WmanIf2ArqSupportType ::= TEXTUAL-CONVENTION
        STATUS              current
        DESCRIPTION         "The object of this type indicates whether the
                            SS support ARQ."
        SYNTAX              INTEGER {
                                arqNotSupported( 0 ),
                                arqSupported( 1 )
                            }

    WmanIf2MaxDsxFlowType ::= TEXTUAL-CONVENTION
        STATUS              current
        DESCRIPTION         "The object of this type specifies the maximum
                            number of concurrent DSA, DSC, or DSD transactions
                            that may be outstanding."
        SYNTAX              Integer32 (0..255)

    WmanIf2MacCrcSupport ::= TEXTUAL-CONVENTION
        STATUS              current
        DESCRIPTION         "The object of this type indicates whether or not
                            the SS supports MAC level CRC."
        SYNTAX              INTEGER {
                                noMacCrcSupport( 0 ),
                                macCrcSupport( 1 )
                            }

    WmanIf2MaxMcaFlowType ::= TEXTUAL-CONVENTION
        STATUS              current
        DESCRIPTION         "The object of this type specifies the maximum
                            number of concurrent MCA transactions that may
                            be outstanding."
        SYNTAX              Integer32 (0..255)

    WmanIf2MaxMcpGroupCid ::= TEXTUAL-CONVENTION
        STATUS              current
        DESCRIPTION         "The object of this type indicates the maximum
                            number of simultaneous Multicast Polling Groups
                            the SS is capable of belonging to."
        SYNTAX              Integer32 (0..255)

    WmanIf2MaxPkmFlowType ::= TEXTUAL-CONVENTION
        STATUS              current
        DESCRIPTION         "The object of this type specifies the maximum
                            number of concurrent PKM transactions that may
                            be outstanding."
        SYNTAX              Integer32 (0..255)

    WmanIf2AuthPolicyType ::= TEXTUAL-CONVENTION
        STATUS              current
        DESCRIPTION         "The object of this type specifies authorization
                            policy that both SS and BS need to negotiate
                            and synchronize. A bit value of 0 = 'not supported',
                            1 = 'supported'. If this field is omitted, then
                            both SS and BS shall use the IEEE 802.16 security,
                            constituting X.509 digital certificates and the
                            RSA public key encryption algorithm, as authorization
                            policy."
        SYNTAX              BITS {
                                ieee802Dot16PrivacySupported( 0 ),
                                reserved1( 1 ),
                                reserved2( 2 ),
                                reserved3( 3 ),
                                reserved4( 4 ),
                                reserved5( 5 ),
                                reserved6( 6 ),
                                reserved7( 7 )
                            }

    WmanIf2MaxNumOfSaType ::= TEXTUAL-CONVENTION
        STATUS              current
        DESCRIPTION         "This field specifies maximum number of supported
                            security association of the SS."
        SYNTAX              Integer32 (0..255)

    WmanIf2IpVersionType ::= TEXTUAL-CONVENTION
        STATUS              current
        DESCRIPTION         "The object of this type indicates the version
                            of IP used on the Secondary Management Connection.
                            The valus should be undefined if the 2nd management
                            CID doesn't exist."
        SYNTAX              INTEGER {
                                undefined( 0 ),
                                ipv4( 1 ),
                                ipv6( 2 )
                            }

    WmanIf2MacCsBitMap ::= TEXTUAL-CONVENTION
        STATUS              current
        DESCRIPTION         "The object of this type indicates the set of MAC
                            convergence sublayer support. When a bit is set,
                            it indicates the corresponding CS feature is
                            supported."
        SYNTAX              BITS {
                                atm( 0 ),
                                packetIpv4( 1 ),
                                packetIpv6( 2 ),
                                packet802Dot3( 3 ),
                                packet802Dot1Q( 4 ),
                                packetIpv4Over802Dot3( 5 ),
                                packetIpv6Over802Dot3( 6 ),
                                packetIpv4Over802Dot1Q( 7 ),
                                packetIpv6Over802Dot1Q( 8 ),
                                packet802dot3EthernetRohcHc( 9 ),
                                packet802dot3EthernetEcrtpHc( 10 ),
                                packetIpv4Orv6RohcHc( 11 ),
                                packetIpv4Orv6EcrtpHc( 12 )
                            }

    WmanIf2MaxClassifiers ::= TEXTUAL-CONVENTION
        STATUS              current
        DESCRIPTION         "The object of this type indicates the maximum
                            number of admitted Classifiers that the SS is
                            allowed to have."
        SYNTAX              Integer32 (0..65535)

    WmanIf2PhsSupportType ::= TEXTUAL-CONVENTION
        STATUS              current
        DESCRIPTION         "The object of this type indicates the level of
                            PHS support."
        SYNTAX              INTEGER {
                                noPhsSupport( 0 ),
                                atmPhsSupport( 1 ),
                                packetPhsSupport( 2 ),
                                atmAndPacketPhsSupport( 3 )
                            }

    WmanIf2BwAllocSupport ::= TEXTUAL-CONVENTION
        STATUS              current
        DESCRIPTION         "This field indicates properties of the SS that
                            the BS needs to know for bandwidth allocation
                            purposes. When a bit is set, it indicates the
                            corresponding feature is supported. All unspecified
                            and reserved bits should be set to zero."
        SYNTAX              BITS {
                                reserved( 0 ),
                                halfDuplexFdd( 1 ),
                                fullDuplexFdd( 2 )
                            }

    WmanIf2PduConstruction ::= TEXTUAL-CONVENTION
        STATUS              current
        DESCRIPTION         "Specifies capabilities for construction and transmission
                            of MAC PDUs. When piggybackedRequests bit is
                            set, it indicates that the piggybacked requests
                            are supported. The fsnValuesSize bit is coded
                            as follows: 0 - only 3-bit FSN values are supported
                            1 - only 11-bit FSN values are supported All
                            unspecified and reserved bits should be set to
                            zero."
        SYNTAX              BITS {
                                piggybackedRequests( 0 ),
                                fsnValuesSize( 1 )
                            }

    WmanIf2SsTransitionGap ::= TEXTUAL-CONVENTION
        STATUS              current
        DESCRIPTION         "This field indicates the transition speed SSTTG
                            and SSRTG for TDD and H-FDD SSs. Allowed values
                            are: OFDM mode: TDD and H-FDD 0..100 Other modes:
                            TDD: 0..50; H-FDD: 0..100"
        SYNTAX              Integer32 (0..100)

    WmanIf2MaxTxPowerType ::= TEXTUAL-CONVENTION
        STATUS              current
        DESCRIPTION         "This type is used to define maximum available
                            power for BPSK, QPSK, 16-QAM and 64-QAM constellations.
                            The maximum power parameters are reported in
                            dBm and quantized in 0.5 dBm steps ranging from
                            -64 dBm (encoded 0x00) to 63.5 dBm (encoded 0xFF).
                            Values outside this range shall be assigned the
                            closest extreme. SSs that do not support QAM64
                            shall report the value of 0x00 in the maximum
                            QAM64 power field."
        SYNTAX              Integer32 (0..255)

    WmanIf2OfdmFftSizes ::= TEXTUAL-CONVENTION
        STATUS              current
        DESCRIPTION         "This field indicates the FFT sizes supported by
                            the SS. For each FFT size, a bit value of 0 indicates
                            'not supported' while 1 indicates 'supported'."
        SYNTAX              BITS {
                                fft256( 0 ),
                                fft2048( 1 )
                            }

    WmanIf2OfdmSsDeModType ::= TEXTUAL-CONVENTION
        STATUS              current
        DESCRIPTION         "This field indicates the different demodulator
                            options supported by a WirelessMAN-OFDM PHY SS
                            for downlink. This field is not used for other
                            PHY specifications. A bit value of 0 indicates
                            'not supported' while 1 indicates 'supported'."
        SYNTAX              BITS {
                                qam64( 0 ),
                                btc( 1 ),
                                ctc( 2 ),
                                stc( 3 ),
                                aas( 4 ),
                                subchannelization( 5 )
                            }

    WmanIf2OfdmSsModType ::= TEXTUAL-CONVENTION
        STATUS              current
        DESCRIPTION         "This field indicates the different modulator options
                            supported by a WirelessMAN-OFDM PHY SS for uplink.
                            This field is not used for other PHY specifications.
                            A bit value of 0 indicates 'not supported' while
                            1 indicates 'supported'."
        SYNTAX              BITS {
                                qam64( 0 ),
                                btc( 1 ),
                                ctc( 2 ),
                                subchannelization( 3 ),
                                focusedCtBwReq( 4 ),
                                ulCyclicDelay( 5 )
                            }

    WmanIf2OfdmFocusedCt ::= TEXTUAL-CONVENTION
        STATUS              current
        DESCRIPTION         "This field indicates whether the SS supports Focused
                            Contention (see 8.3.7.3.3). A bit value of 0
                            indicates 'not supported' while 1 indicates 'supported'."
        SYNTAX              BITS {
                                focusedCtSupport( 0 )
                            }

    WmanIf2OfdmTcSublayer ::= TEXTUAL-CONVENTION
        STATUS              current
        DESCRIPTION         "This field indicates whether or not the SS supports
                            the TC sublayer (see 8.3.4). A bit value of 0
                            indicates 'not supported' while 1 indicates 'supported'."
        SYNTAX              BITS {
                                tcSublayerSupport( 0 )
                            }

    WmanIf2OfdmPrivMap ::= TEXTUAL-CONVENTION
        STATUS              current
        DESCRIPTION         "This field indicates if the private map parameters
                            are supported. A bit value of 0 indicates 'not
                            supported' while 1 indicates 'supported'."
        SYNTAX              BITS {
                                regularMap( 0 ),
                                compressedMap( 1 )
                            }

    WmanIf2OfdmUlPower ::= TEXTUAL-CONVENTION
        STATUS              current
        DESCRIPTION         "This field indicates the uplink power control
                            options supported by a WirelessMAN-OFDM PHY SS
                            for uplink transmission. A bit value of 0 indicates
                            'not supported' while 1 indicates 'supported'."
        SYNTAX              BITS {
                                ulOpenLoopPwrCntl( 0 ),
                                ulAasPreamblePwrCntl( 1 )
                            }

    WmanIf2BsIdType ::= TEXTUAL-CONVENTION
        STATUS              current
        DESCRIPTION         "Defines the encoding of BSID. The BSID is a 6
                            byte number and follows the encoding rules of
                            MacAddress textual convention, i.e. as if it
                            were transmitted least-significant bit first.
                            The value should be displayed with 2 parts clearly
                            separated by a colon e.g: 001DFF:00003A. The
                            most significant part is representing the Operator
                            ID."
        SYNTAX              OCTET STRING (SIZE(6))

    WmanIf2Ipv6FlowLabel ::= TEXTUAL-CONVENTION
        STATUS              current
        DESCRIPTION         "The value of this field specifies the matching
                            values for the IPv6 Flow label field. As the
                            flow label field has a length of 20 bits, the
                            first 4 bits of the most significant byte shall
                            be set to 0x0 and disregarded."
        SYNTAX              OCTET STRING (SIZE(3))

    WmanIf2OfdmaFftSizes ::= TEXTUAL-CONVENTION
        STATUS              current
        DESCRIPTION         "This field indicates the FFT sizes supported by
                            the SS/MS. For each FFT size, a bit value of
                            0 indicates 'not supported' while 1 indicates
                            'supported'."
        SYNTAX              BITS {
                                fft256( 0 ),
                                fft2048( 1 ),
                                fft128( 2 ),
                                fft512( 3 ),
                                fft1024( 4 )
                            }

    WmanIf2OfdmaMsDeModType ::= TEXTUAL-CONVENTION
        STATUS              current
        DESCRIPTION         "This field indicates the different demodulator
                            options supported by a WirelessMAN-OFDMA PHY
                            SS for downlink. A bit value of 0 indicates 'not
                            supported' while 1 indicates 'supported'."
        SYNTAX              BITS {
                                qam64( 0 ),
                                btc( 1 ),
                                ctc( 2 ),
                                stc( 3 ),
                                ccWithInterleacer( 4 ),
                                harqChase( 5 ),
                                harqCtcIr( 6 ),
                                reserved( 7 ),
                                harqCcIr( 8 ),
                                ldpc( 9 ),
                                dedicatedPilots( 10 )
                            }

    WmanIf2OfdmaMsModType ::= TEXTUAL-CONVENTION
        STATUS              current
        DESCRIPTION         "This field indicates the different modulator options
                            supported by a WirelessMAN-OFDMA PHY SS for uplink.
                            A bit value of 0 indicates 'not supported' while
                            1 indicates 'supported'."
        SYNTAX              BITS {
                                qam64( 0 ),
                                btc( 1 ),
                                ctc( 2 ),
                                stc( 3 ),
                                harqChase( 4 ),
                                ctcIr( 5 ),
                                ccIr( 6 ),
                                ldpc( 7 )
                            }

    WmanIf2OfdmaPermutation ::= TEXTUAL-CONVENTION
        STATUS              current
        DESCRIPTION         "This field indicates the OFDMA SS Permutation
                            support A bit value of 0 indicates 'not supported'
                            while 1 indicates 'supported'."
        SYNTAX              BITS {
                                optionalPuscSupport( 0 ),
                                optionalFuscSupport( 1 ),
                                amcOneBySixSupport( 2 ),
                                amcTwoByThreeSupport( 3 ),
                                amcThreeByTwoSupport( 4 ),
                                amcSupportWithHarqMap( 5 ),
                                tusc1Support( 6 ),
                                tusc2Support( 7 )
                            }

    WmanIf2OfdmaDemMimo ::= TEXTUAL-CONVENTION
        STATUS              current
        DESCRIPTION         "This field indicates the MIMO capability of OFDMA
                            MS demodulator. A bit value of 0 indicates 'not
                            supported' while 1 indicates 'supported'."
        SYNTAX              BITS {
                                twoAntStcMatrixA( 0 ),
                                twoAntStcMatrixBVCoding( 1 ),
                                twoAntStcMatrixBHCoding( 2 ),
                                fourAntStcMatrixA( 3 ),
                                fourAntStcMatrixBVCoding( 4 ),
                                fourAntStcMatrixBHCoding( 5 ),
                                fourAntStcMatrixCVCoding( 6 ),
                                fourAntStcMatrixCHCodingt( 7 )
                            }

    WmanIf2OfdmaMimoCap ::= TEXTUAL-CONVENTION
        STATUS              current
        DESCRIPTION         "This field indicates the MIMO capability of OFDMA
                            MS demodulator."
        SYNTAX              BITS {
                                twoAntStcMatrixA( 0 ),
                                twoAntStcMatrixBVCoding( 1 ),
                                fourRxAntenna( 2 ),
                                fourAntStcMatrixA( 3 ),
                                fourAntStcMatrixBVCoding( 4 ),
                                fourAntStcMatrixBHCoding( 5 ),
                                fourAntStcMatrixCVCoding( 6 ),
                                fourAntStcMatrixCHCodingt( 7 ),
                                threeAntStcMatrixA( 8 ),
                                threeAntStcMatrixB( 9 ),
                                threeAntStcMatrixCVCoding( 10 ),
                                threeAntStcMatrixCHCodingt( 11 ),
                                calculatingPrecodingWeight( 12 ),
                                adaptiveRateControl( 13 ),
                                calculatingChannelMatrix( 14 ),
                                antennaGrouping( 15 ),
                                antennaSelection( 16 ),
                                codebookBasedPrecoding( 17 ),
                                longTermPrecoding( 18 ),
                                mimoMidamble( 19 )
                            }

    WmanIf2OfdmaUlMimo ::= TEXTUAL-CONVENTION
        STATUS              current
        DESCRIPTION         "This field indicates the different MIMO options
                            supported by a WirelessMAN-OFDMA PHY SS in the
                            uplink. A bit value of 0 indicates 'not supported'
                            while 1 indicates 'supported'."
        SYNTAX              BITS {
                                twoAntSttd( 0 ),
                                twoAntSmVCoding( 1 ),
                                oneAntCooperativeSm( 2 )
                            }

    WmanIf2OfdmaPrivMap ::= TEXTUAL-CONVENTION
        STATUS              current
        DESCRIPTION         "This field indicates the AAS private map parameters
                            supported by a WirelessMAN-OFDMA SS. A bit value
                            of 0 indicates 'not supported' while 1 indicates
                            'supported' for most bits, except chainConcurrency0,
                            chainConcurrency1 that indicates how many parallel
                            private map chains can be supported by an SS.
                            0: no limit 1..3: maximum concurrent private
                            map chains"
        SYNTAX              BITS {
                                harqMap( 0 ),
                                privMap( 1 ),
                                reducedPrivMap( 2 ),
                                privMapChainEnable( 3 ),
                                privMapDlFrameOffset( 4 ),
                                privMapUlFrameOffset( 5 ),
                                chainConcurrency0( 6 ),
                                chainConcurrency1( 7 )
                            }

    WmanIf2OfdmaAasCap ::= TEXTUAL-CONVENTION
        STATUS              current
        DESCRIPTION         "This field indicates the different AAS options
                            supported by a WirelessMAN-OFDMA PHY SS in the
                            downlink. A bit value of 0 indicates 'not supported'
                            while 1 indicates 'supported' for most bits."
        SYNTAX              BITS {
                                aasZone( 0 ),
                                aasDiversityMapScan( 1 ),
                                aasFbckRsp( 2 ),
                                dlAasPreamble( 3 ),
                                ulAasPreamble( 4 )
                            }

    WmanIf2OfdmaCinrCap ::= TEXTUAL-CONVENTION
        STATUS              current
        DESCRIPTION         "This field indicates the CINR measurement capability
                            supported by a WirelessMAN-OFDMA PHY SS in the
                            downlink. A bit value of 0 indicates 'not supported'
                            while 1 indicates 'supported'."
        SYNTAX              BITS {
                                phyCinrPreamble( 0 ),
                                phyCinrPilotSubc( 1 ),
                                phyCinrDataSubc( 2 ),
                                effectiveCinrPreamble( 3 ),
                                effectiveCinrPilotSubc( 4 ),
                                effectiveCinrDataSubc( 5 ),
                                twoCqiChannel( 6 ),
                                freqSelectivityReport( 7 )
                            }

    WmanIf2OfdmaUlPower ::= TEXTUAL-CONVENTION
        STATUS              current
        DESCRIPTION         "This field indicates the power control options
                            supported by a WirelessMAN-OFDMA PHY SS for uplink
                            transmission. A bit value of 0 indicates 'not
                            supported' while 1 indicates 'supported'."
        SYNTAX              BITS {
                                ulOpenLoopPwrCntl( 0 ),
                                ulAasPreamblePwrCntl( 1 )
                            }

    WmanIf2OfdmaMapCap ::= TEXTUAL-CONVENTION
        STATUS              current
        DESCRIPTION         "This field indicates the different MAP options
                            supported by a WirelessMAN-OFDMA PHY SS. A bit
                            value of 0 indicates 'not supported' while 1
                            indicates 'supported'."
        SYNTAX              BITS {
                                harqMap( 0 ),
                                extendedHarqIe( 1 ),
                                subMapFor1stZone( 2 ),
                                subMapForOtherZone( 3 ),
                                dlRegionDefinition( 4 )
                            }

    WmanIf2OfdmaUlCntlCh ::= TEXTUAL-CONVENTION
        STATUS              current
        DESCRIPTION         "This field indicates different uplink control
                            channels supported by a WirelessMAN-OFDMA PHY
                            SS. A bit value of 0 indicates 'not supported'
                            while 1 indicates 'supported'."
        SYNTAX              BITS {
                                threeBitMimoFastFeedback( 0 ),
                                enhancedFastFeedback( 1 ),
                                ulAck( 2 ),
                                reserved( 3 ),
                                uepFastFeedback( 4 ),
                                fastDlMeasurementFeedback( 5 ),
                                priSecFastFeedback( 6 ),
                                diucCqiFastFeedback( 7 )
                            }

    WmanIf2OfdmaMsCistCap ::= TEXTUAL-CONVENTION
        STATUS              current
        DESCRIPTION         "This field indicates MS capability of supporting
                            CSIT (uplink sounding). A bit value of 0 indicates
                            'not supported' while 1 indicates 'supported'.
                            Bits 3..5: Time needed for SS to respond to a
                            sounding command transmitted by the BS 000 0.5ms
                            001 0.75ms 010 1ms 011 1.25ms 100 1.5ms 101 min(2ms,
                            Next Frame) 110 min(5ms, Next Frame) 111 Next
                            Frame Bits 6..9: Max number of simultaneous sounding
                            instructions (0 = unlimited)"
        SYNTAX              BITS {
                                csitTypeA( 0 ),
                                csitTypeB( 1 ),
                                powerAssignment( 2 ),
                                soundingRspTime0( 3 ),
                                soundingRspTime1( 4 ),
                                soundingRspTime2( 5 ),
                                maxSimuSoundInst0( 6 ),
                                maxSimuSoundInst1( 7 ),
                                maxSimuSoundInst2( 8 ),
                                maxSimuSoundInst3( 9 ),
                                noP9Or18ForCsitTypeA( 10 ),
                                csitNotSupported( 11 )
                            }

    WmanIf2OfdmaMaxHarq ::= TEXTUAL-CONVENTION
        STATUS              current
        DESCRIPTION         "This field indicates the maximum number of UL/DL
                            HARQ burst allocations for the SS in a single
                            UL/DL subframe. Bits 0..2: Maximum number of
                            UL HARQ bursts per HARQ enabled MS per frame
                            0b000 = 1 (default) Bit 3: Indicates whether
                            the maximum number of UL HARQ bursts per frame
                            in bits 0-2 includes the one Non-HARQ burst.
                            0 = not included (default) 1 = included Bits
                            4..7: Maximum number of DL HARQ bursts per HARQ
                            enabled MS per frame. 0b0000 = 1 (default)"
        SYNTAX              BITS {
                                maxUlHarqBurst0( 0 ),
                                maxUlHarqBurst1( 1 ),
                                maxUlHarqBurst2( 2 ),
                                nonHarqBurstInUl( 3 ),
                                maxDlHarqBurst0( 4 ),
                                maxDlHarqBurst1( 5 ),
                                maxDlHarqBurst2( 6 ),
                                maxDlHarqBurst3( 7 )
                            }

    WmanIf2OfdmaModMimo ::= TEXTUAL-CONVENTION
        STATUS              current
        DESCRIPTION         "This field indicates the MIMO capability of OFDMA
                            SS modulator. A bit value of 0 indicates 'not
                            supported' while 1 indicates 'supported'"
        SYNTAX              BITS {
                                twoTxAntenna( 0 ),
                                txDiversity( 1 ),
                                spatialMultiplexing( 2 ),
                                beamforming( 3 ),
                                adaptiveRateControl( 4 ),
                                singleAntenna( 5 ),
                                twoAntenna( 6 )
                            }

    WmanIf2SdmaPilotCap ::= TEXTUAL-CONVENTION
        STATUS              current
        DESCRIPTION         "This field indicates SDMA pilot pattern support
                            for AMC zone."
        SYNTAX              INTEGER {
                                noSupport( 0 ),
                                sdmaPilotAandB( 1 ),
                                allSdmaPilotPatterns( 2 )
                            }

    WmanIf2MultiBurst ::= TEXTUAL-CONVENTION
        STATUS              current
        DESCRIPTION         "This field indicates whether multiple FEC types
                            are supported in DL/UL burst profiles. A bit
                            value of 0 indicates 'not supported' while 1
                            indicates 'supported'"
        SYNTAX              INTEGER {
                                dlWithMultiFecType( 0 ),
                                ulWithMultiFecType( 1 )
                            }

    WmanIf2IncrHarqBuf ::= TEXTUAL-CONVENTION
        STATUS              current
        DESCRIPTION         "This field indicates the maximal number of data
                            bits the SS is able to use for buffering for
                            NEP/NSCH based incremental redundancy CTC in
                            downlink and uplink transmissions. Bits 0..3:
                            NEP value indicating downlink HARQ buffering
                            capability for incremental redundancy CTC Bit
                            4: Aggregation Flag for DL 0 = the number of
                            bits is counted separately for each channel 1
                            = buffering capability may be shared between
                            channels Bits 5..7: reserved Bits 8..11: NEP
                            value indicating uplink HARQ buffering capability
                            for incremental redundancy CTC Bit 12: Aggregation
                            Flag for UL 0 = the number of bits is counted
                            separately for each channel 1 = buffering capability
                            may be shared between channels"
        SYNTAX              INTEGER {
                                dlNep0( 0 ),
                                dlNep1( 1 ),
                                dlNep2( 2 ),
                                dlNep3( 3 ),
                                dlAggFlag( 4 ),
                                reserved0( 5 ),
                                reserved1( 6 ),
                                reserved2( 7 ),
                                ulNep0( 8 ),
                                ulNep1( 9 ),
                                ulNep2( 10 ),
                                ulNep3( 11 ),
                                ulAggFlag( 12 )
                            }

    WmanIf2ChaseHarqBuf ::= TEXTUAL-CONVENTION
        STATUS              current
        DESCRIPTION         "This field indicates the maximal number of data
                            bits the SS is able to use for buffering for
                            DIUC/duration based HARQ methods (Chase combining
                            and CC-IR)in downlink and uplink transmissions.
                            Bits 0..5: Downlink HARQ buffering capability
                            for chase combining (K) Bit 6: Aggregation Flag
                            for DL 0 = the number of bits is counted separately
                            for each channel 1 = buffering capability may
                            be shared between channels Bits 7: reserved Bits
                            8..13: Uplink HARQ buffering capability for chase
                            combining (K) Bit 14: Aggregation Flag for UL
                            0 = the number of bits is counted separately
                            for each channel 1 = buffering capability may
                            be shared between channels"
        SYNTAX              Integer32 (0..65535)
--
--      SYNTAX              INTEGER {
--                              dlChaseComb0( 0 ),
--                              dlChaseComb1( 1 ),
--                              dlChaseComb2( 2 ),
--                              dlChaseComb3( 3 ),
--                              dlChaseComb4( 4 ),
--                              dlChaseComb5( 5 ),
--                              dlAggFlag( 6 ),
--                              reserved( 7 ),
--                              ulChaseComb0( 8 ),
--                              ulChaseComb1( 9 ),
--                              ulChaseComb2( 10 ),
--                              ulChaseComb3( 11 ),
--                              ulChaseComb4( 12 ),
--                              ulChaseComb5( 13 ),
--                              ulAggFlag( 14 )
--                          }
--

    WmanIf2PkmVersion ::= TEXTUAL-CONVENTION
        STATUS              current
        DESCRIPTION         "This field indicates a PKM version that SS or
                            BS supports. A bit 0 - 'not supported' 1 - 'supported'
                            Both an SS and a BS should negotiate only one
                            PKM version."
        SYNTAX              BITS {
                                pkmVersion1( 0 ),
                                pkmVersion2( 1 )
                            }

    WmanIf2AuthPolicy ::= TEXTUAL-CONVENTION
        STATUS              current
        DESCRIPTION         "This field indicates authorization policy used
                            by the MS and BS to negotiate and synchronize.
                            A bit 0 - 'not supported' 1 - 'supported'"
        SYNTAX              BITS {
                                rsaBasedAuthInitNtwkEntry( 0 ),
                                eapBasedAuthInitNtwkEntry( 1 ),
                                authenEapBasedAuthInitNtwkEntry( 2 ),
                                reserved0( 3 ),
                                rsaBasedAuthReentry( 4 ),
                                eapBasedAuthReentry( 5 ),
                                authenEapBasedAuthReentry( 6 ),
                                reserved1( 7 )
                            }

    WmanIf2MacMode ::= TEXTUAL-CONVENTION
        STATUS              current
        DESCRIPTION         "This field indicates a MAC (Message Authentication
                            Code) mode that MS supports. Both MS and BS shall
                            determine and use a MAC mode. A bit 0 - 'not
                            supported' 1 - 'supported'"
        SYNTAX              BITS {
                                hmac( 0 ),
                                cmac( 1 ),
                                sixtyfourBitShortHmaca( 2 ),
                                eightyBitShortHmaca( 3 ),
                                nintysixBitShortHmaca( 4 )
                            }

    WmanIf2ExtCapability ::= TEXTUAL-CONVENTION
        STATUS              current
        DESCRIPTION         "This field indicates the extended subheader format
                            support. A bit 0 - 'not supported' 1 - 'supported'"
        SYNTAX              BITS {
                                extSubheader( 0 )
                            }

    WmanIf2PackingSupport ::= TEXTUAL-CONVENTION
        STATUS              current
        DESCRIPTION         "Indicates the availability of MS support for Packing"
        SYNTAX              INTEGER {
                                noPackingSupport( 0 ),
                                packingSupported( 1 )
                            }

    WmanIf2ExtRtpsSupport ::= TEXTUAL-CONVENTION
        STATUS              current
        DESCRIPTION         "Indicates the availability of MS support for Extended
                            rtPS."
        SYNTAX              INTEGER {
                                noExtendedRtpsSupport( 0 ),
                                extendedRtpsSupported( 1 )
                            }

    WmanIf2IpAllocMethod ::= TEXTUAL-CONVENTION
        STATUS              current
        DESCRIPTION         "Indicates the method of allocating IP address
                            for the secondary management connection. A bit
                            value of 0 indicates 'not supported' while 1
                            indicates 'supported'."
        SYNTAX              BITS {
                                dhcp( 0 ),
                                mobileIpv4( 1 ),
                                dhcpV6( 2 ),
                                ipv6Autoconfig( 3 )
                            }

    WmanIf2ArqAckType ::= TEXTUAL-CONVENTION
        STATUS              current
        DESCRIPTION         "Specifies the ARQ ACK type supported by the MS."
        SYNTAX              BITS {
                                selectiveAck( 0 ),
                                cumulativeAck( 1 ),
                                cumWithSelAck( 2 ),
                                cumWithBlockSeqAck( 3 )
                            }

    WmanIf2MacHeaderSupp ::= TEXTUAL-CONVENTION
        STATUS              current
        DESCRIPTION         "Indicates whether or not the MS and BS support
                            various types of MAC header and extended subheaders.
                            A bit value of 0 indicates 'not supported', while
                            1 indicates 'supported'. Bits 8-10: parameters
                            of SDU_SN extended subheader that represent the
                            period of SDU_SN transmission for connection
                            with ARQ disabled = once every 2^p MAC PDUs."
        SYNTAX              BITS {
                                bwReqUlTxPowerReport( 0 ),
                                bwReqCinrReport( 1 ),
                                cqichAlloationReq( 2 ),
                                phyChannelReport( 3 ),
                                bwReqUlSleepCntl( 4 ),
                                snReport( 5 ),
                                feedbackReport( 6 ),
                                sduSn( 7 ),
                                sdnSnPeriod0( 8 ),
                                sdnSnPeriod1( 9 ),
                                sdnSnPeriod2( 10 ),
                                dlSleepControl( 11 ),
                                feedbackRequest( 12 ),
                                mimcModeFeedback( 13 ),
                                ulTxPowerReport( 14 ),
                                miniFeedback( 15 ),
                                snRequest( 16 ),
                                shortPduSn( 17 ),
                                longPduSn( 18 )
                            }

    WmanIf2HarqAckDelay ::= TEXTUAL-CONVENTION
        STATUS              current
        DESCRIPTION         "HARQ ACK delay for UL and DL bursts 1 = one frame
                            offset 2 = two frames offset 3 = three frames
                            offset"
        SYNTAX              INTEGER {
                                oneframeoffset( 1 ),
                                twoframesoffset( 2 ),
                                threeframesoffset( 3 )
                            }

    WmanIf2AasBeamSel ::= TEXTUAL-CONVENTION
        STATUS              current
        DESCRIPTION         "Boolean to indicate whether unsolicited AAS Beam
                            Select messages (see 6.3.2.3.41 in IEEE 802.16e-2005)
                            should be sent by the MS. 0: MS should not send
                            AAS Beam Select Messages 1: MS may send AAS Beam
                            Select Messages"
        SYNTAX              INTEGER {
                                notAllowed( 0 ),
                                allowed( 1 )
                            }

    WmanIf2MaxMacLevel ::= TEXTUAL-CONVENTION
        STATUS              current
        DESCRIPTION         "maximum amount of MAC level data including MAC
                            headers and HARQ retransmission bursts the MS
                            is capable of processing in the DL/UL part of
                            a single MAC frame."
        SYNTAX              Integer32 (0..65535)

    WmanIfPermutationType ::= TEXTUAL-CONVENTION
        STATUS              current
        DESCRIPTION         "Permutation type for broadcast region in HARQ
                            zone"
        SYNTAX              INTEGER {
                                pusc( 1 ),
                                fusc( 2 ),
                                optionalFusc( 3 ),
                                amc( 4 )
                            }

    WmanIf2HoSupportType ::= TEXTUAL-CONVENTION
        STATUS              current
        DESCRIPTION         "The types of handover supported."
        SYNTAX              BITS {
                                handover( 0 ),
                                mdHandover( 1 ),
                                fbssHandover( 2 )
                            }

    WmanIf2ActionRule ::= TEXTUAL-CONVENTION
        STATUS              current
        DESCRIPTION         "The value of this field specifies an action associated
                            with the classifier rule Bit #0: 0 = none. 1
                            = Discard packet"
        SYNTAX              BITS {
                                discardPacket( 0 )
                            }



    wmanIf2MibObjects OBJECT IDENTIFIER ::= { wmanIf2Mib 1 }

    wmanIf2BsObjects OBJECT IDENTIFIER ::= { wmanIf2MibObjects 1 }

    --
    --
    --
    --
    --
    --
    --
    wmanIf2BsPacketCs OBJECT IDENTIFIER ::= { wmanIf2BsObjects 1 }

    wmanIf2BsSsPacketCounterTable OBJECT-TYPE
        SYNTAX              SEQUENCE OF WmanIf2BsSsPacketCounterEntry
        MAX-ACCESS          not-accessible
        STATUS              current
        DESCRIPTION         "This table contains counters to keep track of
                            the number of packets and octets that have been
                            received or transmitted on the per service flow
                            basis."
        ::= { wmanIf2BsPacketCs 5 }

    wmanIf2BsSsPacketCounterEntry OBJECT-TYPE
        SYNTAX              WmanIf2BsSsPacketCounterEntry
        MAX-ACCESS          not-accessible
        STATUS              current
        DESCRIPTION         "This table provides one row for each service flow,
                            and is indexed by ifIndex, wmanIf2CmnCpsSfMacAddress,
                            and wmanIf2CmnCpsSfId."
        INDEX               {
                                ifIndex,
                                wmanIf2CmnCpsSfMacAddress,
                                wmanIf2CmnCpsSfId
                            }
        ::= { wmanIf2BsSsPacketCounterTable 1 }

    WmanIf2BsSsPacketCounterEntry ::= SEQUENCE {
        wmanIf2BsSsMacSduCount
            Counter64,
        wmanIf2BsSsOctetCount
            Counter64,
        wmanIf2BsSsResetCounter
            INTEGER,
        wmanIf2BsSsResetCounterTime
            TimeStamp
    }

    wmanIf2BsSsMacSduCount OBJECT-TYPE
        SYNTAX              Counter64
        MAX-ACCESS          read-only
        STATUS              current
        DESCRIPTION         "This object counts the number of MAC SDUs that
                            have been transmitted or received."
        ::= { wmanIf2BsSsPacketCounterEntry 1 }

    wmanIf2BsSsOctetCount OBJECT-TYPE
        SYNTAX              Counter64
        MAX-ACCESS          read-only
        STATUS              current
        DESCRIPTION         "This object counts the number of octets of MAC
                            SDUs that have been transmitted or received."
        ::= { wmanIf2BsSsPacketCounterEntry 2 }

    wmanIf2BsSsResetCounter OBJECT-TYPE
        SYNTAX              INTEGER {
                                null( 0 ),
                                resetCounter( 1 )
                            }
        MAX-ACCESS          read-write
        STATUS              current
        DESCRIPTION         "When this attribute is SET to resetCounter(1),
                            the corresponding entry of packet counters will
                            be reset. A GET operation performed on this object
                            will always return null(0). The counter is normally
                            reset after the packet count information is retrieved."
        ::= { wmanIf2BsSsPacketCounterEntry 3 }

    wmanIf2BsSsResetCounterTime OBJECT-TYPE
        SYNTAX              TimeStamp
        MAX-ACCESS          read-only
        STATUS              current
        DESCRIPTION         "Indicates the date and time when the counter is
                            reset."
        ::= { wmanIf2BsSsPacketCounterEntry 4 }

    --
    --
    --
    wmanIf2BsCps OBJECT IDENTIFIER ::= { wmanIf2BsObjects 2 }

    wmanIf2BsRegisteredSsTable OBJECT-TYPE
        SYNTAX              SEQUENCE OF WmanIf2BsRegisteredSsEntry
        MAX-ACCESS          not-accessible
        STATUS              current
        DESCRIPTION         "This table contains the basic capability information
                            of SSs that have been negotiated and agreed between
                            BS and SS via REG-REQ and REG-RSP messages. An
                            entry in this table indicates the SS has entered
                            and registered into the BS."
        ::= { wmanIf2BsCps 1 }

    wmanIf2BsRegisteredSsEntry OBJECT-TYPE
        SYNTAX              WmanIf2BsRegisteredSsEntry
        MAX-ACCESS          not-accessible
        STATUS              current
        DESCRIPTION         "This table provides one row for each SS that has
                            been registered in the BS, and is indexed by
                            wmanIf2BsSsMacAddress. The primary index is the
                            ifIndex with an ifType of ieee80216WMAN, indicating
                            the BS sector with which the SS is associated.
                            wmanIf2BsSsMacAddress identifies the SS being
                            registered."
        INDEX               {
                                ifIndex,
                                wmanIf2BsSsMacAddress
                            }
        ::= { wmanIf2BsRegisteredSsTable 1 }

    WmanIf2BsRegisteredSsEntry ::= SEQUENCE {
        wmanIf2BsSsMacAddress
            MacAddress,
        wmanIf2BsSsBasicCid
            WmanIf2CidType,
        wmanIf2BsSsPrimaryCid
            WmanIf2CidType,
        wmanIf2BsSsSecondaryCid
            WmanIf2CidType,
        wmanIf2BsSsManagementSupport
            INTEGER,
        wmanIf2BsSsIpManagementMode
            INTEGER,
        wmanIf2BsSs2ndMgmtArqEnable
            TruthValue,
        wmanIf2BsSs2ndMgmtArqWindowSize
            Integer32,
        wmanIf2BsSs2ndMgmtArqDnLinkTxDelay
            Integer32,
        wmanIf2BsSs2ndMgmtArqUpLinkTxDelay
            Integer32,
        wmanIf2BsSs2ndMgmtArqDnLinkRxDelay
            Integer32,
        wmanIf2BsSs2ndMgmtArqUpLinkRxDelay
            Integer32,
        wmanIf2BsSs2ndMgmtArqBlockLifetime
            Integer32,
        wmanIf2BsSs2ndMgmtArqSyncLossTimeout
            Integer32,
        wmanIf2BsSs2ndMgmtArqDeliverInOrder
            TruthValue,
        wmanIf2BsSs2ndMgmtArqRxPurgeTimeout
            Integer32,
        wmanIf2BsSs2ndMgmtArqBlockSize
            Integer32,
        wmanIf2BsSsVendorIdEncoding
            OCTET STRING,
        wmanIf2BsSsAasBroadcastPermission
            INTEGER,
        wmanIf2BsSsMaxTxPowerBpsk
            WmanIf2MaxTxPowerType,
        wmanIf2BsSsMaxTxPowerQpsk
            WmanIf2MaxTxPowerType,
        wmanIf2BsSsMaxTxPower16Qam
            WmanIf2MaxTxPowerType,
        wmanIf2BsSsMaxTxPower64Qam
            WmanIf2MaxTxPowerType,
        wmanIf2BsSsMacVersion
            WmanIf2MacVersion
    }

    wmanIf2BsSsMacAddress OBJECT-TYPE
        SYNTAX              MacAddress
        MAX-ACCESS          not-accessible
        STATUS              current
        DESCRIPTION         "The MAC address of SS is received from the RNG-REQ
                            message. When SS registers, this MAC address
                            is entered into the table, and used as the identifier
                            to the SS."
        ::= { wmanIf2BsRegisteredSsEntry 1 }

    wmanIf2BsSsBasicCid OBJECT-TYPE
        SYNTAX              WmanIf2CidType
        MAX-ACCESS          read-only
        STATUS              current
        DESCRIPTION         "The value of this object indicates the SS's basic
                            CID that was sent in the RNG-RSP message."
        ::= { wmanIf2BsRegisteredSsEntry 2 }

    wmanIf2BsSsPrimaryCid OBJECT-TYPE
        SYNTAX              WmanIf2CidType
        MAX-ACCESS          read-only
        STATUS              current
        DESCRIPTION         "The value of this object indicates the primary
                            CID of the SS received from the RNG-RSP message."
        ::= { wmanIf2BsRegisteredSsEntry 3 }

    wmanIf2BsSsSecondaryCid OBJECT-TYPE
        SYNTAX              WmanIf2CidType
        MAX-ACCESS          read-only
        STATUS              current
        DESCRIPTION         "The value of this object indicates the secondary
                            management CID present in the REG-RSP message.
                            The value should be null if the 2nd management
                            connection is not available."
        ::= { wmanIf2BsRegisteredSsEntry 4 }

    wmanIf2BsSsManagementSupport OBJECT-TYPE
        SYNTAX              INTEGER {
                                unmanagedSs( 0 ),
                                managedSs( 1 )
                            }
        MAX-ACCESS          read-only
        STATUS              current
        DESCRIPTION         "This object indicates whether or not the SS is
                            managed."
        ::= { wmanIf2BsRegisteredSsEntry 5 }

    wmanIf2BsSsIpManagementMode OBJECT-TYPE
        SYNTAX              INTEGER {
                                unmanaged( 0 ),
                                ipManaged( 1 )
                            }
        MAX-ACCESS          read-only
        STATUS              current
        DESCRIPTION         "The IP management mode parameter dictates whether
                            the provider intends to manage the SS on an ongoing
                            basis via IP-based mechanisms."
        ::= { wmanIf2BsRegisteredSsEntry 6 }

    wmanIf2BsSs2ndMgmtArqEnable OBJECT-TYPE
        SYNTAX              TruthValue
        MAX-ACCESS          read-only
        STATUS              current
        DESCRIPTION         "True(1) ARQ enabling is requested for the 2nd
                            management channel."
        ::= { wmanIf2BsRegisteredSsEntry 7 }

    wmanIf2BsSs2ndMgmtArqWindowSize OBJECT-TYPE
        SYNTAX              Integer32 (1..1024)
        MAX-ACCESS          read-only
        STATUS              current
        DESCRIPTION         "Indicates the maximum number of unacknowledged
                            fragments at any time for 2nd management connection."
        ::= { wmanIf2BsRegisteredSsEntry 8 }

    wmanIf2BsSs2ndMgmtArqDnLinkTxDelay OBJECT-TYPE
        SYNTAX              Integer32 (0..65535)
        UNITS               "us"
        MAX-ACCESS          read-only
        STATUS              current
        DESCRIPTION         "The object defines the ARQ transmitter delay for
                            downlink transmission."
        ::= { wmanIf2BsRegisteredSsEntry 9 }

    wmanIf2BsSs2ndMgmtArqUpLinkTxDelay OBJECT-TYPE
        SYNTAX              Integer32 (0..65535)
        UNITS               "us"
        MAX-ACCESS          read-only
        STATUS              current
        DESCRIPTION         "The object defines the ARQ transmitter delay for
                            uplink transmission."
        ::= { wmanIf2BsRegisteredSsEntry 10 }

    wmanIf2BsSs2ndMgmtArqDnLinkRxDelay OBJECT-TYPE
        SYNTAX              Integer32 (0..65535)
        UNITS               "us"
        MAX-ACCESS          read-only
        STATUS              current
        DESCRIPTION         "The object defines the ARQ receiver delay for
                            downlink transmission."
        ::= { wmanIf2BsRegisteredSsEntry 11 }

    wmanIf2BsSs2ndMgmtArqUpLinkRxDelay OBJECT-TYPE
        SYNTAX              Integer32 (0..65535)
        UNITS               "us"
        MAX-ACCESS          read-only
        STATUS              current
        DESCRIPTION         "The object defines the ARQ receiver delay for
                            uplink transmission."
        ::= { wmanIf2BsRegisteredSsEntry 12 }

    wmanIf2BsSs2ndMgmtArqBlockLifetime OBJECT-TYPE
        SYNTAX              Integer32 (0..65535)
        UNITS               "10 us"
        MAX-ACCESS          read-only
        STATUS              current
        DESCRIPTION         "The maximum time interval an ARQ fragment will
                            be managed by the transmitter ARQ machine, once
                            initial transmission of the fragment has occured.
                            If transmission or retransmission of the fragment
                            is not acknowledged by the receiver before the
                            time limit is reached, the fragment is discarded.
                            A value of 0 means Infinite. DEFVAL { 0 }"
        ::= { wmanIf2BsRegisteredSsEntry 13 }

    wmanIf2BsSs2ndMgmtArqSyncLossTimeout OBJECT-TYPE
        SYNTAX              Integer32 (0..65535)
        UNITS               "10 us"
        MAX-ACCESS          read-only
        STATUS              current
        DESCRIPTION         "The maximum interval before declaring a loss of
                            synchronization of the sender and receiver state
                            machines. A value of 0 means Infinite. DEFVAL
                            { 0 }"
        ::= { wmanIf2BsRegisteredSsEntry 14 }

    wmanIf2BsSs2ndMgmtArqDeliverInOrder OBJECT-TYPE
        SYNTAX              TruthValue
        MAX-ACCESS          read-only
        STATUS              current
        DESCRIPTION         "Indicates whether or not data is to be delivered
                            by the receiving MAC to its client application
                            in the order in which data was handed off to
                            the originating MAC."
        ::= { wmanIf2BsRegisteredSsEntry 15 }

    wmanIf2BsSs2ndMgmtArqRxPurgeTimeout OBJECT-TYPE
        SYNTAX              Integer32 (0..65535)
        UNITS               "10 us"
        MAX-ACCESS          read-only
        STATUS              current
        DESCRIPTION         "Indicates the time interval the ARQ window is
                            advanced after a fragment is received. A value
                            of 0 means Infinite. DEFVAL { 0 }"
        ::= { wmanIf2BsRegisteredSsEntry 16 }

    wmanIf2BsSs2ndMgmtArqBlockSize OBJECT-TYPE
        SYNTAX              Integer32 (1..2040)
        MAX-ACCESS          read-only
        STATUS              current
        DESCRIPTION         "This parameter specifies the size of a ARQ block.
                            This parameter shall be established by negotiation
                            during the connection setup. The requester includes
                            its desired setting in the REQ message. The receiver
                            of the REQ message shall take the smaller of
                            the value it prefers and value in the REQ message.
                            The minimum value is included in the RSP message."
        ::= { wmanIf2BsRegisteredSsEntry 17 }

    wmanIf2BsSsVendorIdEncoding OBJECT-TYPE
        SYNTAX              OCTET STRING (SIZE(3))
        MAX-ACCESS          read-only
        STATUS              current
        DESCRIPTION         "The value field contains the vendor identification
                            specified by the 3 byte vendor-specific organizationally
                            unique identifier of the SS or BS MAC address.A
                            vendor ID used in a REG-REQ shall be the Vendor
                            ID of the SS sending the request. A vendor ID
                            used in a REG-RSP shall be the Vendor ID of the
                            BS sending the response."
        ::= { wmanIf2BsRegisteredSsEntry 18 }

    wmanIf2BsSsAasBroadcastPermission OBJECT-TYPE
        SYNTAX              INTEGER {
                                contBasedBwReqPermitted( 0 ),
                                contBasedBwReqNotPermitted( 1 )
                            }
        MAX-ACCESS          read-only
        STATUS              current
        DESCRIPTION         "This parameter specifies if SS can issue contention-based
                            bandwidth request or not."
        ::= { wmanIf2BsRegisteredSsEntry 19 }

    wmanIf2BsSsMaxTxPowerBpsk OBJECT-TYPE
        SYNTAX              WmanIf2MaxTxPowerType
        MAX-ACCESS          read-only
        STATUS              current
        DESCRIPTION         "The maximum available power for BPSK. The maximum
                            power parameters are reported in dBm and quantized
                            in 0.5 dBm steps ranging from -64 dBm (encoded
                            0x00) to 63.5 dBm (encoded 0xFF). Values outside
                            this range shall be assigned the closest extreme.
                            This parameter is only applicable to systems
                            supporting the SCa, OFDM or OFDMA PHY."
        ::= { wmanIf2BsRegisteredSsEntry 20 }

    wmanIf2BsSsMaxTxPowerQpsk OBJECT-TYPE
        SYNTAX              WmanIf2MaxTxPowerType
        MAX-ACCESS          read-only
        STATUS              current
        DESCRIPTION         "The maximum available power for QPSK. The maximum
                            power parameters are reported in dBm and quantized
                            in 0.5 dBm steps ranging from -64 dBm (encoded
                            0x00) to 63.5 dBm (encoded 0xFF). Values outside
                            this range shall be assigned to closest extreme.
                            This parameter is only applicable to systems
                            supporting the SCa, OFDM or OFDMA PHY."
        ::= { wmanIf2BsRegisteredSsEntry 21 }

    wmanIf2BsSsMaxTxPower16Qam OBJECT-TYPE
        SYNTAX              WmanIf2MaxTxPowerType
        MAX-ACCESS          read-only
        STATUS              current
        DESCRIPTION         "The maximum available power for 16-QAM constellations.
                            The maximum power parameters are reported in
                            dBm and quantized in 0.5 dBm steps ranging from
                            -64 dBm (encoded 0x00) to 63.5 dBm (encoded 0xFF).
                            Values outside this range shall be assigned the
                            closest extreme. This parameter is only applicable
                            to systems supporting the SCa, OFDM or OFDMA
                            PHY."
        ::= { wmanIf2BsRegisteredSsEntry 22 }

    wmanIf2BsSsMaxTxPower64Qam OBJECT-TYPE
        SYNTAX              WmanIf2MaxTxPowerType
        MAX-ACCESS          read-only
        STATUS              current
        DESCRIPTION         "The maximum available power for 64-QAM constellations.
                            The maximum power parameters are reported in
                            dBm and quantized in 0.5 dBm steps ranging from
                            -64 dBm (encoded 0x00) to 63.5 dBm (encoded 0xFF).
                            Values outside this range shall be assigned the
                            closest extreme. SSs that do not support QAM64
                            shall report the value of 0x00. This parameter
                            is only applicable to systems supporting the
                            SCa, OFDM or OFDMA PHY."
        ::= { wmanIf2BsRegisteredSsEntry 23 }

    wmanIf2BsSsMacVersion OBJECT-TYPE
        SYNTAX              WmanIf2MacVersion
        MAX-ACCESS          read-only
        STATUS              current
        DESCRIPTION         "This parameter specifies the version of 802.16
                            to which the message originator conforms."
        ::= { wmanIf2BsRegisteredSsEntry 24 }

    --
    --
    --
    wmanIf2BsConfigurationTable OBJECT-TYPE
        SYNTAX              SEQUENCE OF WmanIf2BsConfigurationEntry
        MAX-ACCESS          not-accessible
        STATUS              current
        DESCRIPTION         "This table provides one row for each BS sector
                            that contains the BS system parameters as defined
                            in Subclause 10.1 of [3]. The objects in this
                            table define the default behaviour of the BS
                            for 2nd Management connection scheduling and
                            SFID allocation as well as configuration parameters
                            of the CPS scheduler and AAS system."
        ::= { wmanIf2BsCps 2 }

    wmanIf2BsConfigurationEntry OBJECT-TYPE
        SYNTAX              WmanIf2BsConfigurationEntry
        MAX-ACCESS          not-accessible
        STATUS              current
        DESCRIPTION         "This table is indexed by ifIndex with an ifType
                            of ieee80216WMAN."
        INDEX               {
                                ifIndex
                            }
        ::= { wmanIf2BsConfigurationTable 1 }

    WmanIf2BsConfigurationEntry ::= SEQUENCE {
        wmanIf2BsDcdInterval
            Integer32,
        wmanIf2BsUcdInterval
            Integer32,
        wmanIf2BsUcdTransition
            Integer32,
        wmanIf2BsDcdTransition
            Integer32,
        wmanIf2BsInitialRangingInterval
            Integer32,
        wmanIf2BsT9Timeout
            Integer32,
        wmanIf2BsSsULMapProcTime
            Unsigned32,
        wmanIf2BsSsRangRespProcTime
            Unsigned32,
        wmanIf2BsT13Timeout
            Integer32,
        wmanIf2BsT15Timeout
            Integer32,
        wmanIf2BsT17Timeout
            Integer32,
        wmanIf2BsT27IdleTimer
            Unsigned32,
        wmanIf2BsT27ActiveTimer
            Unsigned32,
        wmanIf2Bs2ndMgmtDlQoSProfileIndex
            Integer32,
        wmanIf2Bs2ndMgmtUlQoSProfileIndex
            Integer32,
        wmanIf2BsAutoSfidEnabled
            INTEGER,
        wmanIf2BsAutoSfidRangeMin
            Unsigned32,
        wmanIf2BsAutoSfidRangeMax
            Unsigned32,
        wmanIf2BsAasChanFbckReqFreq
            Integer32,
        wmanIf2BsAasBeamSelectFreq
            Integer32,
        wmanIf2BsAasChanFbckReqResolution
            INTEGER,
        wmanIf2BsAasBeamReqResolution
            INTEGER,
        wmanIf2BsAasNumOptDiversityZones
            Integer32,
        wmanIf2BsResetSector
            INTEGER,
        wmanIf2BsSaChallengeTimer
            Integer32,
        wmanIf2BsSaChallengeMaxResends
            Integer32,
        wmanIf2BsSaTekTimer
            Integer32,
        wmanIf2BsSaTekReqMaxResends
            Integer32,
        wmanIf2Bs2ndEapTimeout
            Integer32,
        wmanIf2BsEapCompleteResends
            Integer32
    }

    wmanIf2BsDcdInterval OBJECT-TYPE
        SYNTAX              Integer32 (0..65535)
        UNITS               "Number of MAC Frames"
        MAX-ACCESS          read-write
        STATUS              current
        DESCRIPTION         "Time between transmission of DCD messages in Number
                            of MAC Frames(1frame=5ms)."
        ::= { wmanIf2BsConfigurationEntry 1 }

    wmanIf2BsUcdInterval OBJECT-TYPE
        SYNTAX              Integer32 (0..65535)
        UNITS               "Number of MAC Frames"
        MAX-ACCESS          read-write
        STATUS              current
        DESCRIPTION         "Time between transmission of UCD messages in Number
                            of MAC Frames(1frame=5ms)."
        ::= { wmanIf2BsConfigurationEntry 2 }

    wmanIf2BsUcdTransition OBJECT-TYPE
        SYNTAX              Integer32 (2..65535)
        UNITS               "Number of MAC Frames"
        MAX-ACCESS          read-only
        STATUS              current
        DESCRIPTION         "The number of frames from the end of the frame
                            carrying the UCD message the BS shall wait after
                            transmitting a UCD message with an incremented
                            Configuration Change Count before issuing a UL-MAP
                            message referring to Uplink_Burst_Profiles defined
                            in that UCD message. Minimum value = 20ms following
                            the last fragment of the message"
        ::= { wmanIf2BsConfigurationEntry 3 }

    wmanIf2BsDcdTransition OBJECT-TYPE
        SYNTAX              Integer32 (2..65535)
        UNITS               "Number of MAC Frames"
        MAX-ACCESS          read-only
        STATUS              current
        DESCRIPTION         "The number of frames from the end of the frame
                            carrying the DCD message the BS shall wait after
                            transmitting a DCD message with an incremented
                            Configuration Change Count before issuing a DL-MAP
                            message referring to Downlink_Burst_Profiles
                            defined in that DCD message. Minimum value =
                            20ms following the last fragment of the message"
        ::= { wmanIf2BsConfigurationEntry 4 }

    wmanIf2BsInitialRangingInterval OBJECT-TYPE
        SYNTAX              Integer32 (0..400)
        UNITS               "Number of MAC Frames"
        MAX-ACCESS          read-write
        STATUS              current
        DESCRIPTION         "Time between Initial Ranging regions assigned
                            by the BS in in Number of MAC Frames(1frame=5ms)."
        ::= { wmanIf2BsConfigurationEntry 5 }

    wmanIf2BsT9Timeout OBJECT-TYPE
        SYNTAX              Integer32 (300..65535)
        UNITS               "milliseconds"
        MAX-ACCESS          read-only
        STATUS              current
        DESCRIPTION         "Registration Timeout, the time allowed between
                            the BS sending a RNG-RSP (success) to an SS,
                            and receiving a SBC-REQ from that same SS in
                            ms. OID CHANGE(9->6) for NEC 080718"
        ::= { wmanIf2BsConfigurationEntry 6 }

    wmanIf2BsSsULMapProcTime OBJECT-TYPE
        SYNTAX              Unsigned32 (200..4294967295)
        UNITS               "micro seconds"
        MAX-ACCESS          read-write
        STATUS              current
        DESCRIPTION         "Time provided between arrival of the last bit
                            of a UL-MAP at an SS and effectiveness of that
                            map in us. For OFDMA mode, the time shall be
                            counted starting from the end of the burst carrying
                            the UL-MAP. Minimum value: SC = 200us OFDM =
                            1ms OFDMA = frame duration. OID CHANGE(6->7) for NEC
                            080718"
        ::= { wmanIf2BsConfigurationEntry 7 }

    wmanIf2BsSsRangRespProcTime OBJECT-TYPE
        SYNTAX              Unsigned32 (10000..4294967295)
        UNITS               "micro seconds"
        MAX-ACCESS          read-write
        STATUS              current
        DESCRIPTION         "Time allowed for an SS following receipt of a
                            ranging response before it is expected to reply
                            to an invited ranging request in us.OID CHANGE
                            (7->9) for NEC 080718"
        ::= { wmanIf2BsConfigurationEntry 9 }

    wmanIf2BsT13Timeout OBJECT-TYPE
        SYNTAX              Integer32 (15..65535)
        UNITS               "minutes"
        MAX-ACCESS          read-write
        STATUS              current
        DESCRIPTION         "The time allowed for an SS, following receipt
                            of a REG-RSP message to send a TFTP-CPLT message
                            to the BS in min."
        ::= { wmanIf2BsConfigurationEntry 10 }

    wmanIf2BsT15Timeout OBJECT-TYPE
        SYNTAX              Integer32 (20..65535)
        UNITS               "milliseconds"
        MAX-ACCESS          read-write
        STATUS              current
        DESCRIPTION         "Wait for MCA-RSP in ms."
        ::= { wmanIf2BsConfigurationEntry 11 }

    wmanIf2BsT17Timeout OBJECT-TYPE
        SYNTAX              Integer32 (5..65535)
        UNITS               "minutes"
        MAX-ACCESS          read-only
        STATUS              current
        DESCRIPTION         "Time allowed for SS to complete SS Authorization
                            and Key Exchange in minutes."
        ::= { wmanIf2BsConfigurationEntry 12 }

    wmanIf2BsT27IdleTimer OBJECT-TYPE
        SYNTAX              Unsigned32 (10000..4294967295)
        UNITS               "us"
        MAX-ACCESS          read-write
        STATUS              current
        DESCRIPTION         "Maximum time between unicast grants to SS when
                            BS believes SS uplink transmission quality is
                            good enough."
        ::= { wmanIf2BsConfigurationEntry 13 }

    wmanIf2BsT27ActiveTimer OBJECT-TYPE
        SYNTAX              Unsigned32 (10000..4294967295)
        UNITS               "us"
        MAX-ACCESS          read-write
        STATUS              current
        DESCRIPTION         "Maximum time between unicast grants to SS when
                            BS believes SS uplink transmission quality is
                            not good enough."
        ::= { wmanIf2BsConfigurationEntry 14 }

    wmanIf2Bs2ndMgmtDlQoSProfileIndex OBJECT-TYPE
        SYNTAX              Integer32 (1..65535)
        MAX-ACCESS          read-write
        STATUS              current
        DESCRIPTION         "This object defines the index of a row in wmanIf2BsServiceClassTable
                            which is used to obtain all QoS parameters required
                            for the BS downlink scheduler to properly allocate
                            and manage the bandwidth and schedule the 2nd
                            Management Connection traffic. The 2nd Management
                            Connection traffic doesn't differ from Traffic
                            Connection traffic in the area of QoS management."
        ::= { wmanIf2BsConfigurationEntry 15 }

    wmanIf2Bs2ndMgmtUlQoSProfileIndex OBJECT-TYPE
        SYNTAX              Integer32 (1..65535)
        MAX-ACCESS          read-write
        STATUS              current
        DESCRIPTION         "This object defines the index of a row in wmanIf2BsServiceClassTable
                            which is used to obtain all QoS parameters required
                            for the BS uplink scheduler to properly allocate
                            and manage the bandwidth and schedule the 2nd
                            Management Connection traffic. The 2nd Management
                            Connection traffic doesn't differ from Traffic
                            Connection traffic in the area of QoS management."
        ::= { wmanIf2BsConfigurationEntry 16 }

    wmanIf2BsAutoSfidEnabled OBJECT-TYPE
        SYNTAX              INTEGER {
                                autoSfidDisabled( 0 ),
                                autoSfidEnabled( 1 )
                            }
        MAX-ACCESS          read-only
        STATUS              current
        DESCRIPTION         "This object defines whether the BS is allowed
                            to autonomously allocate SFIDs. When the object
                            is set to autoSfidEnabled, the BS is allowed
                            to autonomously allocate SFIDs from the range
                            of allowed values defined by wmanIf2BsConfigExtAutoSfidRangeMin
                            and wmanIf2BsConfigExtAutoSfidRangeMax. A SF
                            is created autonomously when it has not been
                            provisioned in the wmanIf2BsProvisionedSfTable
                            and may be initiated by either the SS or BS.
                            The BS should always initiate SF creation based
                            on the provisioned Service flows configured in
                            wmanIf2BsProvisionedSfTable."
        ::= { wmanIf2BsConfigurationEntry 17 }

    wmanIf2BsAutoSfidRangeMin OBJECT-TYPE
        SYNTAX              Unsigned32 (1..4294967295)
        MAX-ACCESS          read-write
        STATUS              current
        DESCRIPTION         "This object defines the minimum value of the range
                            of SFID values allocated for the BS sector for
                            the purpose of autonomous creation of service
                            flows. This value is used when the object wmanIf2BsAutoSfidEnabled
                            allows autonomous creation of SFIDs."
        ::= { wmanIf2BsConfigurationEntry 18 }

    wmanIf2BsAutoSfidRangeMax OBJECT-TYPE
        SYNTAX              Unsigned32 (1..4294967295)
        MAX-ACCESS          read-write
        STATUS              current
        DESCRIPTION         "This object defines the maximum value of the range
                            of SFID values allocated for the BS sector for
                            the purpose of autonomous creation of the service
                            flows. This value is used when the object wmanIf2BsAutoSfidEnabled
                            allows autonomous creation of SFIDs."
        ::= { wmanIf2BsConfigurationEntry 19 }

    wmanIf2BsAasChanFbckReqFreq OBJECT-TYPE
        SYNTAX              Integer32 (5..10000)
        UNITS               "ms"
        MAX-ACCESS          read-write
        STATUS              current
        DESCRIPTION         "This object defines AAS channel feedback request
                            frequency. It controls the frequency of downlink
                            beam measurements. The relevant MAC messages
                            are AAS-FBCK-REQ/RSP"
        ::= { wmanIf2BsConfigurationEntry 20 }

    wmanIf2BsAasBeamSelectFreq OBJECT-TYPE
        SYNTAX              Integer32 (5..10000)
        UNITS               "ms"
        MAX-ACCESS          read-write
        STATUS              current
        DESCRIPTION         "This object defines AAS beam select frequency.
                            It controls how often SS issues beam select messages.
                            The relevant MAC message is AAS_Beam_Select"
        ::= { wmanIf2BsConfigurationEntry 21 }

    wmanIf2BsAasChanFbckReqResolution OBJECT-TYPE
        SYNTAX              INTEGER {
                                aasChanFbckRes00( 0 ),
                                aasChanFbckRes01( 1 ),
                                aasChanFbckRes10( 2 ),
                                aasChanFbckRes11( 3 )
                            }
        MAX-ACCESS          read-write
        STATUS              current
        DESCRIPTION         "This object defines AAS feedback request frequency
                            measurements resolution. It is coded as follows:
                            aasChanFbckRes00 - every 4th carrier (-100, -96,
                            -92, .., 100) aasChanFbckRes01 - every 8th carrier
                            (-100, -92, -84, .., 100) aasChanFbckRes10 -
                            every 16th carrier (-100, -84, -68, .., 100)
                            aasChanFbckRes11 - every 32th carrier (-100,
                            -68, -36, .., 100)"
        ::= { wmanIf2BsConfigurationEntry 22 }

    wmanIf2BsAasBeamReqResolution OBJECT-TYPE
        SYNTAX              INTEGER {
                                aasBeamReqRes000( 0 ),
                                aasBeamReqRes001( 1 ),
                                aasBeamReqRes010( 2 ),
                                aasBeamReqRes011( 3 ),
                                aasBeamReqRes100( 4 )
                            }
        MAX-ACCESS          read-write
        STATUS              current
        DESCRIPTION         "This object defines AAS beam select request resolution
                            parameter. It is coded as follows: aasBeamReqRes000
                            - every 4th carrier aasBeamReqRes001 - every
                            8th carrier aasBeamReqRes010 - every 16th carrier
                            aasBeamReqRes011 - every 32th carrier aasBeamReqRes100
                            - every 64th carrier"
        ::= { wmanIf2BsConfigurationEntry 23 }

    wmanIf2BsAasNumOptDiversityZones OBJECT-TYPE
        SYNTAX              Integer32 (0..65535)
        MAX-ACCESS          read-write
        STATUS              current
        DESCRIPTION         "This object defines the number of optional diversity
                            zones transmitted in downlink."
        ::= { wmanIf2BsConfigurationEntry 24 }

    wmanIf2BsResetSector OBJECT-TYPE
        SYNTAX              INTEGER {
                                actionResetSectorNoAction( 0 ),
                                actionResetSector( 1 )
                            }
        MAX-ACCESS          read-write
        STATUS              current
        DESCRIPTION         "This object should be implemented as follows:
                            - When set to actionsResetSector value, instructs
                            BS to reset the sector identified by ifIndex.
                            As a result of this action the Phy and Mac of
                            this sector should be reinitialised. - When set
                            to value different than actionsResetSector it
                            should be ignored - When read it should return
                            actionsResetSectorNoAction"
        ::= { wmanIf2BsConfigurationEntry 25 }

    wmanIf2BsSaChallengeTimer OBJECT-TYPE
        SYNTAX              Integer32 (5..20)
        UNITS               "100milliseconds"
        MAX-ACCESS          read-write
        STATUS              current
        DESCRIPTION         "Time prior to re-send of SATEK-Challenge. DEFVAL
                            { 10 }"
        ::= { wmanIf2BsConfigurationEntry 27 }

    wmanIf2BsSaChallengeMaxResends OBJECT-TYPE
        SYNTAX              Integer32 (1..3)
        MAX-ACCESS          read-write
        STATUS              current
        DESCRIPTION         "Maximum number of transmissions of SA-TEK-Challenge.
                            DEFVAL { 3 }"
        ::= { wmanIf2BsConfigurationEntry 28 }

    wmanIf2BsSaTekTimer OBJECT-TYPE
        SYNTAX              Integer32 (100..1000)
        UNITS               "milliseconds"
        MAX-ACCESS          read-write
        STATUS              current
        DESCRIPTION         "Time prior to re-send of SATEK-Request. DEFVAL
                            { 300 }"
        ::= { wmanIf2BsConfigurationEntry 29 }

    wmanIf2BsSaTekReqMaxResends OBJECT-TYPE
        SYNTAX              Integer32 (1..3)
        MAX-ACCESS          read-write
        STATUS              current
        DESCRIPTION         "Maximum number of transmissions of SA-TEK-Request.
                            DEFVAL { 3 }"
        ::= { wmanIf2BsConfigurationEntry 30 }

    wmanIf2Bs2ndEapTimeout OBJECT-TYPE
        SYNTAX              Integer32 (3..10)
        UNITS               "100milliseconds"
        MAX-ACCESS          read-write
        STATUS              current
        DESCRIPTION         "Time, in seconds, to wait for PKMv2_EAP_Start
                            or PKMv2_Authenticated_EAP_Start after the success
                            of the first EAP in double EAP mode. DEFVAL {
                            10 }"
        ::= { wmanIf2BsConfigurationEntry 31 }

    wmanIf2BsEapCompleteResends OBJECT-TYPE
        SYNTAX              Integer32 (1..3)
        MAX-ACCESS          read-write
        STATUS              current
        DESCRIPTION         "Total number of sending PKMv2_EAP_Complete message
                            in double EAP mode. DEFVAL { 3 }"
        ::= { wmanIf2BsConfigurationEntry 32 }

    --
    --
    --
    wmanIf2BsChannelMeasurementTable OBJECT-TYPE
        SYNTAX              SEQUENCE OF WmanIf2BsChannelMeasurementEntry
        MAX-ACCESS          not-accessible
        STATUS              current
        DESCRIPTION         "This table contains channel measurement information
                            as derived from BS measurement of uplink signal
                            from SS, and the downlink signal as reported
                            from SS using REP-REQ/RSP messages. The table
                            shall be maintained as FIFO to store measurement
                            samples that can be used to create RSSI and CINR
                            histogram report. When the measurement entry
                            for a SS reaches the limit, the oldest entry
                            shall be deleted as the new entry is added to
                            the table."
        ::= { wmanIf2BsCps 3 }

    wmanIf2BsChannelMeasurementEntry OBJECT-TYPE
        SYNTAX              WmanIf2BsChannelMeasurementEntry
        MAX-ACCESS          not-accessible
        STATUS              current
        DESCRIPTION         "Each entry in the table contains RSSI and CINR
                            signal quality measurement on signal received
                            from the SS. The primary index is the ifIndex
                            with ifType of ieee80216WMAN identifing the BS
                            sector. wmanIf2BsSsMacAddress identifies the
                            SS from which the signal was received. wmanIf2BsChannelDirection
                            is the index to the direction of the channel.
                            wmanIf2BsHistogramIndex is the index to histogram
                            samples. Since there is no time stamp in the
                            table, wmanIf2BsHistogramIndex should be increased
                            monotonically, and wraps around when it reaches
                            the implementation specific limit."
        INDEX               {
                                ifIndex,
                                wmanIf2BsSsMacAddress,
                                wmanIf2BsChannelDirection,
                                wmanIf2BsHistogramIndex
                            }
        ::= { wmanIf2BsChannelMeasurementTable 1 }

    WmanIf2BsChannelMeasurementEntry ::= SEQUENCE {
        wmanIf2BsChannelDirection
            INTEGER,
        wmanIf2BsHistogramIndex
            Unsigned32,
        wmanIf2BsChannelNumber
            WmanIf2ChannelNumber,
        wmanIf2BsStartFrame
            Integer32,
        wmanIf2BsDuration
            Integer32,
        wmanIf2BsBasicReport
            BITS,
        wmanIf2BsMeanCinrReport
            Integer32,
        wmanIf2BsMeanRssiReport
            Integer32,
        wmanIf2BsStdDeviationCinrReport
            Integer32,
        wmanIf2BsStdDeviationRssiReport
            Integer32
    }

    wmanIf2BsChannelDirection OBJECT-TYPE
        SYNTAX              INTEGER {
                                downstream( 1 ),
                                upstream( 2 )
                            }
        MAX-ACCESS          not-accessible
        STATUS              current
        DESCRIPTION         "wmanIf2BsChannelDirection identifies the direction
                            of a a channel where the measurement takes place."
        ::= { wmanIf2BsChannelMeasurementEntry 1 }

    wmanIf2BsHistogramIndex OBJECT-TYPE
        SYNTAX              Unsigned32 (1..4294967295)
        MAX-ACCESS          read-only
        STATUS              current
        DESCRIPTION         "wmanIf2BsHistogramIndex identifies the histogram
                            samples in the table for each subscriber station."
        ::= { wmanIf2BsChannelMeasurementEntry 2 }

    wmanIf2BsChannelNumber OBJECT-TYPE
        SYNTAX              WmanIf2ChannelNumber
        MAX-ACCESS          read-only
        STATUS              current
        DESCRIPTION         "Physical channel number to be reported on is only
                            applicable to license exempt band. For licensed
                            band, this parameter should be null."
        ::= { wmanIf2BsChannelMeasurementEntry 3 }

    wmanIf2BsStartFrame OBJECT-TYPE
        SYNTAX              Integer32 (0..65535)
        MAX-ACCESS          read-only
        STATUS              current
        DESCRIPTION         "Frame number in which measurement for this channel
                            started."
        ::= { wmanIf2BsChannelMeasurementEntry 4 }

    wmanIf2BsDuration OBJECT-TYPE
        SYNTAX              Integer32 (0..16777215)
        MAX-ACCESS          read-only
        STATUS              current
        DESCRIPTION         "Cumulative measurement duration on the channel
                            in multiples of Ts. For any value exceeding 0xFFFFFF,
                            report 0xFFFFFF."
        ::= { wmanIf2BsChannelMeasurementEntry 5 }

    wmanIf2BsBasicReport OBJECT-TYPE
        SYNTAX              BITS {
                                wirelessHuman( 0 ),
                                unknownTransmission( 1 ),
                                primaryUser( 2 ),
                                channelNotMeasured( 3 )
                            }
        MAX-ACCESS          read-only
        STATUS              current
        DESCRIPTION         "Bit #0: WirelessHUMAN detected on the channel
                            Bit #1: Unknown transmissions detected on the
                            channel Bit #2: Primary User detected on the
                            channel Bit #3: Unmeasured. Channel not measured"
        ::= { wmanIf2BsChannelMeasurementEntry 6 }

    wmanIf2BsMeanCinrReport OBJECT-TYPE
        SYNTAX              Integer32 (-20..37)
        UNITS               "dB"
        MAX-ACCESS          read-only
        STATUS              current
        DESCRIPTION         "Mean CINR report."
        ::= { wmanIf2BsChannelMeasurementEntry 7 }

    wmanIf2BsMeanRssiReport OBJECT-TYPE
        SYNTAX              Integer32 (-123..-40)
        UNITS               "dBm"
        MAX-ACCESS          read-only
        STATUS              current
        DESCRIPTION         "Mean RSSI report."
        ::= { wmanIf2BsChannelMeasurementEntry 8 }

    wmanIf2BsStdDeviationCinrReport OBJECT-TYPE
        SYNTAX              Integer32 (0..29)
        UNITS               "dB"
        MAX-ACCESS          read-only
        STATUS              current
        DESCRIPTION         "Standard deviation CINR report."
        ::= { wmanIf2BsChannelMeasurementEntry 9 }

    wmanIf2BsStdDeviationRssiReport OBJECT-TYPE
        SYNTAX              Integer32 (0..42)
        UNITS               "dB"
        MAX-ACCESS          read-only
        STATUS              current
        DESCRIPTION         "Standard deviation RSSI report."
        ::= { wmanIf2BsChannelMeasurementEntry 10 }

    --
    --
    --
    wmanIf2BsCapabilities OBJECT IDENTIFIER ::= { wmanIf2BsCps 4 }

    wmanIf2BsBasicCapabilitiesTable OBJECT-TYPE
        SYNTAX              SEQUENCE OF WmanIf2BsBasicCapabilitiesEntry
        MAX-ACCESS          not-accessible
        STATUS              current
        DESCRIPTION         "This table contains the basic capabilities of
                            the BS as implemented in BS hardware and software.
                            These capabilities along with the configuration
                            for them (wmanIf2BsCapabilitiesConfigTable) are
                            used for negotiation of basic capabilities with
                            SS using RNG-RSP, SBC-RSP and REG-RSP messages.
                            The negotiated capabilities are obtained by interSubclause
                            of SS raw reported capabilities, BS raw capabilities
                            and BS configured capabilities. The objects in
                            the table have read-only access. The table is
                            maintained by BS."
        ::= { wmanIf2BsCapabilities 3 }

    wmanIf2BsBasicCapabilitiesEntry OBJECT-TYPE
        SYNTAX              WmanIf2BsBasicCapabilitiesEntry
        MAX-ACCESS          not-accessible
        STATUS              current
        DESCRIPTION         "This table provides one row for each BS sector
                            and is indexed by ifIndex."
        INDEX               {
                                ifIndex
                            }
        ::= { wmanIf2BsBasicCapabilitiesTable 1 }

    WmanIf2BsBasicCapabilitiesEntry ::= SEQUENCE {
        wmanIf2BsCapUplinkCidSupport
            WmanIf2NumOfCid,
        wmanIf2BsCapArqSupport
            WmanIf2ArqSupportType,
        wmanIf2BsCapDsxFlowControl
            WmanIf2MaxDsxFlowType,
        wmanIf2BsCapMacCrcSupport
            WmanIf2MacCrcSupport,
        wmanIf2BsCapMcaFlowControl
            WmanIf2MaxMcaFlowType,
        wmanIf2BsCapMcpGroupCidSupport
            WmanIf2MaxMcpGroupCid,
        wmanIf2BsCapPkmFlowControl
            WmanIf2MaxPkmFlowType,
        wmanIf2BsCapAuthPolicyControl
            WmanIf2AuthPolicyType,
        wmanIf2BsCapMaxNumOfSupportedSA
            WmanIf2MaxNumOfSaType,
        wmanIf2BsCapIpVersion
            WmanIf2IpVersionType,
        wmanIf2BsCapMacCsSupportBitMap
            WmanIf2MacCsBitMap,
        wmanIf2BsCapMaxNumOfClassifier
            WmanIf2MaxClassifiers,
        wmanIf2BsCapPhsSupport
            WmanIf2PhsSupportType,
        wmanIf2BsCapBandwidthAllocSupport
            WmanIf2BwAllocSupport,
        wmanIf2BsCapPduConstruction
            WmanIf2PduConstruction,
        wmanIf2BsCapTtgTransitionGap
            WmanIf2SsTransitionGap,
        wmanIf2BsCapRtgTransitionGap
            WmanIf2SsTransitionGap,
        wmanIf2BsCapDownlinkCidSupport
            WmanIf2NumOfCid,
        wmanIf2BsCapPackingSupport
            WmanIf2PackingSupport,
        wmanIf2BsCapExtendedRtpsSupport
            WmanIf2ExtRtpsSupport,
        wmanIf2BsCapMaxNumBurstToMs
            Integer32,
        wmanIf2BsCapIpAddrAllocMethod
            WmanIf2IpAllocMethod,
        wmanIf2BsCapArqAckType
            WmanIf2ArqAckType,
        wmanIf2BsCapMacHeader
            WmanIf2MacHeaderSupp,
        wmanIf2BsCapMaxMacLevelDlFrame
            WmanIf2MaxMacLevel,
        wmanIf2BsCapMaxMacLevelUlFrame
            WmanIf2MaxMacLevel,
        wmanIf2BsCapNumOfProvisionedSf
            Unsigned32,
        wmanIf2BsCapPkmVersion
            WmanIf2PkmVersion,
        wmanIf2BsCapAuthPolicy
            WmanIf2AuthPolicy,
        wmanIf2BsCapMacMode
            WmanIf2MacMode,
        wmanIf2BsCapPnWindowSize
            Integer32,
        wmanIf2BsCapExtCapability
            WmanIf2ExtCapability
    }

    wmanIf2BsCapUplinkCidSupport OBJECT-TYPE
        SYNTAX              WmanIf2NumOfCid
        MAX-ACCESS          read-only
        STATUS              current
        DESCRIPTION         "This object shows the number of Uplink CIDs the
                            BS can support per SS."
        ::= { wmanIf2BsBasicCapabilitiesEntry 1 }

    wmanIf2BsCapArqSupport OBJECT-TYPE
        SYNTAX              WmanIf2ArqSupportType
        MAX-ACCESS          read-only
        STATUS              current
        DESCRIPTION         "This object indicates whether the BS supports
                            ARQ."
        ::= { wmanIf2BsBasicCapabilitiesEntry 2 }

    wmanIf2BsCapDsxFlowControl OBJECT-TYPE
        SYNTAX              WmanIf2MaxDsxFlowType
        MAX-ACCESS          read-only
        STATUS              current
        DESCRIPTION         "This object specifies the maximum number of concurrent
                            DSA, DSC, or DSD transactions that BS allows
                            each SS to have outstanding. DEFVAL { 0 }"
        ::= { wmanIf2BsBasicCapabilitiesEntry 3 }

    wmanIf2BsCapMacCrcSupport OBJECT-TYPE
        SYNTAX              WmanIf2MacCrcSupport
        MAX-ACCESS          read-only
        STATUS              current
        DESCRIPTION         "This object indicates whether or not the BS supports
                            MAC level CRC. DEFVAL { macCrcSupport }"
        ::= { wmanIf2BsBasicCapabilitiesEntry 4 }

    wmanIf2BsCapMcaFlowControl OBJECT-TYPE
        SYNTAX              WmanIf2MaxMcaFlowType
        MAX-ACCESS          read-only
        STATUS              current
        DESCRIPTION         "This object specifies the maximum number of concurrent
                            MCA transactions that BS allows each SS to have.
                            DEFVAL { 0 }"
        ::= { wmanIf2BsBasicCapabilitiesEntry 5 }

    wmanIf2BsCapMcpGroupCidSupport OBJECT-TYPE
        SYNTAX              WmanIf2MaxMcpGroupCid
        MAX-ACCESS          read-only
        STATUS              current
        DESCRIPTION         "This object indicates the maximum number of simultaneous
                            Multicast Polling Groups the BS allows each SS
                            to belong to. DEFVAL { 0 }"
        ::= { wmanIf2BsBasicCapabilitiesEntry 6 }

    wmanIf2BsCapPkmFlowControl OBJECT-TYPE
        SYNTAX              WmanIf2MaxPkmFlowType
        MAX-ACCESS          read-only
        STATUS              current
        DESCRIPTION         "This object specifies the maximum number of concurrent
                            PKM transactions that BS allows each SS to have.
                            DEFVAL { 0 }"
        ::= { wmanIf2BsBasicCapabilitiesEntry 7 }

    wmanIf2BsCapAuthPolicyControl OBJECT-TYPE
        SYNTAX              WmanIf2AuthPolicyType
        MAX-ACCESS          read-only
        STATUS              current
        DESCRIPTION         "This object specifies authorization policy that
                            BS is capable of. A bit value of 0 = 'not supported',
                            1 = 'supported'. If this field is omitted, then
                            both SS and BS shall use the IEEE 802.16 security,
                            constituting X.509 digital certificates and the
                            RSA public key encryption algorithm, as authorization
                            policy."
        ::= { wmanIf2BsBasicCapabilitiesEntry 8 }

    wmanIf2BsCapMaxNumOfSupportedSA OBJECT-TYPE
        SYNTAX              WmanIf2MaxNumOfSaType
        MAX-ACCESS          read-only
        STATUS              current
        DESCRIPTION         "This field specifies maximum number of supported
                            security associations per SS that the BS allows.
                            DEFVAL { 1 }"
        ::= { wmanIf2BsBasicCapabilitiesEntry 9 }

    wmanIf2BsCapIpVersion OBJECT-TYPE
        SYNTAX              WmanIf2IpVersionType
        MAX-ACCESS          read-only
        STATUS              current
        DESCRIPTION         "This object indicates the version of IP BS allows
                            each SS to use on the 2nd Management Connection.
                            The value 'undefined' should not be used for
                            this field."
        ::= { wmanIf2BsBasicCapabilitiesEntry 10 }

    wmanIf2BsCapMacCsSupportBitMap OBJECT-TYPE
        SYNTAX              WmanIf2MacCsBitMap
        MAX-ACCESS          read-only
        STATUS              current
        DESCRIPTION         "This object indicates BS set of MAC convergence
                            sublayer support. When a bit is set, it indicates
                            the corresponding CS feature is supported."
        ::= { wmanIf2BsBasicCapabilitiesEntry 11 }

    wmanIf2BsCapMaxNumOfClassifier OBJECT-TYPE
        SYNTAX              WmanIf2MaxClassifiers
        MAX-ACCESS          read-only
        STATUS              current
        DESCRIPTION         "This object indicates the maximum number of admitted
                            Classifiers per SS that the BS allows. DEFVAL
                            { 0 }"
        ::= { wmanIf2BsBasicCapabilitiesEntry 12 }

    wmanIf2BsCapPhsSupport OBJECT-TYPE
        SYNTAX              WmanIf2PhsSupportType
        MAX-ACCESS          read-only
        STATUS              current
        DESCRIPTION         "This object indicates the level of BS support
                            for PHS. The usage is defined by WmanIf2PhsSupportType.
                            DEFVAL { noPhsSupport }"
        ::= { wmanIf2BsBasicCapabilitiesEntry 13 }

    wmanIf2BsCapBandwidthAllocSupport OBJECT-TYPE
        SYNTAX              WmanIf2BwAllocSupport
        MAX-ACCESS          read-only
        STATUS              current
        DESCRIPTION         "This field indicates the bandwidth allocation
                            properties that the BS permits SSs to use. The
                            usage is defined by WmanIf2BwAllocSupport."
        ::= { wmanIf2BsBasicCapabilitiesEntry 14 }

    wmanIf2BsCapPduConstruction OBJECT-TYPE
        SYNTAX              WmanIf2PduConstruction
        MAX-ACCESS          read-only
        STATUS              current
        DESCRIPTION         "Specifies the capabilities for construction and
                            transmission of MAC PDUs allowed by the BS. The
                            usage is defined by WmanIf2PduConstruction."
        ::= { wmanIf2BsBasicCapabilitiesEntry 15 }

    wmanIf2BsCapTtgTransitionGap OBJECT-TYPE
        SYNTAX              WmanIf2SsTransitionGap
        UNITS               "us"
        MAX-ACCESS          read-only
        STATUS              current
        DESCRIPTION         "This field indicates the transition speed SSTTG
                            for TDD and H-FDD SSs allowed by the BS. The
                            usage is defined by WmanIf2SsTransitionGap."
        ::= { wmanIf2BsBasicCapabilitiesEntry 16 }

    wmanIf2BsCapRtgTransitionGap OBJECT-TYPE
        SYNTAX              WmanIf2SsTransitionGap
        UNITS               "us"
        MAX-ACCESS          read-only
        STATUS              current
        DESCRIPTION         "This field indicates the transition speed SSRTG
                            for TDD and H-FDD SSs allowed by the BS. The
                            usage is defined by WmanIf2SsTransitionGap."
        ::= { wmanIf2BsBasicCapabilitiesEntry 17 }

    wmanIf2BsCapDownlinkCidSupport OBJECT-TYPE
        SYNTAX              WmanIf2NumOfCid
        MAX-ACCESS          read-only
        STATUS              current
        DESCRIPTION         "This object shows the number of Downlink CIDs
                            the SS can support."
        ::= { wmanIf2BsBasicCapabilitiesEntry 18 }

    wmanIf2BsCapPackingSupport OBJECT-TYPE
        SYNTAX              WmanIf2PackingSupport
        MAX-ACCESS          read-only
        STATUS              current
        DESCRIPTION         "Indicates the availability of MS support for Packing."
        ::= { wmanIf2BsBasicCapabilitiesEntry 19 }

    wmanIf2BsCapExtendedRtpsSupport OBJECT-TYPE
        SYNTAX              WmanIf2ExtRtpsSupport
        MAX-ACCESS          read-only
        STATUS              current
        DESCRIPTION         "Indicates the availability of SS support for extended
                            rtPs."
        ::= { wmanIf2BsBasicCapabilitiesEntry 20 }

    wmanIf2BsCapMaxNumBurstToMs OBJECT-TYPE
        SYNTAX              Integer32 (1..16)
        MAX-ACCESS          read-only
        STATUS              current
        DESCRIPTION         "Maximum number of bursts transmitted concurrently
                            to the MS , including all bursts without CID
                            or with CIDs matching the MS CIDs."
        ::= { wmanIf2BsBasicCapabilitiesEntry 21 }

    wmanIf2BsCapIpAddrAllocMethod OBJECT-TYPE
        SYNTAX              WmanIf2IpAllocMethod
        MAX-ACCESS          read-only
        STATUS              current
        DESCRIPTION         "Indicates the method of allocating IP address
                            for the secondary management connection."
        ::= { wmanIf2BsBasicCapabilitiesEntry 22 }

    wmanIf2BsCapArqAckType OBJECT-TYPE
        SYNTAX              WmanIf2ArqAckType
        MAX-ACCESS          read-only
        STATUS              current
        DESCRIPTION         "The value of this parameter specifies the ARQ
                            ACK type supported by the MS."
        ::= { wmanIf2BsBasicCapabilitiesEntry 23 }

    wmanIf2BsCapMacHeader OBJECT-TYPE
        SYNTAX              WmanIf2MacHeaderSupp
        MAX-ACCESS          read-only
        STATUS              current
        DESCRIPTION         "Indicates whether or not the MS and BS support
                            various types of MAC header and extended subheaders."
        ::= { wmanIf2BsBasicCapabilitiesEntry 24 }

    wmanIf2BsCapMaxMacLevelDlFrame OBJECT-TYPE
        SYNTAX              WmanIf2MaxMacLevel
        MAX-ACCESS          read-only
        STATUS              current
        DESCRIPTION         "Maximum amount of MAC level data the MS is capable
                            of processing per DL frame. A value of 0 indicates
                            such limitation does not exist, except the limitation
                            of the physical medium. DEFVAL { 0 }"
        ::= { wmanIf2BsBasicCapabilitiesEntry 25 }

    wmanIf2BsCapMaxMacLevelUlFrame OBJECT-TYPE
        SYNTAX              WmanIf2MaxMacLevel
        MAX-ACCESS          read-only
        STATUS              current
        DESCRIPTION         "Maximum amount of MAC level data the MS is capable
                            of processing per UL frame. A value of 0 indicates
                            such limitation does not exist, except the limitation
                            of the physical medium. DEFVAL { 0 }"
        ::= { wmanIf2BsBasicCapabilitiesEntry 26 }

    wmanIf2BsCapNumOfProvisionedSf OBJECT-TYPE
        SYNTAX              Unsigned32 (0..255)
        MAX-ACCESS          read-only
        STATUS              current
        DESCRIPTION         "When a BS is to transmit multiple DSA transactions
                            for provisioned service flows, this object indicates
                            how many DSA transactions with provisioned service
                            flows will be transmitted."
        ::= { wmanIf2BsBasicCapabilitiesEntry 27 }

    wmanIf2BsCapPkmVersion OBJECT-TYPE
        SYNTAX              WmanIf2PkmVersion
        MAX-ACCESS          read-only
        STATUS              current
        DESCRIPTION         "Indicates a PKM version that SS or BS supports."
        ::= { wmanIf2BsBasicCapabilitiesEntry 28 }

    wmanIf2BsCapAuthPolicy OBJECT-TYPE
        SYNTAX              WmanIf2AuthPolicy
        MAX-ACCESS          read-only
        STATUS              current
        DESCRIPTION         "Indicates authorization policy used by the MS
                            and BS to negotiate and synchronize."
        ::= { wmanIf2BsBasicCapabilitiesEntry 29 }

    wmanIf2BsCapMacMode OBJECT-TYPE
        SYNTAX              WmanIf2MacMode
        MAX-ACCESS          read-only
        STATUS              current
        DESCRIPTION         "Indicates a MAC (Message Authentication Code)
                            mode that MS supports."
        ::= { wmanIf2BsBasicCapabilitiesEntry 30 }

    wmanIf2BsCapPnWindowSize OBJECT-TYPE
        SYNTAX              Integer32 (0..65535)
        MAX-ACCESS          read-only
        STATUS              current
        DESCRIPTION         "Specifies the size capability of the receiver
                            PN window for SAs and management connections.
                            The receiver shall track PNs within this window
                            to prevent replay attacks (see 7.5.1.2.4)."
        ::= { wmanIf2BsBasicCapabilitiesEntry 31 }

    wmanIf2BsCapExtCapability OBJECT-TYPE
        SYNTAX              WmanIf2ExtCapability
        MAX-ACCESS          read-only
        STATUS              current
        DESCRIPTION         "Indicates the extended subheader format support."
        ::= { wmanIf2BsBasicCapabilitiesEntry 32 }

    wmanIf2BsCapabilitiesConfigTable OBJECT-TYPE
        SYNTAX              SEQUENCE OF WmanIf2BsCapabilitiesConfigEntry
        MAX-ACCESS          not-accessible
        STATUS              current
        DESCRIPTION         "This table contains the configuration for basic
                            capabilities of BS. The table is intended to
                            be used to restrict the Capabilities implemented
                            by BS, for example in order to comply with local
                            regulatory requirements. The BS should use the
                            configuration along with the implemented Capabilities
                            (wmanIf2BsBasicCapabilitiesTable) for negotiation
                            of basic capabilities with SS using RNG-RSP,
                            SBC-RSP and REG-RSP messages. The negotiated
                            capabilities are obtained by interSubclause of
                            SS reported capabilities, BS raw capabilities
                            and BS configured capabilities. The objects in
                            the table have read-write access. The rows are
                            created by BS as a copy of wmanIf2BsBasicCapabilitiesTable
                            and can be modified by NMS."
        ::= { wmanIf2BsCapabilities 4 }

    wmanIf2BsCapabilitiesConfigEntry OBJECT-TYPE
        SYNTAX              WmanIf2BsCapabilitiesConfigEntry
        MAX-ACCESS          not-accessible
        STATUS              current
        DESCRIPTION         "This table provides one row for each BS sector
                            and is indexed by ifIndex."
        INDEX               {
                                ifIndex
                            }
        ::= { wmanIf2BsCapabilitiesConfigTable 1 }

    WmanIf2BsCapabilitiesConfigEntry ::= SEQUENCE {
        wmanIf2BsCapCfgUplinkCidSupport
            WmanIf2NumOfCid,
        wmanIf2BsCapCfgArqSupport
            WmanIf2ArqSupportType,
        wmanIf2BsCapCfgDsxFlowControl
            WmanIf2MaxDsxFlowType,
        wmanIf2BsCapCfgMacCrcSupport
            WmanIf2MacCrcSupport,
        wmanIf2BsCapCfgMcaFlowControl
            WmanIf2MaxMcaFlowType,
        wmanIf2BsCapCfgMcpGroupCidSupport
            WmanIf2MaxMcpGroupCid,
        wmanIf2BsCapCfgPkmFlowControl
            WmanIf2MaxPkmFlowType,
        wmanIf2BsCapCfgAuthPolicyControl
            WmanIf2AuthPolicyType,
        wmanIf2BsCapCfgMaxNumOfSupportedSA
            WmanIf2MaxNumOfSaType,
        wmanIf2BsCapCfgIpVersion
            WmanIf2IpVersionType,
        wmanIf2BsCapCfgMacCsSupportBitMap
            WmanIf2MacCsBitMap,
        wmanIf2BsCapCfgMaxNumOfClassifier
            WmanIf2MaxClassifiers,
        wmanIf2BsCapCfgPhsSupport
            WmanIf2PhsSupportType,
        wmanIf2BsCapCfgBandwidthAllocSupport
            WmanIf2BwAllocSupport,
        wmanIf2BsCapCfgPduConstruction
            WmanIf2PduConstruction,
        wmanIf2BsCapCfgTtgTransitionGap
            WmanIf2SsTransitionGap,
        wmanIf2BsCapCfgRtgTransitionGap
            WmanIf2SsTransitionGap,
        wmanIf2BsCapCfgDownlinkCidSupport
            WmanIf2NumOfCid,
        wmanIf2BsCapCfgPackingSupport
            WmanIf2PackingSupport,
        wmanIf2BsCapCfgExtendedRtpsSupport
            WmanIf2ExtRtpsSupport,
        wmanIf2BsCapCfgMaxNumBurstToMs
            Integer32,
        wmanIf2BsCapCfgIpAddrAllocMethod
            WmanIf2IpAllocMethod,
        wmanIf2BsCapCfgArqAckType
            WmanIf2ArqAckType,
        wmanIf2BsCapCfgMacHeader
            WmanIf2MacHeaderSupp,
        wmanIf2BsCapCfgMaxMacLevelDlFrame
            WmanIf2MaxMacLevel,
        wmanIf2BsCapCfgMaxMacLevelUlFrame
            WmanIf2MaxMacLevel,
        wmanIf2BsCapCfgNumOfProvisionedSf
            Unsigned32,
        wmanIf2BsCapCfgPkmVersion
            WmanIf2PkmVersion,
        wmanIf2BsCapCfgAuthPolicy
            WmanIf2AuthPolicy,
        wmanIf2BsCapCfgMacMode
            WmanIf2MacMode,
        wmanIf2BsCapCfgPnWindowSize
            Integer32,
        wmanIf2BsCapCfgExtCapability
            WmanIf2ExtCapability
    }

    wmanIf2BsCapCfgUplinkCidSupport OBJECT-TYPE
        SYNTAX              WmanIf2NumOfCid
        MAX-ACCESS          read-write
        STATUS              current
        DESCRIPTION         "This object shows the configured number of Uplink
                            CIDs the BS can support per SS."
        ::= { wmanIf2BsCapabilitiesConfigEntry 1 }

    wmanIf2BsCapCfgArqSupport OBJECT-TYPE
        SYNTAX              WmanIf2ArqSupportType
        MAX-ACCESS          read-write
        STATUS              current
        DESCRIPTION         "This object indicates whether the BS is configured
                            to support ARQ."
        ::= { wmanIf2BsCapabilitiesConfigEntry 2 }

    wmanIf2BsCapCfgDsxFlowControl OBJECT-TYPE
        SYNTAX              WmanIf2MaxDsxFlowType
        MAX-ACCESS          read-write
        STATUS              current
        DESCRIPTION         "This object specifies the configured maximum number
                            of concurrent DSA, DSC, or DSD transactions that
                            BS allows each SS to have outstanding. DEFVAL
                            { 0 }"
        ::= { wmanIf2BsCapabilitiesConfigEntry 3 }

    wmanIf2BsCapCfgMacCrcSupport OBJECT-TYPE
        SYNTAX              WmanIf2MacCrcSupport
        MAX-ACCESS          read-write
        STATUS              current
        DESCRIPTION         "This object indicates whether BS is configured
                            to support MAC level CRC. DEFVAL { macCrcSupport
                            }"
        ::= { wmanIf2BsCapabilitiesConfigEntry 4 }

    wmanIf2BsCapCfgMcaFlowControl OBJECT-TYPE
        SYNTAX              WmanIf2MaxMcaFlowType
        MAX-ACCESS          read-write
        STATUS              current
        DESCRIPTION         "This object specifies the maximum number of concurrent
                            MCA transactions that BS is configured to allow
                            each SS to have. DEFVAL { 0 }"
        ::= { wmanIf2BsCapabilitiesConfigEntry 5 }

    wmanIf2BsCapCfgMcpGroupCidSupport OBJECT-TYPE
        SYNTAX              WmanIf2MaxMcpGroupCid
        MAX-ACCESS          read-write
        STATUS              current
        DESCRIPTION         "This object indicates the maximum number of simultaneous
                            Multicast Polling Groups the BS is configured
                            to allow each SS to belong to. DEFVAL { 0 }"
        ::= { wmanIf2BsCapabilitiesConfigEntry 6 }

    wmanIf2BsCapCfgPkmFlowControl OBJECT-TYPE
        SYNTAX              WmanIf2MaxPkmFlowType
        MAX-ACCESS          read-write
        STATUS              current
        DESCRIPTION         "This object specifies the maximum number of concurrent
                            PKM transactions that BS is configured to allow
                            each SS to have. DEFVAL { 0 }"
        ::= { wmanIf2BsCapabilitiesConfigEntry 7 }

    wmanIf2BsCapCfgAuthPolicyControl OBJECT-TYPE
        SYNTAX              WmanIf2AuthPolicyType
        MAX-ACCESS          read-write
        STATUS              current
        DESCRIPTION         "This object specifies authorization policy that
                            BS is configured to be capable of. A bit value
                            of 0 = 'not supported', 1 = 'supported'. If this
                            field is omitted, then both SS and BS shall use
                            the IEEE 802.16 security, constituting X.509
                            digital certificates and the RSA public key encryption
                            algorithm, as authorization policy."
        ::= { wmanIf2BsCapabilitiesConfigEntry 8 }

    wmanIf2BsCapCfgMaxNumOfSupportedSA OBJECT-TYPE
        SYNTAX              WmanIf2MaxNumOfSaType
        MAX-ACCESS          read-write
        STATUS              current
        DESCRIPTION         "This field specifies configured maximum number
                            of supported security association per SS. DEFVAL
                            { 1 }"
        ::= { wmanIf2BsCapabilitiesConfigEntry 9 }

    wmanIf2BsCapCfgIpVersion OBJECT-TYPE
        SYNTAX              WmanIf2IpVersionType
        MAX-ACCESS          read-write
        STATUS              current
        DESCRIPTION         "This object indicates the configured version of
                            IP that the BS allows each SS to use on the 2nd
                            Management Connection. The value 'undefined'
                            should not be used in this field."
        ::= { wmanIf2BsCapabilitiesConfigEntry 10 }

    wmanIf2BsCapCfgMacCsSupportBitMap OBJECT-TYPE
        SYNTAX              WmanIf2MacCsBitMap
        MAX-ACCESS          read-write
        STATUS              current
        DESCRIPTION         "This object indicates BS configured set of MAC
                            convergence sublayer support. When a bit is set,
                            it indicates the corresponding CS feature is
                            supported."
        ::= { wmanIf2BsCapabilitiesConfigEntry 11 }

    wmanIf2BsCapCfgMaxNumOfClassifier OBJECT-TYPE
        SYNTAX              WmanIf2MaxClassifiers
        MAX-ACCESS          read-write
        STATUS              current
        DESCRIPTION         "This object indicates the configured maximum number
                            of admitted Classifiers per SS that the BS can
                            support. DEFVAL { 0 }"
        ::= { wmanIf2BsCapabilitiesConfigEntry 12 }

    wmanIf2BsCapCfgPhsSupport OBJECT-TYPE
        SYNTAX              WmanIf2PhsSupportType
        MAX-ACCESS          read-write
        STATUS              current
        DESCRIPTION         "This object indicates the configured level of
                            BS support for PHS. DEFVAL { noPhsSupport }"
        ::= { wmanIf2BsCapabilitiesConfigEntry 13 }

    wmanIf2BsCapCfgBandwidthAllocSupport OBJECT-TYPE
        SYNTAX              WmanIf2BwAllocSupport
        MAX-ACCESS          read-write
        STATUS              current
        DESCRIPTION         "This field indicates configured properties of
                            the BS for bandwidth allocation purposes. The
                            usage is defined by WmanIf2CapBwAllocSupport."
        ::= { wmanIf2BsCapabilitiesConfigEntry 14 }

    wmanIf2BsCapCfgPduConstruction OBJECT-TYPE
        SYNTAX              WmanIf2PduConstruction
        MAX-ACCESS          read-write
        STATUS              current
        DESCRIPTION         "Specifies configured capabilities for construction
                            and transmission of MAC PDUs. The usage is defined
                            by WmanIf2PduConstruction."
        ::= { wmanIf2BsCapabilitiesConfigEntry 15 }

    wmanIf2BsCapCfgTtgTransitionGap OBJECT-TYPE
        SYNTAX              WmanIf2SsTransitionGap
        UNITS               "us"
        MAX-ACCESS          read-write
        STATUS              current
        DESCRIPTION         "This field indicates the configured transition
                            speed SSTTG for TDD and H-FDD SSs. The usage
                            is defined by WmanIf2SsTransitionGap."
        ::= { wmanIf2BsCapabilitiesConfigEntry 16 }

    wmanIf2BsCapCfgRtgTransitionGap OBJECT-TYPE
        SYNTAX              WmanIf2SsTransitionGap
        UNITS               "us"
        MAX-ACCESS          read-write
        STATUS              current
        DESCRIPTION         "This field indicates the configured transition
                            speed SSRTG for TDD and H-FDD SSs. The usage
                            is defined by WmanIf2SsTransitionGap."
        ::= { wmanIf2BsCapabilitiesConfigEntry 17 }

    wmanIf2BsCapCfgDownlinkCidSupport OBJECT-TYPE
        SYNTAX              WmanIf2NumOfCid
        MAX-ACCESS          read-write
        STATUS              current
        DESCRIPTION         "This object shows the number of Downlink CIDs
                            the SS can support."
        ::= { wmanIf2BsCapabilitiesConfigEntry 18 }

    wmanIf2BsCapCfgPackingSupport OBJECT-TYPE
        SYNTAX              WmanIf2PackingSupport
        MAX-ACCESS          read-write
        STATUS              current
        DESCRIPTION         "Change MAX-ACCESS from R/O to R/W by NEC. Indicates
                            the availability of MS support for Packing."
        ::= { wmanIf2BsCapabilitiesConfigEntry 19 }

    wmanIf2BsCapCfgExtendedRtpsSupport OBJECT-TYPE
        SYNTAX              WmanIf2ExtRtpsSupport
        MAX-ACCESS          read-write
        STATUS              current
        DESCRIPTION         "Indicates the availability of SS support for extended
                            rtPs."
        ::= { wmanIf2BsCapabilitiesConfigEntry 20 }

    wmanIf2BsCapCfgMaxNumBurstToMs OBJECT-TYPE
        SYNTAX              Integer32 (1..16)
        MAX-ACCESS          read-write
        STATUS              current
        DESCRIPTION         "Maximum number of bursts transmitted concurrently
                            to the MS , including all bursts without CID
                            or with CIDs matching the MS CIDs."
        ::= { wmanIf2BsCapabilitiesConfigEntry 21 }

    wmanIf2BsCapCfgIpAddrAllocMethod OBJECT-TYPE
        SYNTAX              WmanIf2IpAllocMethod
        MAX-ACCESS          read-write
        STATUS              current
        DESCRIPTION         "Indicates the method of allocating IP address
                            for the secondary management connection."
        ::= { wmanIf2BsCapabilitiesConfigEntry 22 }

    wmanIf2BsCapCfgArqAckType OBJECT-TYPE
        SYNTAX              WmanIf2ArqAckType
        MAX-ACCESS          read-write
        STATUS              current
        DESCRIPTION         "The value of this parameter specifies the ARQ
                            ACK type supported by the MS."
        ::= { wmanIf2BsCapabilitiesConfigEntry 23 }

    wmanIf2BsCapCfgMacHeader OBJECT-TYPE
        SYNTAX              WmanIf2MacHeaderSupp
        MAX-ACCESS          read-write
        STATUS              current
        DESCRIPTION         "Indicates whether or not the MS and BS support
                            various types of MAC header and extended subheaders."
        ::= { wmanIf2BsCapabilitiesConfigEntry 24 }

    wmanIf2BsCapCfgMaxMacLevelDlFrame OBJECT-TYPE
        SYNTAX              WmanIf2MaxMacLevel
        MAX-ACCESS          read-write
        STATUS              current
        DESCRIPTION         "Maximum amount of MAC level data the MS is capable
                            of processing per DL frame. A value of 0 indicates
                            such limitation does not exist, except the limitation
                            of the physical medium. DEFVAL { 0 }"
        ::= { wmanIf2BsCapabilitiesConfigEntry 25 }

    wmanIf2BsCapCfgMaxMacLevelUlFrame OBJECT-TYPE
        SYNTAX              WmanIf2MaxMacLevel
        MAX-ACCESS          read-write
        STATUS              current
        DESCRIPTION         "Maximum amount of MAC level data the MS is capable
                            of processing per UL frame. A value of 0 indicates
                            such limitation does not exist, except the limitation
                            of the physical medium. DEFVAL { 0 }"
        ::= { wmanIf2BsCapabilitiesConfigEntry 26 }

    wmanIf2BsCapCfgNumOfProvisionedSf OBJECT-TYPE
        SYNTAX              Unsigned32 (0..255)
        MAX-ACCESS          read-write
        STATUS              current
        DESCRIPTION         "When a BS is to transmit multiple DSA transactions
                            for provisioned service flows, this object indicates
                            how many DSA transactions with provisioned service
                            flows will be transmitted."
        ::= { wmanIf2BsCapabilitiesConfigEntry 27 }

    wmanIf2BsCapCfgPkmVersion OBJECT-TYPE
        SYNTAX              WmanIf2PkmVersion
        MAX-ACCESS          read-write
        STATUS              current
        DESCRIPTION         "Indicates a PKM version that SS or BS supports.
                             CHANGE from read-only to read-write by NEC 2008.6.11"
        ::= { wmanIf2BsCapabilitiesConfigEntry 28 }

    wmanIf2BsCapCfgAuthPolicy OBJECT-TYPE
        SYNTAX              WmanIf2AuthPolicy
        MAX-ACCESS          read-only
        STATUS              current
        DESCRIPTION         "Indicates authorization policy used by the MS
                            and BS to negotiate and synchronize."
        ::= { wmanIf2BsCapabilitiesConfigEntry 29 }

    wmanIf2BsCapCfgMacMode OBJECT-TYPE
        SYNTAX              WmanIf2MacMode
        MAX-ACCESS          read-only
        STATUS              current
        DESCRIPTION         "Indicates a MAC (Message Authentication Code)
                            mode that MS supports."
        ::= { wmanIf2BsCapabilitiesConfigEntry 30 }

    wmanIf2BsCapCfgPnWindowSize OBJECT-TYPE
        SYNTAX              Integer32 (0..65535)
        MAX-ACCESS          read-write
        STATUS              current
        DESCRIPTION         "Change MAX-ACCESS from R/O to R/W by NEC. Specifies
                            the size capability of the receiver PN window
                            for SAs and management connections. The receiver
                            shall track PNs within this window to prevent
                            replay attacks (see 7.5.1.2.4)."
        ::= { wmanIf2BsCapabilitiesConfigEntry 31 }

    wmanIf2BsCapCfgExtCapability OBJECT-TYPE
        SYNTAX              WmanIf2ExtCapability
        MAX-ACCESS          read-only
        STATUS              current
        DESCRIPTION         "Indicates the extended subheader format support."
        ::= { wmanIf2BsCapabilitiesConfigEntry 32 }

    wmanIf2BsSsActionsTable OBJECT-TYPE
        SYNTAX              SEQUENCE OF WmanIf2BsSsActionsEntry
        MAX-ACCESS          not-accessible
        STATUS              current
        DESCRIPTION         "This table contains all the actions specified
                            for SSs in the standard. The actions are routed
                            down to SS using unsolicited MAC messages: REG-RSP,
                            DREG-REQ and RES-CMD. The table also contains
                            the parameters of the actions in cases where
                            they are specified by the standard."
        ::= { wmanIf2BsCps 5 }

    wmanIf2BsSsActionsEntry OBJECT-TYPE
        SYNTAX              WmanIf2BsSsActionsEntry
        MAX-ACCESS          not-accessible
        STATUS              current
        DESCRIPTION         "This table is indexed by wmanIf2BsSsActionsMacAddress.
                            The action can be requested for SS in any state
                            not only those registered. However BS will decide
                            whether the action is applicable to the SS based
                            on its current state and execute it or skip it
                            as defined in each action definition."
        INDEX               {
                                wmanIf2BsSsActionsMacAddress
                            }
        ::= { wmanIf2BsSsActionsTable 1 }

    WmanIf2BsSsActionsEntry ::= SEQUENCE {
        wmanIf2BsSsActionsMacAddress
            MacAddress,
        wmanIf2BsSsActionsResetSs
            INTEGER,
        wmanIf2BsSsActionsAbortSs
            INTEGER,
        wmanIf2BsSsActionsOverrideDnFreq
            Unsigned32,
        wmanIf2BsSsActionsOverrideChannelId
            Integer32,
        wmanIf2BsSsActionsDeReRegSs
            INTEGER,
        wmanIf2BsSsActionsDeReRegSsCode
            INTEGER,
        wmanIf2BsSsActionsRowStatus
            RowStatus
    }

    wmanIf2BsSsActionsMacAddress OBJECT-TYPE
        SYNTAX              MacAddress
        MAX-ACCESS          not-accessible
        STATUS              current
        DESCRIPTION         "This object uniquely identifies the SS as an action
                            target."
        ::= { wmanIf2BsSsActionsEntry 1 }

    wmanIf2BsSsActionsResetSs OBJECT-TYPE
        SYNTAX              INTEGER {
                                actionsResetSsNoAction( 0 ),
                                actionsResetSs( 1 )
                            }
        MAX-ACCESS          read-create
        STATUS              current
        DESCRIPTION         "This object should be implemented as follows:
                            - When set to actionsResetSs value, instructs
                            BS to send RES-CMD to SS - When set to value
                            different than actionsResetSs it should be ignored
                            - When read it should return actionsResetSsNoAction
                            The RES-CMD message shall be transmitted by the
                            BS on an SS Basic CID to force the SS to reset
                            itself, reinitialize its MAC, and repeat initial
                            system access."
        ::= { wmanIf2BsSsActionsEntry 2 }

    wmanIf2BsSsActionsAbortSs OBJECT-TYPE
        SYNTAX              INTEGER {
                                actionsAbortSsNoAction( 0 ),
                                actionsAbortSs( 1 ),
                                actionAbortSsParams( 2 )
                            }
        MAX-ACCESS          read-create
        STATUS              current
        DESCRIPTION         "This object should be implemented as follows:
                            - When set to actionsAbortSs value, it instructs
                            BS to send unsolicited RNG-RSP with Ranging Status
                            equal to 'abort' without override parameters
                            - When set to actionAbortSsParams value, it instructs
                            BS to send unsolicited RNG-RSP with Ranging Status
                            equal to 'abort' and with 'Downlink Frequency
                            Override' and 'Uplink Channel ID Override' parameters.
                            - When set to any other value it should be ignored
                            - When read it should returned actionsAbortSsNoAction"
        ::= { wmanIf2BsSsActionsEntry 3 }

    wmanIf2BsSsActionsOverrideDnFreq OBJECT-TYPE
        SYNTAX              Unsigned32
        UNITS               "kHz"
        MAX-ACCESS          read-create
        STATUS              current
        DESCRIPTION         "This object is used as a parmeter of the AbortSs
                            action with the code actionAbortSsParams. It
                            is used for licensed bands only. It defines the
                            Center frequency, in kHz, of new downlink channel
                            where the SS should redo initial ranging."
        ::= { wmanIf2BsSsActionsEntry 4 }

    wmanIf2BsSsActionsOverrideChannelId OBJECT-TYPE
        SYNTAX              Integer32 (0..199)
        MAX-ACCESS          read-create
        STATUS              current
        DESCRIPTION         "This object is used as a parmeter of the AbortSs
                            action with the code actionAbortSsParams. It
                            is coded as follows: - Licensed bands: The identifier
                            of the uplink channel with which the SS is to
                            redo initial ranging (not used with PHYs without
                            channelized uplinks). - License-exempt bands:
                            The Channel Nr (see 8.5.1) where the SS should
                            redo initial ranging."
        ::= { wmanIf2BsSsActionsEntry 5 }

    wmanIf2BsSsActionsDeReRegSs OBJECT-TYPE
        SYNTAX              INTEGER {
                                actionsDeReRegSsNoAction( 0 ),
                                actionsDeReRegSs( 1 )
                            }
        MAX-ACCESS          read-create
        STATUS              current
        DESCRIPTION         "This object should be implemented as follows:
                            - When set to actionsDeReRegSs value, instructs
                            BS to send DREG-CMD to SS with specified action
                            code - When set to value different than actionsDeReRegSs
                            it should be ignored - When read it should return
                            actionsDeReRegSsNoAction The DREG-CMD message
                            shall be transmitted by the BS on an SS Basic
                            CID to force the SS to change its access state.
                            Upon receiving a DREG-CMD, the SS shall take
                            the action indicated by the action code defined
                            by wmanIf2BsSsActionsDeReRegSsCode."
        ::= { wmanIf2BsSsActionsEntry 6 }

    wmanIf2BsSsActionsDeReRegSsCode OBJECT-TYPE
        SYNTAX              INTEGER {
                                actionsDeReRegSsCodeChangeChan( 0 ),
                                actionsDeReRegSsCodeNoTransmit( 1 ),
                                actionsDeReRegSsCodeLtdTransmit( 2 ),
                                actionsDeReRegSsCodeResume( 3 )
                            }
        MAX-ACCESS          read-create
        STATUS              current
        DESCRIPTION         "This object defines the action code for wmanIf2BsSsActionsDeReRegSs
                            action. The codes are defined as follows: actionsDeReRegSsCodeChangeChan
                            - SS shall leave the current channel and attempt
                            to access another channel. actionsDeReRegSsCodeNoTransmit
                            - SS shall listen to the current channel but
                            shall not transmit until an RES-CMD message or
                            DREG_CMD with an Action Code that allows transmission
                            is received. actionsDeReRegSsCodeLtdTransmit
                            - SS shall listen to the current channel but
                            only transmit on the Basic, Primary Management
                            and 2nd Management Connections. actionsDeReRegSsCodeResume
                            - SS shall return to normal operation and may
                            transmit on any of its active connections."
        ::= { wmanIf2BsSsActionsEntry 7 }

    wmanIf2BsSsActionsRowStatus OBJECT-TYPE
        SYNTAX              RowStatus
        MAX-ACCESS          read-create
        STATUS              current
        DESCRIPTION         "This object is used to ensure that the write operation
                            to multiple columns is guaranteed to be treated
                            as atomic operation by agent."
        ::= { wmanIf2BsSsActionsEntry 8 }

    --
    --
    --
    --
    wmanIf2BsPkmObjects OBJECT IDENTIFIER ::= { wmanIf2BsObjects 3 }

    --
    --
    --
    wmanIf2BsPkmSecurityCapabilityTable OBJECT-TYPE
        SYNTAX              SEQUENCE OF WmanIf2BsPkmSecurityCapabilityEntry
        MAX-ACCESS          not-accessible
        STATUS              current
        DESCRIPTION         "This table contains the list of the cryptographic
                            suite(s) an SS supports."
        ::= { wmanIf2BsPkmObjects 1 }

    wmanIf2BsPkmSecurityCapabilityEntry OBJECT-TYPE
        SYNTAX              WmanIf2BsPkmSecurityCapabilityEntry
        MAX-ACCESS          not-accessible
        STATUS              current
        DESCRIPTION         "This table is triple indexed by ifIndex and wmanIf2BsSsSecurityCapIndex."
        INDEX               {
                                ifIndex,
                                wmanIf2BsPkmSecurityCapIndex
                            }
        ::= { wmanIf2BsPkmSecurityCapabilityTable 1 }

    WmanIf2BsPkmSecurityCapabilityEntry ::= SEQUENCE {
        wmanIf2BsPkmSecurityCapIndex
            Integer32,
        wmanIf2BsPkmScDataEncryptAlgorithm
            WmanIf2DataEncryptAlgId,
        wmanIf2BsPkmScDataAuthentAlgorithm
            WmanIf2DataAuthAlgId,
        wmanIf2BsPkmScEncryptAlgorithm
            WmanIf2TekEncryptAlgId
    }

    wmanIf2BsPkmSecurityCapIndex OBJECT-TYPE
        SYNTAX              Integer32 (1..65535)
        MAX-ACCESS          not-accessible
        STATUS              current
        DESCRIPTION         "The index value which uniquely identifies an entry
                            in the wmanIf2BsPkmSecurityCapabilityTable"
        ::= { wmanIf2BsPkmSecurityCapabilityEntry 1 }

    wmanIf2BsPkmScDataEncryptAlgorithm OBJECT-TYPE
        SYNTAX              WmanIf2DataEncryptAlgId
        MAX-ACCESS          read-only
        STATUS              current
        DESCRIPTION         "The value of this object is the data encryption
                            algorithm being utilized."
        ::= { wmanIf2BsPkmSecurityCapabilityEntry 2 }

    wmanIf2BsPkmScDataAuthentAlgorithm OBJECT-TYPE
        SYNTAX              WmanIf2DataAuthAlgId
        MAX-ACCESS          read-only
        STATUS              current
        DESCRIPTION         "The value of this object is the data authentication
                            algorithm being utilized."
        ::= { wmanIf2BsPkmSecurityCapabilityEntry 3 }

    wmanIf2BsPkmScEncryptAlgorithm OBJECT-TYPE
        SYNTAX              WmanIf2TekEncryptAlgId
        MAX-ACCESS          read-only
        STATUS              current
        DESCRIPTION         "The value of this object is the TEK key encryption
                            algorithm being utilized."
        ::= { wmanIf2BsPkmSecurityCapabilityEntry 4 }

    --
    --
    --
    wmanIf2BsSsPkmSecurityCapabilityTable OBJECT-TYPE
        SYNTAX              SEQUENCE OF WmanIf2BsSsPkmSecurityCapabilityEntry
        MAX-ACCESS          not-accessible
        STATUS              current
        DESCRIPTION         "This table contains the SS's Security Capabilities
                            that are conveyed by the Auth Request or PKMv2
                            SA-TEK-Request message. It contains the list
                            of the cryptographic suite(s) an SS supports."
        ::= { wmanIf2BsPkmObjects 2 }

    wmanIf2BsSsPkmSecurityCapabilityEntry OBJECT-TYPE
        SYNTAX              WmanIf2BsSsPkmSecurityCapabilityEntry
        MAX-ACCESS          not-accessible
        STATUS              current
        DESCRIPTION         "This table is triple indexed by ifIndex, wmanIf2BsSsSecurityCapIndex
                            and wmanIf2BsSsMacAddress."
        INDEX               {
                                ifIndex,
                                wmanIf2BsSsMacAddress,
                                wmanIf2BsSsPkmSecurityCapIndex
                            }
        ::= { wmanIf2BsSsPkmSecurityCapabilityTable 1 }

    WmanIf2BsSsPkmSecurityCapabilityEntry ::= SEQUENCE {
        wmanIf2BsSsPkmSecurityCapIndex
            Integer32,
        wmanIf2BsSsPkmScDataEncryptAlgorithm
            WmanIf2DataEncryptAlgId,
        wmanIf2BsSsPkmScDataAuthentAlgorithm
            WmanIf2DataAuthAlgId,
        wmanIf2BsSsPkmScEncryptAlgorithm
            WmanIf2TekEncryptAlgId
    }

    wmanIf2BsSsPkmSecurityCapIndex OBJECT-TYPE
        SYNTAX              Integer32 (1..65535)
        MAX-ACCESS          not-accessible
        STATUS              current
        DESCRIPTION         "The index value which uniquely identifies an entry
                            in the wmanIf2BsSsPkmSecurityCapabilityTable"
        ::= { wmanIf2BsSsPkmSecurityCapabilityEntry 1 }

    wmanIf2BsSsPkmScDataEncryptAlgorithm OBJECT-TYPE
        SYNTAX              WmanIf2DataEncryptAlgId
        MAX-ACCESS          read-only
        STATUS              current
        DESCRIPTION         "The value of this object is the data encryption
                            algorithm being utilized."
        ::= { wmanIf2BsSsPkmSecurityCapabilityEntry 2 }

    wmanIf2BsSsPkmScDataAuthentAlgorithm OBJECT-TYPE
        SYNTAX              WmanIf2DataAuthAlgId
        MAX-ACCESS          read-only
        STATUS              current
        DESCRIPTION         "The value of this object is the data authentication
                            algorithm being utilized."
        ::= { wmanIf2BsSsPkmSecurityCapabilityEntry 3 }

    wmanIf2BsSsPkmScEncryptAlgorithm OBJECT-TYPE
        SYNTAX              WmanIf2TekEncryptAlgId
        MAX-ACCESS          read-only
        STATUS              current
        DESCRIPTION         "The value of this object is the TEK key encryption
                            algorithm being utilized."
        ::= { wmanIf2BsSsPkmSecurityCapabilityEntry 4 }

    wmanIf2BsPkmV1Objects OBJECT IDENTIFIER ::= { wmanIf2BsPkmObjects 3 }

    --
    --
    --
    wmanIf2BsPkmV1ConfigTable OBJECT-TYPE
        SYNTAX              SEQUENCE OF WmanIf2BsPkmV1ConfigEntry
        MAX-ACCESS          not-accessible
        STATUS              current
        DESCRIPTION         "This table contains the configuration of the PKM
                            attributes that are to be used for BS and SS."
        ::= { wmanIf2BsPkmV1Objects 1 }

    wmanIf2BsPkmV1ConfigEntry OBJECT-TYPE
        SYNTAX              WmanIf2BsPkmV1ConfigEntry
        MAX-ACCESS          not-accessible
        STATUS              current
        DESCRIPTION         "Each entry contains objects that define the PKM
                            attributes of each BS wireless interface, and
                            all SSs that are connected with such BS. The
                            table is indexed by ifIndex that is associated
                            with the BS sector."
        INDEX               {
                                ifIndex
                            }
        ::= { wmanIf2BsPkmV1ConfigTable 1 }

    WmanIf2BsPkmV1ConfigEntry ::= SEQUENCE {
        wmanIf2BsPkmV1AkLifetime
            Integer32,
        wmanIf2BsPkmV1TekLifetime
            Integer32,
        wmanIf2BsPkmV1SelfSigManufCertTrust
            INTEGER,
        wmanIf2BsPkmV1AuthWaitTimeout
            Integer32,
        wmanIf2BsPkmV1ReauthWaitTimeout
            Integer32,
        wmanIf2BsPkmV1AuthGraceTime
            Integer32,
        wmanIf2BsPkmV1OpWaitTimeout
            Integer32,
        wmanIf2BsPkmV1RekeyWaitTimeout
            Integer32,
        wmanIf2BsPkmV1TekGraceTime
            Integer32,
        wmanIf2BsPkmV1AuthRejectWaitTimeout
            Integer32,
        wmanIf2BsPkmV1CheckCertValidityPeriods
            TruthValue
    }

    wmanIf2BsPkmV1AkLifetime OBJECT-TYPE
        SYNTAX              Integer32 (86400..6048000)
        UNITS               "seconds"
        MAX-ACCESS          read-write
        STATUS              current
        DESCRIPTION         "This object defines the lifetime of a newly assigned
                            authorization key. DEFVAL { 604800 }"
        ::= { wmanIf2BsPkmV1ConfigEntry 1 }

    wmanIf2BsPkmV1TekLifetime OBJECT-TYPE
        SYNTAX              Integer32 (60..604800)
        UNITS               "seconds"
        MAX-ACCESS          read-write
        STATUS              current
        DESCRIPTION         "This object defines the lifetime of a newly assigned
                            Traffic Encryption Key(TEK). DEFVAL { 3600 }"
        ::= { wmanIf2BsPkmV1ConfigEntry 2 }

    wmanIf2BsPkmV1SelfSigManufCertTrust OBJECT-TYPE
        SYNTAX              INTEGER {
                                trusted( 1 ),
                                untrusted( 2 )
                            }
        MAX-ACCESS          read-write
        STATUS              current
        DESCRIPTION         "This object determines the default trust of all
                            (new) self-signed manufacturer certificates obtained
                            after setting the object."
        ::= { wmanIf2BsPkmV1ConfigEntry 3 }

    wmanIf2BsPkmV1AuthWaitTimeout OBJECT-TYPE
        SYNTAX              Integer32 (2..30)
        UNITS               "seconds"
        MAX-ACCESS          read-write
        STATUS              current
        DESCRIPTION         "This object defines the Auth Req retransmission
                            interval from Auth Wait state. DEFVAL { 10 }"
        ::= { wmanIf2BsPkmV1ConfigEntry 4 }

    wmanIf2BsPkmV1ReauthWaitTimeout OBJECT-TYPE
        SYNTAX              Integer32 (2..30)
        UNITS               "seconds"
        MAX-ACCESS          read-write
        STATUS              current
        DESCRIPTION         "This object defines the Auth Req retransmission
                            interval from Reauth Wait state. DEFVAL { 10
                            }"
        ::= { wmanIf2BsPkmV1ConfigEntry 5 }

    wmanIf2BsPkmV1AuthGraceTime OBJECT-TYPE
        SYNTAX              Integer32 (10..604800)
        UNITS               "seconds"
        MAX-ACCESS          read-write
        STATUS              current
        DESCRIPTION         "The value of this object is the grace time for
                            an authorization key. A SS is expected to start
                            trying to get a new authorization key beginning
                            AuthGraceTime seconds before the authorization
                            key actually expires. DEFVAL { 70 }"
        ::= { wmanIf2BsPkmV1ConfigEntry 6 }

    wmanIf2BsPkmV1OpWaitTimeout OBJECT-TYPE
        SYNTAX              Integer32 (1..10)
        UNITS               "seconds"
        MAX-ACCESS          read-write
        STATUS              current
        DESCRIPTION         "This object defines the Key Req retransmission
                            interval from Op Wait state. DEFVAL { 1 }"
        ::= { wmanIf2BsPkmV1ConfigEntry 7 }

    wmanIf2BsPkmV1RekeyWaitTimeout OBJECT-TYPE
        SYNTAX              Integer32 (1..10)
        UNITS               "seconds"
        MAX-ACCESS          read-write
        STATUS              current
        DESCRIPTION         "This object defines the Key Req retransmission
                            interval from Rekey Wait state. DEFVAL { 1 }"
        ::= { wmanIf2BsPkmV1ConfigEntry 8 }

    wmanIf2BsPkmV1TekGraceTime OBJECT-TYPE
        SYNTAX              Integer32 (10..3600)
        UNITS               "seconds"
        MAX-ACCESS          read-write
        STATUS              current
        DESCRIPTION         "The value of this object is the grace time for
                            the TEK in seconds. The SS is expected to start
                            trying to acquire a new TEK beginning TEK GraceTime
                            seconds before the expiration of the most recent
                            TEK. DEFVAL { 600 }"
        ::= { wmanIf2BsPkmV1ConfigEntry 9 }

    wmanIf2BsPkmV1AuthRejectWaitTimeout OBJECT-TYPE
        SYNTAX              Integer32 (10..600)
        UNITS               "seconds"
        MAX-ACCESS          read-write
        STATUS              current
        DESCRIPTION         "This object defines the Delay before resending
                            Auth Request after receiving Auth Reject. DEFVAL
                            { 60 }"
        ::= { wmanIf2BsPkmV1ConfigEntry 10 }

    wmanIf2BsPkmV1CheckCertValidityPeriods OBJECT-TYPE
        SYNTAX              TruthValue
        MAX-ACCESS          read-write
        STATUS              current
        DESCRIPTION         "Setting this object to TRUE causes all certificates
                            received thereafter to have their validity periods
                            (and their chain's validity periods) checked
                            against the current time of day. A FALSE setting
                            will cause all certificates received Thereafter
                            to not have their validity periods (nor their
                            chain's validity periods) checked against the
                            current time of day."
        ::= { wmanIf2BsPkmV1ConfigEntry 11 }

    wmanIf2BsPkmV2Objects OBJECT IDENTIFIER ::= { wmanIf2BsPkmObjects 4 }

    --
    --
    --
    wmanIf2BsPkmV2ConfigTable OBJECT-TYPE
        SYNTAX              SEQUENCE OF WmanIf2BsPkmV2ConfigEntry
        MAX-ACCESS          not-accessible
        STATUS              current
        DESCRIPTION         "This table contains the configuration of the PKM
                            attributes that are needed to PKM operation."
        ::= { wmanIf2BsPkmV2Objects 1 }

    wmanIf2BsPkmV2ConfigEntry OBJECT-TYPE
        SYNTAX              WmanIf2BsPkmV2ConfigEntry
        MAX-ACCESS          not-accessible
        STATUS              current
        DESCRIPTION         "Each entry contains objects that define the PKM
                            attributes of each BS. The table is indexed by
                            ifIndex that is associated with the BS sector."
        INDEX               {
                                ifIndex
                            }
        ::= { wmanIf2BsPkmV2ConfigTable 1 }

    WmanIf2BsPkmV2ConfigEntry ::= SEQUENCE {
        wmanIf2BsPkmPmkPrehandshakeLifetime
            Integer32,
        wmanIf2BsPkmPmkLifetime
            Integer32,
        wmanIf2BsSaChallengeTimeout
            Integer32,
        wmanIf2BsMaxSaTekChallenge
            Integer32,
        wmanIf2BsSaTekTimeout
            Integer32,
        wmanIf2BsMaxSaTekRequest
            Integer32
    }

    wmanIf2BsPkmPmkPrehandshakeLifetime OBJECT-TYPE
        SYNTAX              Integer32 (5..900)
        UNITS               "seconds"
        MAX-ACCESS          read-write
        STATUS              current
        DESCRIPTION         "This object defines the PMK or PAK prehandshake
                            lifetime. DEFVAL { 10 }"
        ::= { wmanIf2BsPkmV2ConfigEntry 1 }

    wmanIf2BsPkmPmkLifetime OBJECT-TYPE
        SYNTAX              Integer32 (60..86400)
        UNITS               "seconds"
        MAX-ACCESS          read-write
        STATUS              current
        DESCRIPTION         "This object defines PMK lifetime, if MSK lifetime
                            is unspecified (i.e., by AAA server). DEFVAL
                            { 3600 }"
        ::= { wmanIf2BsPkmV2ConfigEntry 2 }

    wmanIf2BsSaChallengeTimeout OBJECT-TYPE
        SYNTAX              Integer32 (5..20)
        UNITS               "100milliseconds"
        MAX-ACCESS          read-write
        STATUS              current
        DESCRIPTION         "This object defines the timeout value for SA-TEKChallenge
                            retransmission. DEFVAL { 10 }"
        ::= { wmanIf2BsPkmV2ConfigEntry 3 }

    wmanIf2BsMaxSaTekChallenge OBJECT-TYPE
        SYNTAX              Integer32 (1..3)
        MAX-ACCESS          read-write
        STATUS              current
        DESCRIPTION         "This object defines the maximum number of SA-TEK-Challenge
                            transmissions. DEFVAL { 3 }"
        ::= { wmanIf2BsPkmV2ConfigEntry 4 }

    wmanIf2BsSaTekTimeout OBJECT-TYPE
        SYNTAX              Integer32 (100..1000)
        UNITS               "milliseconds"
        MAX-ACCESS          read-write
        STATUS              current
        DESCRIPTION         "This object defines the timeout value for SA-TEKRequest
                            retransmission. DEFVAL { 300 }"
        ::= { wmanIf2BsPkmV2ConfigEntry 5 }

    wmanIf2BsMaxSaTekRequest OBJECT-TYPE
        SYNTAX              Integer32 (1..3)
        MAX-ACCESS          read-write
        STATUS              current
        DESCRIPTION         "This object defines the maximum number of SA-TEK-Request
                            retransmission. DEFVAL { 3 }"
        ::= { wmanIf2BsPkmV2ConfigEntry 6 }

    --
    --
    --
    --
    wmanIf2BsNotification OBJECT IDENTIFIER ::= { wmanIf2BsObjects 5 }

    wmanIf2BsTrapControl OBJECT IDENTIFIER ::= { wmanIf2BsNotification 1 }

    --
    --
    --
    wmanIf2BsThresholdConfigTable OBJECT-TYPE
        SYNTAX              SEQUENCE OF WmanIf2BsThresholdConfigEntry
        MAX-ACCESS          not-accessible
        STATUS              current
        DESCRIPTION         "This table contains threshold objects that can
                            be set to detect the threshold crossing events."
        ::= { wmanIf2BsTrapControl 3 }

    wmanIf2BsThresholdConfigEntry OBJECT-TYPE
        SYNTAX              WmanIf2BsThresholdConfigEntry
        MAX-ACCESS          not-accessible
        STATUS              current
        DESCRIPTION         "This table provides one row for each BS sector,
                            and is indexed by ifIndex."
        INDEX               {
                                ifIndex
                            }
        ::= { wmanIf2BsThresholdConfigTable 1 }

    WmanIf2BsThresholdConfigEntry ::= SEQUENCE {
        wmanIf2BsRssiLowThreshold
            Integer32,
        wmanIf2BsRssiHighThreshold
            Integer32
    }

    wmanIf2BsRssiLowThreshold OBJECT-TYPE
        SYNTAX              Integer32 (-500..-80)
        UNITS               "0.25dBm"
        MAX-ACCESS          read-write
        STATUS              current
        DESCRIPTION         "Low threshold for generating the RSSI alarm.
                             NEC modify 20080701,20081119"
        ::= { wmanIf2BsThresholdConfigEntry 1 }

    wmanIf2BsRssiHighThreshold OBJECT-TYPE
        SYNTAX              Integer32 (-500..-80)
        UNITS               "0.25dBm"
        MAX-ACCESS          read-write
        STATUS              current
        DESCRIPTION         "High threshold for clearing the RSSI alarm.
                             NEC modify 20080701,20081119"
        ::= { wmanIf2BsThresholdConfigEntry 2 }

    --
    --
    --
    wmanIf2BsPhy OBJECT IDENTIFIER ::= { wmanIf2BsObjects 6 }

    --
    --
    --
    wmanIf2BsOfdmaPhy OBJECT IDENTIFIER ::= { wmanIf2BsPhy 2 }

    wmanIf2BsOfdmaUplinkChannelTable OBJECT-TYPE
        SYNTAX              SEQUENCE OF WmanIf2BsOfdmaUplinkChannelEntry
        MAX-ACCESS          not-accessible
        STATUS              current
        DESCRIPTION         "This table contains UCD channel attributes, defining
                            the transmission characteristics of uplink channels"
        ::= { wmanIf2BsOfdmaPhy 1 }

    wmanIf2BsOfdmaUplinkChannelEntry OBJECT-TYPE
        SYNTAX              WmanIf2BsOfdmaUplinkChannelEntry
        MAX-ACCESS          not-accessible
        STATUS              current
        DESCRIPTION         "This table provides one row for each uplink channel
                            of multi-sector BS, and is indexed by BS ifIndex.
                            An entry in this table exists for each ifEntry
                            of BS with an ifType of ieee80216WMAN."
        INDEX               {
                                ifIndex
                            }
        ::= { wmanIf2BsOfdmaUplinkChannelTable 1 }

    WmanIf2BsOfdmaUplinkChannelEntry ::= SEQUENCE {
        wmanIf2BsOfdmaCtBasedResvTimeout
            Integer32,
        wmanIf2BsOfdmaUplinkCenterFreq
            Unsigned32,
        wmanIf2BsOfdmaStartOfRngCodes
            Integer32,
        wmanIf2BsOfdmaPermutationBase
            Integer32,
        wmanIf2BsOfdmaULAllocSubchBitmap
            OCTET STRING,
        wmanIf2BsOfdmaOptPermULAllocSubchBitmap
            OCTET STRING,
        wmanIf2BsOfdmaBandAMCAllocThreshold
            Integer32,
        wmanIf2BsOfdmaBandAMCReleaseThreshold
            Integer32,
        wmanIf2BsOfdmaBandAMCAllocTimer
            Integer32,
        wmanIf2BsOfdmaBandAMCReleaseTimer
            Integer32,
        wmanIf2BsOfdmaBandStatRepMAXPeriod
            Integer32,
        wmanIf2BsOfdmaBandAMCRetryTimer
            Integer32
    }

    wmanIf2BsOfdmaCtBasedResvTimeout OBJECT-TYPE
        SYNTAX              Integer32 (0..255)
        MAX-ACCESS          read-write
        STATUS              current
        DESCRIPTION         "The number of UL-MAPs to receive before contention-based
                            reservation is attempted again for the same connection."
        ::= { wmanIf2BsOfdmaUplinkChannelEntry 1 }

    wmanIf2BsOfdmaUplinkCenterFreq OBJECT-TYPE
        SYNTAX              Unsigned32 (2496000..2690000 | 3400000..3620000)
        UNITS               "kHz"
        MAX-ACCESS          read-write
        STATUS              current
        DESCRIPTION         "Uplink center frequency (kHz) DEFVAL { 3500000 }"
        ::= { wmanIf2BsOfdmaUplinkChannelEntry 4 }

    wmanIf2BsOfdmaStartOfRngCodes OBJECT-TYPE
        SYNTAX              Integer32 (0..255)
        MAX-ACCESS          read-write
        STATUS              current
        DESCRIPTION         "Indicates the starting number, S, of the group
                            of codes used for this uplink.All the ranging
                            codes used on this uplink will be between S and
                            ((S+N+M+L) mod 256). Where, N: the number of
                            initial-ranging codes M: the number of periodic-ranging
                            codes L: the number of bandwidth-request codes
                            O: the number of handover-ranging codes DEFVAL
                            { 0 }"
        ::= { wmanIf2BsOfdmaUplinkChannelEntry 10 }

    wmanIf2BsOfdmaPermutationBase OBJECT-TYPE
        SYNTAX              Integer32 (0..255)
        MAX-ACCESS          read-write
        STATUS              current
        DESCRIPTION         "Determines the UL_PermBase parameter for the subcarrier
                            permutation to be used on this uplink channel.
                            UL_PermBase = 7 LSBs of Permutation base. DEFVAL
                            { 0 }"
        ::= { wmanIf2BsOfdmaUplinkChannelEntry 11 }

    wmanIf2BsOfdmaULAllocSubchBitmap OBJECT-TYPE
        SYNTAX              OCTET STRING (SIZE(9))
        MAX-ACCESS          read-write
        STATUS              current
        DESCRIPTION         "This is a bitmap describing the physical sub-channels
                            allocated to the segment in the UL, when using
                            the uplink PUSC permutation. The LSB of the first
                            byte shall correspond to subchannel 0. For any
                            bit that is not set, the corresponding subchannel
                            shall not be used by the SS on that segment"
        ::= { wmanIf2BsOfdmaUplinkChannelEntry 12 }

    wmanIf2BsOfdmaOptPermULAllocSubchBitmap OBJECT-TYPE
        SYNTAX              OCTET STRING (SIZE(13))
        MAX-ACCESS          read-write
        STATUS              current
        DESCRIPTION         "This is a bitmap describing the sub-channels allocated
                            to the segment in the UL, when using the uplink
                            optional PUSC permutation (see 8.4.6.2.5 in IEEE
                            Std 802.16-2004). The LSB of the first byte shall
                            correspond to subchannel 0. For any bit that
                            is not set, the corresponding subchannel shall
                            not be used by the SS on that segment. When this
                            TLV is not present, BS may allocate any subchannels
                            to an SS."
        ::= { wmanIf2BsOfdmaUplinkChannelEntry 13 }

    wmanIf2BsOfdmaBandAMCAllocThreshold OBJECT-TYPE
        SYNTAX              Integer32 (0..255)
        UNITS               "dB"
        MAX-ACCESS          read-write
        STATUS              current
        DESCRIPTION         "Threshold of the maximum of the standard deviations
                            of the individual bands CINR measurements over
                            time to trigger mode transition from normal subchannel
                            to Band AMC"
        ::= { wmanIf2BsOfdmaUplinkChannelEntry 14 }

    wmanIf2BsOfdmaBandAMCReleaseThreshold OBJECT-TYPE
        SYNTAX              Integer32 (0..255)
        UNITS               "dB"
        MAX-ACCESS          read-write
        STATUS              current
        DESCRIPTION         "Threshold of the maximum of the standard deviations
                            of the individual bands CINR measurements over
                            time to trigger mode transition from Band AMC
                            to normal subchannel"
        ::= { wmanIf2BsOfdmaUplinkChannelEntry 15 }

    wmanIf2BsOfdmaBandAMCAllocTimer OBJECT-TYPE
        SYNTAX              Integer32 (0..255)
        UNITS               "Frame"
        MAX-ACCESS          read-write
        STATUS              current
        DESCRIPTION         "Minimum required number of frames to measure the
                            average and standard deviation for the event
                            of Band AMC triggering"
        ::= { wmanIf2BsOfdmaUplinkChannelEntry 16 }

    wmanIf2BsOfdmaBandAMCReleaseTimer OBJECT-TYPE
        SYNTAX              Integer32 (0..255)
        UNITS               "Frame"
        MAX-ACCESS          read-write
        STATUS              current
        DESCRIPTION         "Minimum required number of frames to measure the
                            average and standard deviation for the event
                            triggering from Band AMC to normal subchannel"
        ::= { wmanIf2BsOfdmaUplinkChannelEntry 17 }

    wmanIf2BsOfdmaBandStatRepMAXPeriod OBJECT-TYPE
        SYNTAX              Integer32 (0..255)
        UNITS               "Frame"
        MAX-ACCESS          read-write
        STATUS              current
        DESCRIPTION         "Maximum period between refreshing the Band CINR
                            measurement by the unsolicited REP-RSP"
        ::= { wmanIf2BsOfdmaUplinkChannelEntry 18 }

    wmanIf2BsOfdmaBandAMCRetryTimer OBJECT-TYPE
        SYNTAX              Integer32 (0..255)
        UNITS               "Frame"
        MAX-ACCESS          read-write
        STATUS              current
        DESCRIPTION         "Backoff timer between consecutive mode transitions
                            from normal subchannel to Band AMC when the previous
                            request is failed"
        ::= { wmanIf2BsOfdmaUplinkChannelEntry 19 }

    wmanIf2BsOfdmaDownlinkChannelTable OBJECT-TYPE
        SYNTAX              SEQUENCE OF WmanIf2BsOfdmaDownlinkChannelEntry
        MAX-ACCESS          not-accessible
        STATUS              current
        DESCRIPTION         "This table contains DCD channel attributes, defining
                            the transmission characteristics of downlink
                            channels"
        ::= { wmanIf2BsOfdmaPhy 2 }

    wmanIf2BsOfdmaDownlinkChannelEntry OBJECT-TYPE
        SYNTAX              WmanIf2BsOfdmaDownlinkChannelEntry
        MAX-ACCESS          not-accessible
        STATUS              current
        DESCRIPTION         "This table provides one row for each downlink
                            channel of multi-sector BS, and is indexed by
                            BS ifIndex. An entry in this table exists for
                            each ifEntry of BS with an ifType of ieee80216WMAN."
        INDEX               {
                                ifIndex
                            }
        ::= { wmanIf2BsOfdmaDownlinkChannelTable 1 }

    WmanIf2BsOfdmaDownlinkChannelEntry ::= SEQUENCE {
        wmanIf2BsOfdmaBsEIRP
            Integer32,
        wmanIf2BsOfdmaChannelNumber
            WmanIf2ChannelNumber,
        wmanIf2BsOfdmaTTG
            Integer32,
        wmanIf2BsOfdmaRTG
            Integer32,
        wmanIf2BsOfdmaInitRngMaxRSS
            Integer32,
        wmanIf2BsOfdmaDownlinkCenterFreq
            Unsigned32,
        wmanIf2BsOfdmaBsId
            WmanIf2BsIdType,
        wmanIf2BsOfdmaMacVersion
            WmanIf2MacVersion,
        wmanIf2BsOfdmaFrameDurationCode
            INTEGER
    }

    wmanIf2BsOfdmaBsEIRP OBJECT-TYPE
        SYNTAX              Integer32 (-32768..32767)
        UNITS               "dBm"
        MAX-ACCESS          read-write
        STATUS              current
        DESCRIPTION         "The EIRP is the equivalent isotropic radiated
                            power of the base station, which is computed
                            for a simple single-antenna transmitter."
        ::= { wmanIf2BsOfdmaDownlinkChannelEntry 1 }

    wmanIf2BsOfdmaChannelNumber OBJECT-TYPE
        SYNTAX              WmanIf2ChannelNumber
        MAX-ACCESS          read-write
        STATUS              current
        DESCRIPTION         "Downlink channel number as defined in 8.5. Used
                            for license-exempt operation only."
        ::= { wmanIf2BsOfdmaDownlinkChannelEntry 2 }

    wmanIf2BsOfdmaTTG OBJECT-TYPE
        SYNTAX              Integer32 (0..65535)
        UNITS               "PS"
        MAX-ACCESS          read-write
        STATUS              current
        DESCRIPTION         "Transmit / Receive Transition Gap. Used on TDD
                            system only."
        ::= { wmanIf2BsOfdmaDownlinkChannelEntry 3 }

    wmanIf2BsOfdmaRTG OBJECT-TYPE
        SYNTAX              Integer32 (0..255)
        UNITS               "PS"
        MAX-ACCESS          read-write
        STATUS              current
        DESCRIPTION         "Receive / Transmit Transition Gap. Used on TDD
                            system only."
        ::= { wmanIf2BsOfdmaDownlinkChannelEntry 4 }

    wmanIf2BsOfdmaInitRngMaxRSS OBJECT-TYPE
        SYNTAX              Integer32 (-128..127)
        UNITS               "dBm"
        MAX-ACCESS          read-write
        STATUS              current
        DESCRIPTION         "Initial Ranging Max. equivalent isotropic received
                            power at BS Signed in units of 1 dBm."
        ::= { wmanIf2BsOfdmaDownlinkChannelEntry 5 }

    wmanIf2BsOfdmaDownlinkCenterFreq OBJECT-TYPE
        SYNTAX              Unsigned32 (2496000..2690000 | 3400000..3620000)
        UNITS               "kHz"
        MAX-ACCESS          read-write
        STATUS              current
        DESCRIPTION         "Downlink center frequency (kHz). DEFVAL {3500000}"
        ::= { wmanIf2BsOfdmaDownlinkChannelEntry 6 }

    wmanIf2BsOfdmaBsId OBJECT-TYPE
        SYNTAX              WmanIf2BsIdType
        MAX-ACCESS          read-only
        STATUS              current
        DESCRIPTION         "Base station ID. Changed by NEC to R/O"
        ::= { wmanIf2BsOfdmaDownlinkChannelEntry 7 }

    wmanIf2BsOfdmaMacVersion OBJECT-TYPE
        SYNTAX              WmanIf2MacVersion
        MAX-ACCESS          read-only
        STATUS              current
        DESCRIPTION         "This parameter specifies the version of 802.16
                            to which the message originator conforms."
        ::= { wmanIf2BsOfdmaDownlinkChannelEntry 8 }

    wmanIf2BsOfdmaFrameDurationCode OBJECT-TYPE
        SYNTAX              INTEGER {
                                aASGap( 0 ),
                                duration2ms( 1 ),
                                duration2dot5ms( 2 ),
                                duration4ms( 3 ),
                                duration5ms( 4 ),
                                duration8ms( 5 ),
                                duration10ms( 6 ),
                                duration12dot5ms( 7 ),
                                duration20ms( 8 )
                            }
        MAX-ACCESS          read-write
        STATUS              current
        DESCRIPTION         "The duration of the frame. The frame duration
                            code values are specified in Table 274."
        ::= { wmanIf2BsOfdmaDownlinkChannelEntry 9 }

    wmanIf2BsOfdmaUcdBurstProfileTable OBJECT-TYPE
        SYNTAX              SEQUENCE OF WmanIf2BsOfdmaUcdBurstProfileEntry
        MAX-ACCESS          not-accessible
        STATUS              current
        DESCRIPTION         "This table contains UCD burst profiles for each
                            uplink channel"
        ::= { wmanIf2BsOfdmaPhy 3 }

    wmanIf2BsOfdmaUcdBurstProfileEntry OBJECT-TYPE
        SYNTAX              WmanIf2BsOfdmaUcdBurstProfileEntry
        MAX-ACCESS          not-accessible
        STATUS              current
        DESCRIPTION         "This table provides one row for each UCD burst
                            profile. This table is double indexed. The primary
                            index is an ifIndex with an ifType of ieee80216WMAN.
                            The secondary index is wmanIf2BsOfdmaUiucIndex."
        INDEX               {
                                ifIndex,
                                wmanIf2BsOfdmaUiucIndex
                            }
        ::= { wmanIf2BsOfdmaUcdBurstProfileTable 1 }

    WmanIf2BsOfdmaUcdBurstProfileEntry ::= SEQUENCE {
        wmanIf2BsOfdmaUiucIndex
            Integer32,
        wmanIf2BsOfdmaUcdFecCodeType
            WmanIf2OfdmaUcdFecCode,
        wmanIf2BsOfdmaRangingDataRatio
            Integer32,
        wmanIf2BsOfdmaUcdBurstProfileRowStatus
            RowStatus
    }

    wmanIf2BsOfdmaUiucIndex OBJECT-TYPE
        SYNTAX              Integer32 (1..10)
        MAX-ACCESS          not-accessible
        STATUS              current
        DESCRIPTION         "The Uplink Interval Usage Code indicates the uplink
                            burst profile in the UCD message, and is used
                            along with ifIndex to identify an entry in the
                            wmanIf2BsOfdmaUcdBurstProfileTable."
        ::= { wmanIf2BsOfdmaUcdBurstProfileEntry 1 }

    wmanIf2BsOfdmaUcdFecCodeType OBJECT-TYPE
        SYNTAX              WmanIf2OfdmaUcdFecCode
        MAX-ACCESS          read-create
        STATUS              current
        DESCRIPTION         "Uplink FEC code type and modulation type"
        ::= { wmanIf2BsOfdmaUcdBurstProfileEntry 2 }

    wmanIf2BsOfdmaRangingDataRatio OBJECT-TYPE
        SYNTAX              Integer32 (-128..127)
        UNITS               "dB"
        MAX-ACCESS          read-create
        STATUS              current
        DESCRIPTION         "Reducing factor in units of 1 dB, between the
                            power used for this burst and power should be
                            used for CDMA Ranging."
        ::= { wmanIf2BsOfdmaUcdBurstProfileEntry 3 }

    wmanIf2BsOfdmaUcdBurstProfileRowStatus OBJECT-TYPE
        SYNTAX              RowStatus
        MAX-ACCESS          read-create
        STATUS              current
        DESCRIPTION         "This object is used to create a new row or modify
                            or delete an existing row in this table. If the
                            implementator of this MIB has choosen not to
                            implement 'dynamic assignment' of profiles, this
                            object is not useful and should return noSuchName
                            upon SNMP request."
        ::= { wmanIf2BsOfdmaUcdBurstProfileEntry 5 }

    wmanIf2BsOfdmaDcdBurstProfileTable OBJECT-TYPE
        SYNTAX              SEQUENCE OF WmanIf2BsOfdmaDcdBurstProfileEntry
        MAX-ACCESS          not-accessible
        STATUS              current
        DESCRIPTION         "This table provides one row for each DCD burst
                            profile. This table is double indexed. The primary
                            index is an ifIndex with an ifType of ieee80216WMAN.
                            The secondary index is wmanIf2BsOfdmaDiucIndex."
        ::= { wmanIf2BsOfdmaPhy 4 }

    wmanIf2BsOfdmaDcdBurstProfileEntry OBJECT-TYPE
        SYNTAX              WmanIf2BsOfdmaDcdBurstProfileEntry
        MAX-ACCESS          not-accessible
        STATUS              current
        DESCRIPTION         "This table provides one row for each DCD burst
                            profile. This table is double indexed. The primary
                            index is an ifIndex with an ifType of ieee80216WMAN.
                            The secondary index is wmanIf2BsOfdmaDiucIndex."
        INDEX               {
                                ifIndex,
                                wmanIf2BsOfdmaDiucIndex
                            }
        ::= { wmanIf2BsOfdmaDcdBurstProfileTable 1 }

    WmanIf2BsOfdmaDcdBurstProfileEntry ::= SEQUENCE {
        wmanIf2BsOfdmaDiucIndex
            Integer32,
        wmanIf2BsOfdmaDownlinkFrequency
            Unsigned32,
        wmanIf2BsOfdmaDcdFecCodeType
            WmanIf2OfdmaDcdFecCode,
        wmanIf2BsOfdmaDcdBurstProfileRowStatus
            RowStatus
    }

    wmanIf2BsOfdmaDiucIndex OBJECT-TYPE
        SYNTAX              Integer32 (0..12)
        MAX-ACCESS          not-accessible
        STATUS              current
        DESCRIPTION         "The Downlink Interval Usage Code indicates the
                            downlink burst profile in the DCD message, and
                            is used along with ifIndex to identify an entry
                            in the wmanIf2BsOfdmaDcdBurstProfileTable."
        ::= { wmanIf2BsOfdmaDcdBurstProfileEntry 1 }

    wmanIf2BsOfdmaDownlinkFrequency OBJECT-TYPE
        SYNTAX              Unsigned32
        UNITS               "kHz"
        MAX-ACCESS          read-create
        STATUS              current
        DESCRIPTION         "Downlink Frequency (kHz)."
        ::= { wmanIf2BsOfdmaDcdBurstProfileEntry 2 }

    wmanIf2BsOfdmaDcdFecCodeType OBJECT-TYPE
        SYNTAX              WmanIf2OfdmaDcdFecCode
        MAX-ACCESS          read-create
        STATUS              current
        DESCRIPTION         "Downlink FEC code type and modulation type"
        ::= { wmanIf2BsOfdmaDcdBurstProfileEntry 3 }

    wmanIf2BsOfdmaDcdBurstProfileRowStatus OBJECT-TYPE
        SYNTAX              RowStatus
        MAX-ACCESS          read-create
        STATUS              current
        DESCRIPTION         "This object is used to create a new row or modify
                            or delete an existing row in this table. If the
                            implementator of this MIB has choosen not to
                            implement 'dynamic assignment' of profiles, this
                            object is not useful and should return noSuchName
                            upon SNMP request."
        ::= { wmanIf2BsOfdmaDcdBurstProfileEntry 6 }

    wmanIf2BsOfdmaCapabilitiesTable OBJECT-TYPE
        SYNTAX              SEQUENCE OF WmanIf2BsOfdmaCapabilitiesEntry
        MAX-ACCESS          not-accessible
        STATUS              current
        DESCRIPTION         "This table contains the basic capabilities, specific
                            to OFDMA Phy, of the BS as implemented in BS
                            hardware and software. These capabilities along
                            with the configuration for them (wmanIf2BsOfdmaCapabilitiesConfigTable)
                            are used for negotiation of basic capabilities
                            with SS using RNG-RSP, SBC-RSP and REG-RSP messages.
                            The negotiated capabilities are obtained by interSubclause
                            of MS raw reported capabilities, BS raw capabilities
                            and BS configured capabilities. The objects in
                            the table have read-only access. The table is
                            maintained by BS."
        ::= { wmanIf2BsOfdmaPhy 7 }

    wmanIf2BsOfdmaCapabilitiesEntry OBJECT-TYPE
        SYNTAX              WmanIf2BsOfdmaCapabilitiesEntry
        MAX-ACCESS          not-accessible
        STATUS              current
        DESCRIPTION         "This table provides one row for each BS sector
                            and is indexed by ifIndex."
        INDEX               {
                                ifIndex
                            }
        ::= { wmanIf2BsOfdmaCapabilitiesTable 1 }

    WmanIf2BsOfdmaCapabilitiesEntry ::= SEQUENCE {
        wmanIf2BsOfdmaCapFftSizes
            WmanIf2OfdmaFftSizes,
        wmanIf2BsOfdmaCapDemodulator
            WmanIf2OfdmaMsDeModType,
        wmanIf2BsOfdmaCapModulator
            WmanIf2OfdmaMsModType,
        wmanIf2BsOfdmaCapNoHarqChannel
            Unsigned32,
        wmanIf2BsOfdmaCapPermutation
            WmanIf2OfdmaPermutation,
        wmanIf2BsSsOfdmaCapDemMimo
            WmanIf2OfdmaDemMimo,
        wmanIf2BsSsOfdmaCapMimoCapability
            WmanIf2OfdmaMimoCap,
        wmanIf2BsSsOfdmaCapUlMimo
            WmanIf2OfdmaUlMimo,
        wmanIf2BsSsOfdmaCapPrivateMap
            WmanIf2OfdmaPrivMap,
        wmanIf2BsSsOfdmaCapAasCapability
            WmanIf2OfdmaAasCap,
        wmanIf2BsSsOfdmaCapCinrMeasurement
            WmanIf2OfdmaCinrCap,
        wmanIf2BsSsOfdmaCapUlPowerControl
            WmanIf2OfdmaUlPower,
        wmanIf2BsSsOfdmaCapMapCapability
            WmanIf2OfdmaMapCap,
        wmanIf2BsSsOfdmaCapUlControlChannel
            WmanIf2OfdmaUlCntlCh,
        wmanIf2BsSsOfdmaCapCistCapability
            WmanIf2OfdmaMsCistCap,
        wmanIf2BsSsOfdmaCapMaxHarqBurst
            WmanIf2OfdmaMaxHarq,
        wmanIf2BsSsOfdmaCapModMimo
            WmanIf2OfdmaModMimo,
        wmanIf2BsSsOfdmaCapSdmaPilot
            WmanIf2SdmaPilotCap,
        wmanIf2BsSsOfdmaCapMultipleBurst
            WmanIf2MultiBurst,
        wmanIf2BsSsOfdmaCapIncrHarqBuffer
            WmanIf2IncrHarqBuf,
        wmanIf2BsSsOfdmaCapChaseHarqBuffer
            WmanIf2ChaseHarqBuf
    }

    wmanIf2BsOfdmaCapFftSizes OBJECT-TYPE
        SYNTAX              WmanIf2OfdmaFftSizes
        MAX-ACCESS          read-only
        STATUS              current
        DESCRIPTION         "This field indicates the FFT sizes supported by
                            BS."
        ::= { wmanIf2BsOfdmaCapabilitiesEntry 1 }

    wmanIf2BsOfdmaCapDemodulator OBJECT-TYPE
        SYNTAX              WmanIf2OfdmaMsDeModType
        MAX-ACCESS          read-only
        STATUS              current
        DESCRIPTION         "This field indicates the different demodulator
                            options supported by BS."
        ::= { wmanIf2BsOfdmaCapabilitiesEntry 2 }

    wmanIf2BsOfdmaCapModulator OBJECT-TYPE
        SYNTAX              WmanIf2OfdmaMsModType
        MAX-ACCESS          read-only
        STATUS              current
        DESCRIPTION         "This field indicates the different modulator options
                            supported by BS."
        ::= { wmanIf2BsOfdmaCapabilitiesEntry 3 }

    wmanIf2BsOfdmaCapNoHarqChannel OBJECT-TYPE
        SYNTAX              Unsigned32
        MAX-ACCESS          read-only
        STATUS              current
        DESCRIPTION         "This field specifies the number of uplink H-ARQ
                            channels (n) the SS supports, where n = 1..16.
                            The value of this object should be 0..15."
        ::= { wmanIf2BsOfdmaCapabilitiesEntry 4 }

    wmanIf2BsOfdmaCapPermutation OBJECT-TYPE
        SYNTAX              WmanIf2OfdmaPermutation
        MAX-ACCESS          read-only
        STATUS              current
        DESCRIPTION         "This field indicates the OFDMA MS Permutation
                            support supported by BS."
        ::= { wmanIf2BsOfdmaCapabilitiesEntry 5 }

    wmanIf2BsSsOfdmaCapDemMimo OBJECT-TYPE
        SYNTAX              WmanIf2OfdmaDemMimo
        MAX-ACCESS          read-only
        STATUS              current
        DESCRIPTION         "This field indicates the different MIMO options
                            supported by a WirelessMAN-OFDMA PHY SS in the
                            downlink."
        ::= { wmanIf2BsOfdmaCapabilitiesEntry 6 }

    wmanIf2BsSsOfdmaCapMimoCapability OBJECT-TYPE
        SYNTAX              WmanIf2OfdmaMimoCap
        MAX-ACCESS          read-only
        STATUS              current
        DESCRIPTION         "This field indicates the MIMO capability of OFDMA
                            MS demodulator."
        ::= { wmanIf2BsOfdmaCapabilitiesEntry 7 }

    wmanIf2BsSsOfdmaCapUlMimo OBJECT-TYPE
        SYNTAX              WmanIf2OfdmaUlMimo
        MAX-ACCESS          read-only
        STATUS              current
        DESCRIPTION         "This field indicates different MIMO options supported
                            by a OFDMA PHY SS in the uplink"
        ::= { wmanIf2BsOfdmaCapabilitiesEntry 8 }

    wmanIf2BsSsOfdmaCapPrivateMap OBJECT-TYPE
        SYNTAX              WmanIf2OfdmaPrivMap
        MAX-ACCESS          read-only
        STATUS              current
        DESCRIPTION         "This field indicates AAS private map parameters
                            supported by a OFDMA SS"
        ::= { wmanIf2BsOfdmaCapabilitiesEntry 9 }

    wmanIf2BsSsOfdmaCapAasCapability OBJECT-TYPE
        SYNTAX              WmanIf2OfdmaAasCap
        MAX-ACCESS          read-only
        STATUS              current
        DESCRIPTION         "This field indicates different AAS options supported
                            by a OFDMA PHY SS in the downlink"
        ::= { wmanIf2BsOfdmaCapabilitiesEntry 10 }

    wmanIf2BsSsOfdmaCapCinrMeasurement OBJECT-TYPE
        SYNTAX              WmanIf2OfdmaCinrCap
        MAX-ACCESS          read-only
        STATUS              current
        DESCRIPTION         "This field indicates the CINR measurement capability
                            supported by a OFDMA PHY SS in the downlink."
        ::= { wmanIf2BsOfdmaCapabilitiesEntry 11 }

    wmanIf2BsSsOfdmaCapUlPowerControl OBJECT-TYPE
        SYNTAX              WmanIf2OfdmaUlPower
        MAX-ACCESS          read-only
        STATUS              current
        DESCRIPTION         "This field indicates the power control options
                            supported by a OFDMA PHY SS for uplink transmission."
        ::= { wmanIf2BsOfdmaCapabilitiesEntry 12 }

    wmanIf2BsSsOfdmaCapMapCapability OBJECT-TYPE
        SYNTAX              WmanIf2OfdmaMapCap
        MAX-ACCESS          read-only
        STATUS              current
        DESCRIPTION         "This field indicates the different MAP options
                            supported by a OFDMA PHY SS"
        ::= { wmanIf2BsOfdmaCapabilitiesEntry 13 }

    wmanIf2BsSsOfdmaCapUlControlChannel OBJECT-TYPE
        SYNTAX              WmanIf2OfdmaUlCntlCh
        MAX-ACCESS          read-only
        STATUS              current
        DESCRIPTION         "This field indicates the different uplink control
                            channels supported by a OFDMA PHY SS."
        ::= { wmanIf2BsOfdmaCapabilitiesEntry 14 }

    wmanIf2BsSsOfdmaCapCistCapability OBJECT-TYPE
        SYNTAX              WmanIf2OfdmaMsCistCap
        MAX-ACCESS          read-only
        STATUS              current
        DESCRIPTION         "This field indicates the MS capability of supporting
                            CSIT (uplink sounding)."
        ::= { wmanIf2BsOfdmaCapabilitiesEntry 15 }

    wmanIf2BsSsOfdmaCapMaxHarqBurst OBJECT-TYPE
        SYNTAX              WmanIf2OfdmaMaxHarq
        MAX-ACCESS          read-only
        STATUS              current
        DESCRIPTION         "This field indicates the maximum number of UL/DL
                            HARQ burst allocations for the SS in a single
                            UL/DL subframe."
        ::= { wmanIf2BsOfdmaCapabilitiesEntry 16 }

    wmanIf2BsSsOfdmaCapModMimo OBJECT-TYPE
        SYNTAX              WmanIf2OfdmaModMimo
        MAX-ACCESS          read-only
        STATUS              current
        DESCRIPTION         "This field indicates the MIMO capability of OFDMA
                            SS modulator."
        ::= { wmanIf2BsOfdmaCapabilitiesEntry 17 }

    wmanIf2BsSsOfdmaCapSdmaPilot OBJECT-TYPE
        SYNTAX              WmanIf2SdmaPilotCap
        MAX-ACCESS          read-only
        STATUS              current
        DESCRIPTION         "This field indicates the SDMA pilot pattern support
                            for AMC zone."
        ::= { wmanIf2BsOfdmaCapabilitiesEntry 18 }

    wmanIf2BsSsOfdmaCapMultipleBurst OBJECT-TYPE
        SYNTAX              WmanIf2MultiBurst
        MAX-ACCESS          read-only
        STATUS              current
        DESCRIPTION         "This field indicates whether multiple FEC types
                            are supported in DL/UL burst profiles."
        ::= { wmanIf2BsOfdmaCapabilitiesEntry 19 }

    wmanIf2BsSsOfdmaCapIncrHarqBuffer OBJECT-TYPE
        SYNTAX              WmanIf2IncrHarqBuf
        MAX-ACCESS          read-only
        STATUS              current
        DESCRIPTION         "This field indicates the maximal number of data
                            bits the SS is able to use for buffering for
                            NEP/NSCH based incremental redundancy CTC in
                            downlink and uplink transmissions."
        ::= { wmanIf2BsOfdmaCapabilitiesEntry 20 }

    wmanIf2BsSsOfdmaCapChaseHarqBuffer OBJECT-TYPE
        SYNTAX              WmanIf2ChaseHarqBuf
        MAX-ACCESS          read-only
        STATUS              current
        DESCRIPTION         "This field indicates the maximal number of data
                            bits the SS is able to use for buffering for
                            DIUC/duration based HARQ methods (Chase combining
                            and CC-IR)in downlink and uplink transmissions."
        ::= { wmanIf2BsOfdmaCapabilitiesEntry 21 }

    wmanIf2BsOfdmaCapabilitiesConfigTable OBJECT-TYPE
        SYNTAX              SEQUENCE OF WmanIf2BsOfdmaCapabilitiesConfigEntry
        MAX-ACCESS          not-accessible
        STATUS              current
        DESCRIPTION         "This table contains the configuration for basic
                            capabilities of BS, specific to OFDMA Phy. The
                            table is intended to be used to restrict the
                            Capabilities implemented by BS, for example in
                            order to comply with local regulatory requirements.
                            The BS should use the configuration along with
                            the implemented Capabilities (wmanIf2BsOfdmaPhyTable)
                            for negotiation of basic capabilities with SS
                            using RNG-RSP, SBC-RSP and REG-RSP messages.
                            The negotiated capabilities are obtained by interSubclause
                            of MS reported capabilities, BS raw capabilities
                            and BS configured capabilities. The objects in
                            the table have read-write access. The rows are
                            created by BS as a copy of wmanIf2BsBasicCapabilitiesTable
                            and can be modified by NMS."
        ::= { wmanIf2BsOfdmaPhy 8 }

    wmanIf2BsOfdmaCapabilitiesConfigEntry OBJECT-TYPE
        SYNTAX              WmanIf2BsOfdmaCapabilitiesConfigEntry
        MAX-ACCESS          not-accessible
        STATUS              current
        DESCRIPTION         "This table provides one row for each BS sector
                            and is indexed by ifIndex."
        INDEX               {
                                ifIndex
                            }
        ::= { wmanIf2BsOfdmaCapabilitiesConfigTable 1 }

    WmanIf2BsOfdmaCapabilitiesConfigEntry ::= SEQUENCE {
        wmanIf2BsOfdmaCapCfgFftSizes
            WmanIf2OfdmaFftSizes,
        wmanIf2BsOfdmaCapCfgDemodulator
            WmanIf2OfdmaMsDeModType,
        wmanIf2BsOfdmaCapCfgModulator
            WmanIf2OfdmaMsModType,
        wmanIf2BsOfdmaCapCfgNoHarqChannel
            Unsigned32,
        wmanIf2BsOfdmaCapCfgPermutation
            WmanIf2OfdmaPermutation,
        wmanIf2BsSsOfdmaCapCfgDemMimo
            WmanIf2OfdmaDemMimo,
        wmanIf2BsSsOfdmaCapCfgMimoCapability
            WmanIf2OfdmaMimoCap,
        wmanIf2BsSsOfdmaCapCfgUlMimo
            WmanIf2OfdmaUlMimo,
        wmanIf2BsSsOfdmaCapCfgPrivateMap
            WmanIf2OfdmaPrivMap,
        wmanIf2BsSsOfdmaCapCfgAasCapability
            WmanIf2OfdmaAasCap,
        wmanIf2BsSsOfdmaCapCfgCinrMeasurement
            WmanIf2OfdmaCinrCap,
        wmanIf2BsSsOfdmaCapCfgUlPowerControl
            WmanIf2OfdmaUlPower,
        wmanIf2BsSsOfdmaCapCfgMapCapability
            WmanIf2OfdmaMapCap,
        wmanIf2BsSsOfdmaCapCfgUlControlChannel
            WmanIf2OfdmaUlCntlCh,
        wmanIf2BsSsOfdmaCapCfgCistCapability
            WmanIf2OfdmaMsCistCap,
        wmanIf2BsSsOfdmaCapCfgMaxHarqBurst
            WmanIf2OfdmaMaxHarq,
        wmanIf2BsSsOfdmaCapCfgModMimo
            WmanIf2OfdmaModMimo,
        wmanIf2BsSsOfdmaCapCfgSdmaPilot
            WmanIf2SdmaPilotCap,
        wmanIf2BsSsOfdmaCapCfgMultipleBurst
            WmanIf2MultiBurst,
        wmanIf2BsSsOfdmaCapCfgIncrHarqBuffer
            WmanIf2IncrHarqBuf,
        wmanIf2BsSsOfdmaCapCfgChaseHarqBuffer
            WmanIf2ChaseHarqBuf
    }

    wmanIf2BsOfdmaCapCfgFftSizes OBJECT-TYPE
        SYNTAX              WmanIf2OfdmaFftSizes
        MAX-ACCESS          read-write
        STATUS              current
        DESCRIPTION         "This field indicates the FFT sizes configured
                            for the BS."
        ::= { wmanIf2BsOfdmaCapabilitiesConfigEntry 1 }

    wmanIf2BsOfdmaCapCfgDemodulator OBJECT-TYPE
        SYNTAX              WmanIf2OfdmaMsDeModType
        MAX-ACCESS          read-write
        STATUS              current
        DESCRIPTION         "This field indicates the different demodulator
                            options configured for the BS."
        ::= { wmanIf2BsOfdmaCapabilitiesConfigEntry 2 }

    wmanIf2BsOfdmaCapCfgModulator OBJECT-TYPE
        SYNTAX              WmanIf2OfdmaMsModType
        MAX-ACCESS          read-write
        STATUS              current
        DESCRIPTION         "This field indicates the different modulator options
                            configured for the BS."
        ::= { wmanIf2BsOfdmaCapabilitiesConfigEntry 3 }

    wmanIf2BsOfdmaCapCfgNoHarqChannel OBJECT-TYPE
        SYNTAX              Unsigned32
        MAX-ACCESS          read-only
        STATUS              current
        DESCRIPTION         "This field specifies the number of uplink H-ARQ
                            channels (n) the SS supports, where n = 1..16.
                            The value of this object should be 0..15."
        ::= { wmanIf2BsOfdmaCapabilitiesConfigEntry 4 }

    wmanIf2BsOfdmaCapCfgPermutation OBJECT-TYPE
        SYNTAX              WmanIf2OfdmaPermutation
        MAX-ACCESS          read-write
        STATUS              current
        DESCRIPTION         "This field indicates the OFDMA MS Permutation
                            support configured for the BS."
        ::= { wmanIf2BsOfdmaCapabilitiesConfigEntry 5 }

    wmanIf2BsSsOfdmaCapCfgDemMimo OBJECT-TYPE
        SYNTAX              WmanIf2OfdmaDemMimo
        MAX-ACCESS          read-write
        STATUS              current
        DESCRIPTION         "This field indicates the different MIMO options
                            supported by a WirelessMAN-OFDMA PHY SS in the
                            downlink."
        ::= { wmanIf2BsOfdmaCapabilitiesConfigEntry 6 }

    wmanIf2BsSsOfdmaCapCfgMimoCapability OBJECT-TYPE
        SYNTAX              WmanIf2OfdmaMimoCap
        MAX-ACCESS          read-write
        STATUS              current
        DESCRIPTION         "This field indicates the MIMO capability of OFDMA
                            MS demodulator."
        ::= { wmanIf2BsOfdmaCapabilitiesConfigEntry 7 }

    wmanIf2BsSsOfdmaCapCfgUlMimo OBJECT-TYPE
        SYNTAX              WmanIf2OfdmaUlMimo
        MAX-ACCESS          read-write
        STATUS              current
        DESCRIPTION         "This field indicates different MIMO options supported
                            by a OFDMA PHY SS in the uplink"
        ::= { wmanIf2BsOfdmaCapabilitiesConfigEntry 8 }

    wmanIf2BsSsOfdmaCapCfgPrivateMap OBJECT-TYPE
        SYNTAX              WmanIf2OfdmaPrivMap
        MAX-ACCESS          read-write
        STATUS              current
        DESCRIPTION         "This field indicates AAS private map parameters
                            supported by a OFDMA SS"
        ::= { wmanIf2BsOfdmaCapabilitiesConfigEntry 9 }

    wmanIf2BsSsOfdmaCapCfgAasCapability OBJECT-TYPE
        SYNTAX              WmanIf2OfdmaAasCap
        MAX-ACCESS          read-write
        STATUS              current
        DESCRIPTION         "This field indicates different AAS options supported
                            by a OFDMA PHY SS in the downlink"
        ::= { wmanIf2BsOfdmaCapabilitiesConfigEntry 10 }

    wmanIf2BsSsOfdmaCapCfgCinrMeasurement OBJECT-TYPE
        SYNTAX              WmanIf2OfdmaCinrCap
        MAX-ACCESS          read-write
        STATUS              current
        DESCRIPTION         "This field indicates the CINR measurement capability
                            supported by a OFDMA PHY SS in the downlink."
        ::= { wmanIf2BsOfdmaCapabilitiesConfigEntry 11 }

    wmanIf2BsSsOfdmaCapCfgUlPowerControl OBJECT-TYPE
        SYNTAX              WmanIf2OfdmaUlPower
        MAX-ACCESS          read-write
        STATUS              current
        DESCRIPTION         "This field indicates the power control options
                            supported by a OFDMA PHY SS for uplink transmission."
        ::= { wmanIf2BsOfdmaCapabilitiesConfigEntry 12 }

    wmanIf2BsSsOfdmaCapCfgMapCapability OBJECT-TYPE
        SYNTAX              WmanIf2OfdmaMapCap
        MAX-ACCESS          read-write
        STATUS              current
        DESCRIPTION         "This field indicates the different MAP options
                            supported by a OFDMA PHY SS"
        ::= { wmanIf2BsOfdmaCapabilitiesConfigEntry 13 }

    wmanIf2BsSsOfdmaCapCfgUlControlChannel OBJECT-TYPE
        SYNTAX              WmanIf2OfdmaUlCntlCh
        MAX-ACCESS          read-write
        STATUS              current
        DESCRIPTION         "This field indicates the different uplink control
                            channels supported by a OFDMA PHY SS."
        ::= { wmanIf2BsOfdmaCapabilitiesConfigEntry 14 }

    wmanIf2BsSsOfdmaCapCfgCistCapability OBJECT-TYPE
        SYNTAX              WmanIf2OfdmaMsCistCap
        MAX-ACCESS          read-write
        STATUS              current
        DESCRIPTION         "This field indicates the MS capability of supporting
                            CSIT (uplink sounding)."
        ::= { wmanIf2BsOfdmaCapabilitiesConfigEntry 15 }

    wmanIf2BsSsOfdmaCapCfgMaxHarqBurst OBJECT-TYPE
        SYNTAX              WmanIf2OfdmaMaxHarq
        MAX-ACCESS          read-write
        STATUS              current
        DESCRIPTION         "This field indicates the maximum number of UL/DL
                            HARQ burst allocations for the SS in a single
                            UL/DL subframe."
        ::= { wmanIf2BsOfdmaCapabilitiesConfigEntry 16 }

    wmanIf2BsSsOfdmaCapCfgModMimo OBJECT-TYPE
        SYNTAX              WmanIf2OfdmaModMimo
        MAX-ACCESS          read-write
        STATUS              current
        DESCRIPTION         "This field indicates the MIMO capability of OFDMA
                            SS modulator."
        ::= { wmanIf2BsOfdmaCapabilitiesConfigEntry 17 }

    wmanIf2BsSsOfdmaCapCfgSdmaPilot OBJECT-TYPE
        SYNTAX              WmanIf2SdmaPilotCap
        MAX-ACCESS          read-write
        STATUS              current
        DESCRIPTION         "This field indicates the SDMA pilot pattern support
                            for AMC zone."
        ::= { wmanIf2BsOfdmaCapabilitiesConfigEntry 18 }

    wmanIf2BsSsOfdmaCapCfgMultipleBurst OBJECT-TYPE
        SYNTAX              WmanIf2MultiBurst
        MAX-ACCESS          read-write
        STATUS              current
        DESCRIPTION         "This field indicates whether multiple FEC types
                            are supported in DL/UL burst profiles."
        ::= { wmanIf2BsOfdmaCapabilitiesConfigEntry 19 }

    wmanIf2BsSsOfdmaCapCfgIncrHarqBuffer OBJECT-TYPE
        SYNTAX              WmanIf2IncrHarqBuf
        MAX-ACCESS          read-write
        STATUS              current
        DESCRIPTION         "This field indicates the maximal number of data
                            bits the SS is able to use for buffering for
                            NEP/NSCH based incremental redundancy CTC in
                            downlink and uplink transmissions."
        ::= { wmanIf2BsOfdmaCapabilitiesConfigEntry 20 }

    wmanIf2BsSsOfdmaCapCfgChaseHarqBuffer OBJECT-TYPE
        SYNTAX              WmanIf2ChaseHarqBuf
        MAX-ACCESS          read-write
        STATUS              current
        DESCRIPTION         "This field indicates the maximal number of data
                            bits the SS is able to use for buffering for
                            DIUC/duration based HARQ methods (Chase combining
                            and CC-IR)in downlink and uplink transmissions."
        ::= { wmanIf2BsOfdmaCapabilitiesConfigEntry 21 }

    wmanIf2BsOfdmaExUplinkChannelTable OBJECT-TYPE
        SYNTAX              SEQUENCE OF WmanIf2BsOfdmaExUplinkChannelEntry
        MAX-ACCESS          not-accessible
        STATUS              current
        DESCRIPTION         "This table contains UCD channel attributes, defining
                            the transmission characteristics of uplink channels"
        ::= { wmanIf2BsOfdmaPhy 9 }

    wmanIf2BsOfdmaExUplinkChannelEntry OBJECT-TYPE
        SYNTAX              WmanIf2BsOfdmaExUplinkChannelEntry
        MAX-ACCESS          not-accessible
        STATUS              current
        DESCRIPTION         "This table provides one row for each uplink channel
                            of multi-sector BS, and is indexed by BS ifIndex.
                            An entry in this table exists for each ifEntry
                            of BS with an ifType of ieee80216WMAN."
        AUGMENTS            {
                                wmanIf2BsOfdmaUplinkChannelEntry
                            }
        ::= { wmanIf2BsOfdmaExUplinkChannelTable 1 }

    WmanIf2BsOfdmaExUplinkChannelEntry ::= SEQUENCE {
        wmanIf2BsOfdmaExHandoverRangingStart
            Integer32,
        wmanIf2BsOfdmaExHandoverRangingEnd
            Integer32,
        wmanIf2BsOfdmaExHARQAckDelayDLBurst
            WmanIf2HarqAckDelay,
        wmanIf2BsOfdmaExUlAmcAlloPhyBandsBitmap
            OCTET STRING,
        wmanIf2BsOfdmaExMaxRetransmission
            Integer32,
        wmanIf2BsOfdmaExNormalizedCnOverride
            OCTET STRING,
        wmanIf2BsOfdmaExSizeOfCqichId
            Integer32,
        wmanIf2BsOfdmaExNormalizedCnValue
            Integer32,
        wmanIf2BsOfdmaExNormalizedCnOverride2
            OCTET STRING,
        wmanIf2BsOfdmaExBandAmcEntryAvgCinr
            Integer32,
        wmanIf2BsOfdmaExAasPreambleUpperBond
            Integer32,
        wmanIf2BsOfdmaExAasPreambleLowerBond
            Integer32,
        wmanIf2BsOfdmaExAasBeamSelectAllowed
            WmanIf2AasBeamSel,
        wmanIf2BsOfdmaExCqichIndicationFlag
            OCTET STRING,
        wmanIf2BsOfdmaExUpPowerAdjStep
            Unsigned32,
        wmanIf2BsOfdmaExDownPowerAdjStep
            Unsigned32,
        wmanIf2BsOfdmaExMinPowerOffsetAdj
            Integer32,
        wmanIf2BsOfdmaExMaxPowerOffsetAdj
            Integer32,
        wmanIf2BsOfdmaExHandoverRngCodes
            Integer32,
        wmanIf2BsOfdmaExInitialRngInterval
            Integer32,
        wmanIf2BsOfdmaExTxPwrRepThreshold
            Integer32,
        wmanIf2BsOfdmaExTprPower
            Integer32,
        wmanIf2BsOfdmaExAlphaPavg
            Integer32,
        wmanIf2BsOfdmaExCqichTxPwrRepThreshold
            Integer32,
        wmanIf2BsOfdmaExCqichTprPower
            Integer32,
        wmanIf2BsOfdmaExCqichAlphaPavg
            Integer32,
        wmanIf2BsOfdmaExNormalizedCnChSounding
            Integer32,
        wmanIf2BsOfdmaExInitialRngBackoffStart
            Integer32,
        wmanIf2BsOfdmaExInitialRngBackoffEnd
            Integer32,
        wmanIf2BsOfdmaExBwRequestBackoffStart
            Integer32,
        wmanIf2BsOfdmaExBwRequestBackoffEnd
            Integer32
    }

    wmanIf2BsOfdmaExHandoverRangingStart OBJECT-TYPE
        SYNTAX              Integer32 (0..15)
        MAX-ACCESS          read-write
        STATUS              current
        DESCRIPTION         "Initial backoff window size for MS performing
                            initial ranging during handover process, expressed
                            as a power of 2."
        ::= { wmanIf2BsOfdmaExUplinkChannelEntry 1 }

    wmanIf2BsOfdmaExHandoverRangingEnd OBJECT-TYPE
        SYNTAX              Integer32 (0..15)
        MAX-ACCESS          read-write
        STATUS              current
        DESCRIPTION         "Final backoff window size for MS performing initial
                            ranging during handover process, expressed as
                            a power of 2."
        ::= { wmanIf2BsOfdmaExUplinkChannelEntry 2 }

    wmanIf2BsOfdmaExHARQAckDelayDLBurst OBJECT-TYPE
        SYNTAX              WmanIf2HarqAckDelay
        MAX-ACCESS          read-write
        STATUS              current
        DESCRIPTION         "This object defines the OFDMA H-ARQ ACK delay
                            for DL burst."
        ::= { wmanIf2BsOfdmaExUplinkChannelEntry 3 }

    wmanIf2BsOfdmaExUlAmcAlloPhyBandsBitmap OBJECT-TYPE
        SYNTAX              OCTET STRING (SIZE(6))
        MAX-ACCESS          read-write
        STATUS              current
        DESCRIPTION         "A bitmap describing the physical bands allocated
                            to the segment in the UL, when using the optional
                            AMC permutation with regular MAPs (see 8.4.6.3).
                            The LSB of the first byte shall correspond to
                            the physical band 0. For any bit that is not
                            set, the corresponding physical bands shall not
                            be used by the SS on that segment. When this
                            TLV is not present, BS may allocate any physical
                            bands to an SS."
        ::= { wmanIf2BsOfdmaExUplinkChannelEntry 4 }

    wmanIf2BsOfdmaExMaxRetransmission OBJECT-TYPE
        SYNTAX              Integer32 (0..255)
        MAX-ACCESS          read-write
        STATUS              current
        DESCRIPTION         "Maximum number of retransmission in UL HARQ. DEFVAL
                            { 4 }"
        ::= { wmanIf2BsOfdmaExUplinkChannelEntry 5 }

    wmanIf2BsOfdmaExNormalizedCnOverride OBJECT-TYPE
        SYNTAX              OCTET STRING (SIZE(8))
        MAX-ACCESS          read-write
        STATUS              current
        DESCRIPTION         "This is a list of numbers, where each number is
                            encoded by one nibble, and interpreted as a signed
                            integer. The nibbles correspond in order to the
                            list define by Table 334, starting from the second
                            line, such that the LS nibble of the first byte
                            corresponds to the second line in the table.
                            The number encoded by each nibble represents
                            the difference in normalized C/N relative to
                            the previous line in the table."
        ::= { wmanIf2BsOfdmaExUplinkChannelEntry 6 }

    wmanIf2BsOfdmaExSizeOfCqichId OBJECT-TYPE
        SYNTAX              Integer32 (0..7)
        MAX-ACCESS          read-write
        STATUS              current
        DESCRIPTION         "Size of CQICH ID field. 0 = 0 bits 1 = 3 bits
                            2 = 4 bits 3 = 5 bits 4 = 6 bits 5 = 7 bits 6
                            = 8 bits 7 = 9 bits DEFVAL { 0 }"
        ::= { wmanIf2BsOfdmaExUplinkChannelEntry 7 }

    wmanIf2BsOfdmaExNormalizedCnValue OBJECT-TYPE
        SYNTAX              Integer32 (-128..128)
        UNITS               "dB"
        MAX-ACCESS          read-write
        STATUS              current
        DESCRIPTION         "It shall be interpreted as signed integer in dB.
                            It corresponds to the normalized C/N value in
                            the first line (counting except for header cell
                            of table)"
        ::= { wmanIf2BsOfdmaExUplinkChannelEntry 8 }

    wmanIf2BsOfdmaExNormalizedCnOverride2 OBJECT-TYPE
        SYNTAX              OCTET STRING (SIZE(8))
        MAX-ACCESS          read-write
        STATUS              current
        DESCRIPTION         "SIZE changed for NEC WIMAX BS from 7 to 8. This
                            is a list of numbers, where each number is encoded
                            by one nibble, and interpreted as a signed integer.
                            The nibbles correspond in order to the list define
                            by Table 334, starting from the second line (counting
                            except for the header cell of table), such that
                            the LS nibble of the first byte corresponds to
                            the second line in the table. The number encoded
                            by each nibble represents the difference in normalized
                            C/N relative to the previous line in the table."
        ::= { wmanIf2BsOfdmaExUplinkChannelEntry 9 }

    wmanIf2BsOfdmaExBandAmcEntryAvgCinr OBJECT-TYPE
        SYNTAX              Integer32 (-128..128)
        UNITS               "dB"
        MAX-ACCESS          read-write
        STATUS              current
        DESCRIPTION         "Threshold of the average CINR of the whole bandwidth
                            to trigger mode transition from normal subchannel
                            to AMC"
        ::= { wmanIf2BsOfdmaExUplinkChannelEntry 10 }

    wmanIf2BsOfdmaExAasPreambleUpperBond OBJECT-TYPE
        SYNTAX              Integer32 (-128..128)
        UNITS               "0.25 dB"
        MAX-ACCESS          read-write
        STATUS              current
        DESCRIPTION         "Upper bound of AAS preamble."
        ::= { wmanIf2BsOfdmaExUplinkChannelEntry 11 }

    wmanIf2BsOfdmaExAasPreambleLowerBond OBJECT-TYPE
        SYNTAX              Integer32 (-128..128)
        UNITS               "0.25 dB"
        MAX-ACCESS          read-write
        STATUS              current
        DESCRIPTION         "Lower bound of AAS preamble."
        ::= { wmanIf2BsOfdmaExUplinkChannelEntry 12 }

    wmanIf2BsOfdmaExAasBeamSelectAllowed OBJECT-TYPE
        SYNTAX              WmanIf2AasBeamSel
        UNITS               "0.25 dB"
        MAX-ACCESS          read-write
        STATUS              current
        DESCRIPTION         "Indicate whether unsolicited AAS Beam Select messages
                            (see 6.3.2.3.41 in IEEE 802.16e-2005) should
                            be sent by the MS. DEFVAL { allowed }"
        ::= { wmanIf2BsOfdmaExUplinkChannelEntry 13 }

    wmanIf2BsOfdmaExCqichIndicationFlag OBJECT-TYPE
        SYNTAX              OCTET STRING (SIZE(1))
        MAX-ACCESS          read-write
        STATUS              current
        DESCRIPTION         "The N MSB values of this field represents the
                            N-bit payload value on the Fast-Feedback channel
                            reserved as indication flag for MS to initiate
                            feedback on the Feedback header, where N is the
                            number of payload bits used for S/N measurement
                            feedback on the Fast-Feedback channel. The value
                            shall not be set to all zeros."
        ::= { wmanIf2BsOfdmaExUplinkChannelEntry 14 }

    wmanIf2BsOfdmaExUpPowerAdjStep OBJECT-TYPE
        SYNTAX              Unsigned32
        UNITS               "0.01 dB"
        MAX-ACCESS          read-write
        STATUS              current
        DESCRIPTION         "MS-specific up power offset adjustment step"
        ::= { wmanIf2BsOfdmaExUplinkChannelEntry 15 }

    wmanIf2BsOfdmaExDownPowerAdjStep OBJECT-TYPE
        SYNTAX              Unsigned32
        UNITS               "0.01 dB"
        MAX-ACCESS          read-write
        STATUS              current
        DESCRIPTION         "MS-specific down power offset adjustment step"
        ::= { wmanIf2BsOfdmaExUplinkChannelEntry 16 }

    wmanIf2BsOfdmaExMinPowerOffsetAdj OBJECT-TYPE
        SYNTAX              Integer32
        UNITS               "0.1 dB"
        MAX-ACCESS          read-write
        STATUS              current
        DESCRIPTION         "Minimum level of power offset adjustment"
        ::= { wmanIf2BsOfdmaExUplinkChannelEntry 17 }

    wmanIf2BsOfdmaExMaxPowerOffsetAdj OBJECT-TYPE
        SYNTAX              Integer32
        UNITS               "0.1 dB"
        MAX-ACCESS          read-write
        STATUS              current
        DESCRIPTION         "Maximum level of power offset adjustment"
        ::= { wmanIf2BsOfdmaExUplinkChannelEntry 18 }

    wmanIf2BsOfdmaExHandoverRngCodes OBJECT-TYPE
        SYNTAX              Integer32 (0..255)
        MAX-ACCESS          read-write
        STATUS              current
        DESCRIPTION         "Number of handover ranging CDMA codes"
        ::= { wmanIf2BsOfdmaExUplinkChannelEntry 19 }

    wmanIf2BsOfdmaExInitialRngInterval OBJECT-TYPE
        SYNTAX              Integer32
        MAX-ACCESS          read-write
        STATUS              current
        DESCRIPTION         "Number of frames between initial ranging interval
                            allocation."
        ::= { wmanIf2BsOfdmaExUplinkChannelEntry 20 }

    wmanIf2BsOfdmaExTxPwrRepThreshold OBJECT-TYPE
        SYNTAX              Integer32 (0..15)
        UNITS               "dB"
        MAX-ACCESS          read-write
        STATUS              current
        DESCRIPTION         "Tx power report threshold. wmanIf2BsOfdmaExTxPwrRepThreshold
                            = 0b1111 means infinite"
        ::= { wmanIf2BsOfdmaExUplinkChannelEntry 21 }

    wmanIf2BsOfdmaExTprPower OBJECT-TYPE
        SYNTAX              Integer32 (0..15)
        UNITS               "dB"
        MAX-ACCESS          read-write
        STATUS              current
        DESCRIPTION         "Tx power report interval = 2 ^ wmanIf2BsOfdmaExTprPower.
                            The unit of Tx power report interval is frame.
                            wmanIf2BsOfdmaExTprPower = 0b1111 means infinite."
        ::= { wmanIf2BsOfdmaExUplinkChannelEntry 22 }

    wmanIf2BsOfdmaExAlphaPavg OBJECT-TYPE
        SYNTAX              Integer32 (0..15)
        UNITS               "dB"
        MAX-ACCESS          read-write
        STATUS              current
        DESCRIPTION         "Aplha p_avg parameter as shown in equation 138d
                            in IEEE 802.16e-2005 indicates the multiple of
                            1/16. For example '0' means 1/16, 15 means 16/16."
        ::= { wmanIf2BsOfdmaExUplinkChannelEntry 23 }

    wmanIf2BsOfdmaExCqichTxPwrRepThreshold OBJECT-TYPE
        SYNTAX              Integer32 (0..15)
        UNITS               "dB"
        MAX-ACCESS          read-write
        STATUS              current
        DESCRIPTION         "Tx power report threshold. wmanIf2BsOfdmaExTxPwrRepThreshold
                            = 0b1111 means infinite. It shall be used when
                            CQICH is allocated to the SS."
        ::= { wmanIf2BsOfdmaExUplinkChannelEntry 24 }

    wmanIf2BsOfdmaExCqichTprPower OBJECT-TYPE
        SYNTAX              Integer32 (0..15)
        UNITS               "dB"
        MAX-ACCESS          read-write
        STATUS              current
        DESCRIPTION         "Tx power report interval = 2 ^ wmanIf2BsOfdmaExTprPower.
                            The unit of Tx power report interval is frame.
                            wmanIf2BsOfdmaExTprPower = 0b1111 means infinite.
                            It shall be used when CQICH is allocated to the
                            SS."
        ::= { wmanIf2BsOfdmaExUplinkChannelEntry 25 }

    wmanIf2BsOfdmaExCqichAlphaPavg OBJECT-TYPE
        SYNTAX              Integer32 (0..15)
        UNITS               "dB"
        MAX-ACCESS          read-write
        STATUS              current
        DESCRIPTION         "Aplha p_avg parameter as shown in equation 138d
                            in IEEE 802.16e-2005 indicates the multiple of
                            1/16. For example '0' means 1/16, 15 means 16/16.
                            It shall be used when CQICH is allocated to the
                            SS."
        ::= { wmanIf2BsOfdmaExUplinkChannelEntry 26 }

    wmanIf2BsOfdmaExNormalizedCnChSounding OBJECT-TYPE
        SYNTAX              Integer32
        MAX-ACCESS          read-write
        STATUS              current
        DESCRIPTION         "Signed integer for the required C/N (dB) for Channel
                            Sounding."
        ::= { wmanIf2BsOfdmaExUplinkChannelEntry 27 }

    wmanIf2BsOfdmaExInitialRngBackoffStart OBJECT-TYPE
        SYNTAX              Integer32 (0..15)
        MAX-ACCESS          read-write
        STATUS              current
        DESCRIPTION         "Initial backoff window size for initial ranging
                            contention, expressed as a power of 2."
        ::= { wmanIf2BsOfdmaExUplinkChannelEntry 28 }

    wmanIf2BsOfdmaExInitialRngBackoffEnd OBJECT-TYPE
        SYNTAX              Integer32 (0..15)
        MAX-ACCESS          read-write
        STATUS              current
        DESCRIPTION         "Final backoff window size for initial ranging
                            contention, expressed as a power of 2."
        ::= { wmanIf2BsOfdmaExUplinkChannelEntry 29 }

    wmanIf2BsOfdmaExBwRequestBackoffStart OBJECT-TYPE
        SYNTAX              Integer32 (0..15)
        MAX-ACCESS          read-write
        STATUS              current
        DESCRIPTION         "Initial backoff window size for contention BW
                            requests, expressed as a power of 2."
        ::= { wmanIf2BsOfdmaExUplinkChannelEntry 30 }

    wmanIf2BsOfdmaExBwRequestBackoffEnd OBJECT-TYPE
        SYNTAX              Integer32 (0..15)
        MAX-ACCESS          read-write
        STATUS              current
        DESCRIPTION         "Final backoff window size for contention BW requests,
                            expressed as a power of 2."
        ::= { wmanIf2BsOfdmaExUplinkChannelEntry 31 }

    wmanIf2BsOfdmaExDownlinkChannelTable OBJECT-TYPE
        SYNTAX              SEQUENCE OF WmanIf2BsOfdmaExDownlinkChannelEntry
        MAX-ACCESS          not-accessible
        STATUS              current
        DESCRIPTION         "This table contains DCD channel attributes, defining
                            the transmission characteristics of uplink channels"
        ::= { wmanIf2BsOfdmaPhy 10 }

    wmanIf2BsOfdmaExDownlinkChannelEntry OBJECT-TYPE
        SYNTAX              WmanIf2BsOfdmaExDownlinkChannelEntry
        MAX-ACCESS          not-accessible
        STATUS              current
        DESCRIPTION         "This table provides one row for each downlink
                            channel of multi-sector BS, and is indexed by
                            BS ifIndex. An entry in this table exists for
                            each ifEntry of BS with an ifType of ieee80216WMAN."
        AUGMENTS            {
                                wmanIf2BsOfdmaDownlinkChannelEntry
                            }
        ::= { wmanIf2BsOfdmaExDownlinkChannelTable 1 }

    WmanIf2BsOfdmaExDownlinkChannelEntry ::= SEQUENCE {
        wmanIf2BsOfdmaExHARQAckDelayULBurst
            WmanIf2HarqAckDelay,
        wmanIf2BsOfdmaExHarqZonePermutation
            WmanIfPermutationType,
        wmanIf2BsOfdmaExHMaxRetransmission
            Integer32,
        wmanIf2BsOfdmaExCinrAlphaAvg
            Integer32,
        wmanIf2BsOfdmaExRssiAlphaAvg
            Integer32,
        wmanIf2BsOfdmaExDlAmcAlloPhyBandsBitmap
            OCTET STRING,
        wmanIf2BsOfdmaExHandoverSupported
            WmanIf2HoSupportType,
        wmanIf2BsOfdmaExThresholdAddBsDivSet
            Integer32,
        wmanIf2BsOfdmaExThresholdDelBsDivSet
            Integer32,
        wmanIf2BsOfdmaExAsrSlotLength
            Integer32,
        wmanIf2BsOfdmaExAsrSwitchingPeriod
            Integer32,
        wmanIf2BsOfdmaExHysteresisMargin
            Integer32,
        wmanIf2BsOfdmaExTimeToTrigger
            Integer32,
        wmanIf2BsOfdmaExRestartCount
            Integer32
    }

    wmanIf2BsOfdmaExHARQAckDelayULBurst OBJECT-TYPE
        SYNTAX              WmanIf2HarqAckDelay
        MAX-ACCESS          read-write
        STATUS              current
        DESCRIPTION         "This object defines the OFDMA H-ARQ ACK delay
                            for UL burst."
        ::= { wmanIf2BsOfdmaExDownlinkChannelEntry 1 }

    wmanIf2BsOfdmaExHarqZonePermutation OBJECT-TYPE
        SYNTAX              WmanIfPermutationType
        MAX-ACCESS          read-write
        STATUS              current
        DESCRIPTION         "Permutation type for broadcast region in HARQ
                            zone"
        ::= { wmanIf2BsOfdmaExDownlinkChannelEntry 2 }

    wmanIf2BsOfdmaExHMaxRetransmission OBJECT-TYPE
        SYNTAX              Integer32 (0..255)
        MAX-ACCESS          read-write
        STATUS              current
        DESCRIPTION         "Maximum number of retransmission in DL HARQ. DEFVAL
                            { 4 }"
        ::= { wmanIf2BsOfdmaExDownlinkChannelEntry 3 }

    wmanIf2BsOfdmaExCinrAlphaAvg OBJECT-TYPE
        SYNTAX              Integer32 (0..15)
        MAX-ACCESS          read-write
        STATUS              current
        DESCRIPTION         "Bit 0..3 of Default RSSI and CINR averaging parameter
                            TLV. Default averaging parameter Alpha Avg for
                            physical CINR measurements, in multiples of 1/16.
                            For example '0' means 1/16, 15 means 16/16. DEFVAL
                            { 3 }"
        ::= { wmanIf2BsOfdmaExDownlinkChannelEntry 4 }

    wmanIf2BsOfdmaExRssiAlphaAvg OBJECT-TYPE
        SYNTAX              Integer32 (0..15)
        MAX-ACCESS          read-write
        STATUS              current
        DESCRIPTION         "Bit 0..3 of Default RSSI and CINR averaging parameter
                            TLV. Default averaging parameter Alpha Avg for
                            physical RSSI measurements, in multiples of 1/16.
                            For example '0' means 1/16, 15 means 16/16. DEFVAL
                            { 3 }"
        ::= { wmanIf2BsOfdmaExDownlinkChannelEntry 5 }

    wmanIf2BsOfdmaExDlAmcAlloPhyBandsBitmap OBJECT-TYPE
        SYNTAX              OCTET STRING (SIZE(6))
        MAX-ACCESS          read-write
        STATUS              current
        DESCRIPTION         "A bitmap describing the physical bands allocated
                            to the segment in the DL, when allocating AMC
                            subchannels through the HARQ MAP, or through
                            the Normal MAP, or for Band-AMC CINR reports,
                            or using the optional AMC permutation (see 8.4.6.3).
                            The LSB of the first byte shall correspond to
                            band 0. For any bit that is not set, the corresponding
                            band shall not be used by the SS on that segment.
                            When this TLV is not present, BS may allocate
                            any physical bands to an SS."
        ::= { wmanIf2BsOfdmaExDownlinkChannelEntry 6 }

    wmanIf2BsOfdmaExHandoverSupported OBJECT-TYPE
        SYNTAX              WmanIf2HoSupportType
        MAX-ACCESS          read-write
        STATUS              current
        DESCRIPTION         "Indicates the types of handover supported. Bit
                            #0 = HO Bit #1 = MDHO Bit #2 = FBSS HO."
        ::= { wmanIf2BsOfdmaExDownlinkChannelEntry 7 }

    wmanIf2BsOfdmaExThresholdAddBsDivSet OBJECT-TYPE
        SYNTAX              Integer32 (0..255)
        UNITS               "dB"
        MAX-ACCESS          read-write
        STATUS              current
        DESCRIPTION         "Threshold used by the MS to add a neighbor BS
                            to the diversity set. When the CINR of a neighbor
                            BS is higher than H_Add_Threshold, the MS should
                            send MOB_MSHO-REQ to request adding this neighbor
                            BS to the diversity set. This threshold is used
                            for the MS that is performing MDHO/FBSS HO. If
                            the BS does not support FBSS HO/MDHO, this value
                            is not set."
        ::= { wmanIf2BsOfdmaExDownlinkChannelEntry 8 }

    wmanIf2BsOfdmaExThresholdDelBsDivSet OBJECT-TYPE
        SYNTAX              Integer32 (0..255)
        UNITS               "dB"
        MAX-ACCESS          read-write
        STATUS              current
        DESCRIPTION         "Threshold used by the MS to delete a neighbor
                            BS to the diversity set. When the CINR of a neighbor
                            BS is lower than H_Add_Threshold, the MS should
                            send MOB_MSHO-REQ to request dropping this neighbor
                            BS to the diversity set. This threshold is used
                            for the MS that is performing MDHO/FBSS HO. If
                            the BS does not support FBSS HO/MDHO, this value
                            is not set."
        ::= { wmanIf2BsOfdmaExDownlinkChannelEntry 9 }

    wmanIf2BsOfdmaExAsrSlotLength OBJECT-TYPE
        SYNTAX              Integer32 (0..15)
        UNITS               "Frames"
        MAX-ACCESS          read-write
        STATUS              current
        DESCRIPTION         "Bit 0..3 of ASR Slot Length and Switching Period.
                            For FBSS operation, the time axis is slotted
                            by an ASR (Anchor Switch Reporting) slot that
                            is wmanIf2BsOfdmaExAsrSlotLength frame long."
        ::= { wmanIf2BsOfdmaExDownlinkChannelEntry 10 }

    wmanIf2BsOfdmaExAsrSwitchingPeriod OBJECT-TYPE
        SYNTAX              Integer32 (0..15)
        UNITS               "ASR slots"
        MAX-ACCESS          read-write
        STATUS              current
        DESCRIPTION         "Bit 0..3 of ASR Slot Length and Switching Period.
                            A switching period is introduced whose duration
                            is equals to wmanIf2BsOfdmaExAsrSwitchingPeriod
                            ASR slots that should be long enough such that
                            certain process (e.g., HARQ transmission, backhaul
                            context transfer) can be completed at the current
                            anchor BS before the MS switches to the new anchor
                            BS."
        ::= { wmanIf2BsOfdmaExDownlinkChannelEntry 11 }

    wmanIf2BsOfdmaExHysteresisMargin OBJECT-TYPE
        SYNTAX              Integer32 (0..57)
        UNITS               "dB"
        MAX-ACCESS          read-write
        STATUS              current
        DESCRIPTION         "When the CINR of a neighbor BS is larger than
                            the sum of the CINR of the current serving BS
                            and wmanIf2BsOfdmaExHysteresisMargin for the
                            time-to-trigger duration, then the neighbor BS
                            is included in the list of possible target BSs
                            in MOB_MSHO-REQ."
        ::= { wmanIf2BsOfdmaExDownlinkChannelEntry 12 }

    wmanIf2BsOfdmaExTimeToTrigger OBJECT-TYPE
        SYNTAX              Integer32
        UNITS               "milliseconds"
        MAX-ACCESS          read-write
        STATUS              current
        DESCRIPTION         "Indicates the time duration for MS decides to
                            select a neighbor BS as a possible target BS.
                            It is applicable only for HHO."
        ::= { wmanIf2BsOfdmaExDownlinkChannelEntry 13 }

    wmanIf2BsOfdmaExRestartCount OBJECT-TYPE
        SYNTAX              Integer32 (0..255)
        MAX-ACCESS          read-only
        STATUS              current
        DESCRIPTION         "The value is incremented by one whenever BS restarts
                            (see 6.3.9.11). The value rolls over from 0 to
                            255."
        ::= { wmanIf2BsOfdmaExDownlinkChannelEntry 14 }

    wmanIf2CommonObjects OBJECT IDENTIFIER ::= { wmanIf2MibObjects 3 }

    --
    --
    --
    --
    wmanIf2CmnCps OBJECT IDENTIFIER ::= { wmanIf2CommonObjects 2 }

    wmanIf2CmnCpsServiceFlowTable OBJECT-TYPE
        SYNTAX              SEQUENCE OF WmanIf2CmnCpsServiceFlowEntry
        MAX-ACCESS          not-accessible
        STATUS              current
        DESCRIPTION         "This table contains Service Flow managed objects
                            that are common in BS and SS."
        ::= { wmanIf2CmnCps 1 }

    wmanIf2CmnCpsServiceFlowEntry OBJECT-TYPE
        SYNTAX              WmanIf2CmnCpsServiceFlowEntry
        MAX-ACCESS          not-accessible
        STATUS              current
        DESCRIPTION         "This table provides one row for each created service
                            flow for a given MacAddress, and is indexed by
                            ifIndex, wmanIf2CmnCpsCpsSfMacAddress, and wmanIf2CmnCpsSfId.
                            IfIndex is associated with the BS sector."
        INDEX               {
                                ifIndex,
                                wmanIf2CmnCpsSfMacAddress,
                                wmanIf2CmnCpsSfId
                            }
        ::= { wmanIf2CmnCpsServiceFlowTable 1 }

    WmanIf2CmnCpsServiceFlowEntry ::= SEQUENCE {
        wmanIf2CmnCpsSfMacAddress
            MacAddress,
        wmanIf2CmnCpsSfId
            Unsigned32,
        wmanIf2CmnCpsSfCid
            WmanIf2CidType,
        wmanIf2CmnCpsSfDirection
            INTEGER,
        wmanIf2CmnCpsSfState
            WmanIf2SfState,
        wmanIf2CmnCpsTrafficPriority
            Integer32,
        wmanIf2CmnCpsMaxSustainedRate
            Unsigned32,
        wmanIf2CmnCpsMaxTrafficBurst
            Unsigned32,
        wmanIf2CmnCpsMinReservedRate
            Unsigned32,
        wmanIf2CmnCpsToleratedJitter
            Unsigned32,
        wmanIf2CmnCpsMaxLatency
            Unsigned32,
        wmanIf2CmnCpsFixedVsVariableSduInd
            INTEGER,
        wmanIf2CmnCpsSduSize
            Unsigned32,
        wmanIf2CmnCpsSfSchedulingType
            WmanIf2SfSchedulingType,
        wmanIf2CmnCpsArqEnable
            TruthValue,
        wmanIf2CmnCpsArqWindowSize
            Integer32,
        wmanIf2CmnCpsArqBlockLifetime
            Integer32,
        wmanIf2CmnCpsArqSyncLossTimeout
            Integer32,
        wmanIf2CmnCpsArqDeliverInOrder
            TruthValue,
        wmanIf2CmnCpsArqRxPurgeTimeout
            Integer32,
        wmanIf2CmnCpsArqBlockSize
            Integer32,
        wmanIf2CmnCpsMinRsvdTolerableRate
            Unsigned32,
        wmanIf2CmnCpsReqTxPolicy
            BITS,
        wmanIf2CmnSfCsSpecification
            WmanIf2CsSpecification,
        wmanIf2CmnCpsTargetSaid
            Integer32
    }

    wmanIf2CmnCpsSfMacAddress OBJECT-TYPE
        SYNTAX              MacAddress
        MAX-ACCESS          not-accessible
        STATUS              current
        DESCRIPTION         "When this table is implemented on the basestation,
                            this object contains the SS Mac address, the
                            reported service flow was created for. On the
                            SS, the value returned is the SS's own Mac address."
        ::= { wmanIf2CmnCpsServiceFlowEntry 1 }

    wmanIf2CmnCpsSfId OBJECT-TYPE
        SYNTAX              Unsigned32 (1..4294967295)
        MAX-ACCESS          read-only
        STATUS              current
        DESCRIPTION         "A 32 bit quantity that uniquely identifies a service
                            flow to both the subscriber station and base
                            station (BS)."
        ::= { wmanIf2CmnCpsServiceFlowEntry 2 }

    wmanIf2CmnCpsSfCid OBJECT-TYPE
        SYNTAX              WmanIf2CidType
        MAX-ACCESS          read-only
        STATUS              current
        DESCRIPTION         "A 16 bit channel identifier to identify the connection
                            being created by DSA."
        ::= { wmanIf2CmnCpsServiceFlowEntry 3 }

    wmanIf2CmnCpsSfDirection OBJECT-TYPE
        SYNTAX              INTEGER {
                                downstream( 1 ),
                                upstream( 2 )
                            }
        MAX-ACCESS          read-only
        STATUS              current
        DESCRIPTION         "An attribute indicating the service flow is downstream
                            or upstream."
        ::= { wmanIf2CmnCpsServiceFlowEntry 4 }

    wmanIf2CmnCpsSfState OBJECT-TYPE
        SYNTAX              WmanIf2SfState
        MAX-ACCESS          read-only
        STATUS              current
        DESCRIPTION         "wmanIf2CmnCpsSfState indicates the service flow
                            state: Authorized (1), Admitted (2), and Active
                            (3) service flow state."
        ::= { wmanIf2CmnCpsServiceFlowEntry 5 }

    wmanIf2CmnCpsTrafficPriority OBJECT-TYPE
        SYNTAX              Integer32 (0..7)
        MAX-ACCESS          read-only
        STATUS              current
        DESCRIPTION         "The value of this parameter specifies the priority
                            assigned to a service flow. For uplink service
                            flows, the BS should use this parameter when
                            determining precedence in request service and
                            grant generation, and the SS shall preferentially
                            select contention Request opportunities for Priority
                            Request CIDs based on this priority"
        ::= { wmanIf2CmnCpsServiceFlowEntry 6 }

    wmanIf2CmnCpsMaxSustainedRate OBJECT-TYPE
        SYNTAX              Unsigned32
        UNITS               "b/s"
        MAX-ACCESS          read-only
        STATUS              current
        DESCRIPTION         "This parameter defines the peak information rate
                            of the service. The rate is expressed in bits
                            per second and pertains to the SDUs at the input
                            to the system."
        ::= { wmanIf2CmnCpsServiceFlowEntry 7 }

    wmanIf2CmnCpsMaxTrafficBurst OBJECT-TYPE
        SYNTAX              Unsigned32
        UNITS               "byte"
        MAX-ACCESS          read-only
        STATUS              current
        DESCRIPTION         "This parameter defines the maximum burst size
                            that must be accommodated for the service."
        ::= { wmanIf2CmnCpsServiceFlowEntry 8 }

    wmanIf2CmnCpsMinReservedRate OBJECT-TYPE
        SYNTAX              Unsigned32
        UNITS               "byte"
        MAX-ACCESS          read-only
        STATUS              current
        DESCRIPTION         "This parameter specifies the minimum rate reserved
                            for this service flow."
        ::= { wmanIf2CmnCpsServiceFlowEntry 9 }

    wmanIf2CmnCpsToleratedJitter OBJECT-TYPE
        SYNTAX              Unsigned32
        UNITS               "millisecond"
        MAX-ACCESS          read-only
        STATUS              current
        DESCRIPTION         "This parameter defines the Maximum delay variation
                            (jitter) for the connection."
        ::= { wmanIf2CmnCpsServiceFlowEntry 10 }

    wmanIf2CmnCpsMaxLatency OBJECT-TYPE
        SYNTAX              Unsigned32
        UNITS               "millisecond"
        MAX-ACCESS          read-only
        STATUS              current
        DESCRIPTION         "The value of this parameter specifies the maximum
                            latency between the reception of a packet by
                            the BS or SS on its network interface and the
                            forwarding of the packet to its RF Interface."
        ::= { wmanIf2CmnCpsServiceFlowEntry 11 }

    wmanIf2CmnCpsFixedVsVariableSduInd OBJECT-TYPE
        SYNTAX              INTEGER {
                                variableLength( 0 ),
                                fixedLength( 1 )
                            }
        MAX-ACCESS          read-only
        STATUS              current
        DESCRIPTION         "The value of this parameter specifies whether
                            the SDUs on the service flow are variable-length
                            (0) or fixed-length (1). The parameter is used
                            only if packing is on for the service flow. The
                            default value is 0, i.e.,variable-length SDUs.
                            DEFVAL { variableLength }"
        ::= { wmanIf2CmnCpsServiceFlowEntry 12 }

    wmanIf2CmnCpsSduSize OBJECT-TYPE
        SYNTAX              Unsigned32
        UNITS               "byte"
        MAX-ACCESS          read-only
        STATUS              current
        DESCRIPTION         "The value of this parameter specifies the length
                            of the SDU for a fixed-length SDU service flow.
                            This parameter is used only if packing is on
                            and the service flow is indicated as carrying
                            fixed-length SDUs. The default value is 49 bytes,
                            i.e., VC-switched ATM cells with PHS. The parameter
                            is relevant for both ATM and Packet Convergence
                            Sublayers. DEFVAL { 49 }"
        ::= { wmanIf2CmnCpsServiceFlowEntry 13 }

    wmanIf2CmnCpsSfSchedulingType OBJECT-TYPE
        SYNTAX              WmanIf2SfSchedulingType
        MAX-ACCESS          read-only
        STATUS              current
        DESCRIPTION         "Specifies the upstream scheduling service used
                            for upstream service flow. If the referenced
                            parameter is not present in the corresponding
                            802.16 QOS Parameter Set of an upstream service
                            flow, the default value of this object is bestEffort(2).
                            DEFVAL { bestEffort } Modified by NEC to represent 
                            not only upstream but downstream"
        ::= { wmanIf2CmnCpsServiceFlowEntry 14 }

    wmanIf2CmnCpsArqEnable OBJECT-TYPE
        SYNTAX              TruthValue
        MAX-ACCESS          read-only
        STATUS              current
        DESCRIPTION         "True(1) ARQ enabling is requested for the connection."
        ::= { wmanIf2CmnCpsServiceFlowEntry 15 }

    wmanIf2CmnCpsArqWindowSize OBJECT-TYPE
        SYNTAX              Integer32 (1..1024)
        MAX-ACCESS          read-only
        STATUS              current
        DESCRIPTION         "Indicates the maximum number of unacknowledged
                            fragments at any time."
        ::= { wmanIf2CmnCpsServiceFlowEntry 16 }

    wmanIf2CmnCpsArqBlockLifetime OBJECT-TYPE
        SYNTAX              Integer32 (0..65535)
        UNITS               "10 us"
        MAX-ACCESS          read-only
        STATUS              current
        DESCRIPTION         "The maximum time interval an ARQ fragment will
                            be managed by the transmitter ARQ machine, once
                            initial transmission of the fragment has occured.
                            If transmission or retransmission of the fragment
                            is not acknowledged by the receiver before the
                            time limit is reached, the fragment is discarded.
                            A value of 0 means Infinite."
        ::= { wmanIf2CmnCpsServiceFlowEntry 17 }

    wmanIf2CmnCpsArqSyncLossTimeout OBJECT-TYPE
        SYNTAX              Integer32 (0..65535)
        UNITS               "10 us"
        MAX-ACCESS          read-only
        STATUS              current
        DESCRIPTION         "The maximum interval before declaring a loss of
                            synchronization of the sender and receiver state
                            machines. A value of 0 means Infinite."
        ::= { wmanIf2CmnCpsServiceFlowEntry 18 }

    wmanIf2CmnCpsArqDeliverInOrder OBJECT-TYPE
        SYNTAX              TruthValue
        MAX-ACCESS          read-only
        STATUS              current
        DESCRIPTION         "Indicates whether or not data is to be delivered
                            by the receiving MAC to its client application
                            in the order in which data was handed off to
                            the originating MAC."
        ::= { wmanIf2CmnCpsServiceFlowEntry 19 }

    wmanIf2CmnCpsArqRxPurgeTimeout OBJECT-TYPE
        SYNTAX              Integer32 (0..65535)
        UNITS               "10 us"
        MAX-ACCESS          read-only
        STATUS              current
        DESCRIPTION         "Indicates the time interval the ARQ window is
                            advanced after a fragment is received. A value
                            of 0 means Infinite."
        ::= { wmanIf2CmnCpsServiceFlowEntry 20 }

    wmanIf2CmnCpsArqBlockSize OBJECT-TYPE
        SYNTAX              Integer32 (1..2040)
        UNITS               "byte"
        MAX-ACCESS          read-only
        STATUS              current
        DESCRIPTION         "This value of this parameter specifies the size
                            of an ARQ block. This parameter shall be established
                            by negotiation during the connection creation
                            dialog."
        ::= { wmanIf2CmnCpsServiceFlowEntry 21 }

    wmanIf2CmnCpsMinRsvdTolerableRate OBJECT-TYPE
        SYNTAX              Unsigned32
        UNITS               "b/s"
        MAX-ACCESS          read-only
        STATUS              current
        DESCRIPTION         "Minimum Tolerable Traffic Rate = R (bits/sec)
                            with time base T(sec) means the following. Let
                            S denote additional demand accumulated at the
                            MAC SAP of the transmitter during an arbitrary
                            time interval of the length T. Then the amount
                            of data forwarded at the receiver to CS (in bits)
                            during this interval should be not less than
                            min {S, R * T}."
        ::= { wmanIf2CmnCpsServiceFlowEntry 22 }

    wmanIf2CmnCpsReqTxPolicy OBJECT-TYPE
        SYNTAX              BITS {
                                noBroadcastBwReq( 0 ),
                                reserved1( 1 ),
                                noPiggybackReq( 2 ),
                                noFragmentData( 3 ),
                                noPHS( 4 ),
                                noSduPacking( 5 ),
                                noCrc( 6 ),
                                reserved2( 7 )
                            }
        MAX-ACCESS          read-only
        STATUS              current
        DESCRIPTION         "The value of this parameter provides the capability
                            to specify certain attributes for the associated
                            service flow. An attribute is enabled by setting
                            the corresponding bit position to 1."
        ::= { wmanIf2CmnCpsServiceFlowEntry 23 }

    wmanIf2CmnSfCsSpecification OBJECT-TYPE
        SYNTAX              WmanIf2CsSpecification
        MAX-ACCESS          read-only
        STATUS              current
        DESCRIPTION         "This parameter specifies the convergence sublayer
                            encapsulation mode."
        ::= { wmanIf2CmnCpsServiceFlowEntry 24 }

    wmanIf2CmnCpsTargetSaid OBJECT-TYPE
        SYNTAX              Integer32 (0..65535)
        MAX-ACCESS          read-only
        STATUS              current
        DESCRIPTION         "The target SAID parameter indicates the SAID onto
                            which the service flow being set up shall be
                            mapped."
        ::= { wmanIf2CmnCpsServiceFlowEntry 25 }

    --
    --
    --
    --
    wmanIf2CmnBsSsConfigurationTable OBJECT-TYPE
        SYNTAX              SEQUENCE OF WmanIf2CmnBsSsConfigurationEntry
        MAX-ACCESS          not-accessible
        STATUS              current
        DESCRIPTION         "This table provides one row for each BS sector
                            that contains the system parameters common in
                            both SS and BS. All SSs shall have the same parameters
                            as the BS to which the SSs are associated."
        ::= { wmanIf2CmnCps 2 }

    wmanIf2CmnBsSsConfigurationEntry OBJECT-TYPE
        SYNTAX              WmanIf2CmnBsSsConfigurationEntry
        MAX-ACCESS          not-accessible
        STATUS              current
        DESCRIPTION         "This table is indexed by ifIndex, indicating BS
                            sector."
        INDEX               {
                                ifIndex
                            }
        ::= { wmanIf2CmnBsSsConfigurationTable 1 }

    WmanIf2CmnBsSsConfigurationEntry ::= SEQUENCE {
        wmanIf2CmnInvitedRangRetries
            Integer32,
        wmanIf2CmnDSxReqRetries
            Unsigned32,
        wmanIf2CmnDSxRespRetries
            Unsigned32,
        wmanIf2CmnT7Timeout
            Integer32,
        wmanIf2CmnT8Timeout
            Integer32,
        wmanIf2CmnT10Timeout
            Integer32,
        wmanIf2CmnT22Timeout
            Integer32
    }

    wmanIf2CmnInvitedRangRetries OBJECT-TYPE
        SYNTAX              Integer32 (16..65535)
        MAX-ACCESS          read-write
        STATUS              current
        DESCRIPTION         "Number of retries on inviting Ranging Requests."
        ::= { wmanIf2CmnBsSsConfigurationEntry 1 }

    wmanIf2CmnDSxReqRetries OBJECT-TYPE
        SYNTAX              Unsigned32
        MAX-ACCESS          read-write
        STATUS              current
        DESCRIPTION         "Number of Timeout Retries on DSA/DSC/DSD Requests.
                            DEFVAL { 3 }"
        ::= { wmanIf2CmnBsSsConfigurationEntry 2 }

    wmanIf2CmnDSxRespRetries OBJECT-TYPE
        SYNTAX              Unsigned32
        MAX-ACCESS          read-write
        STATUS              current
        DESCRIPTION         "Number of Timeout Retries on DSA/DSC/DSD Responses.
                            DEFVAL { 3 }"
        ::= { wmanIf2CmnBsSsConfigurationEntry 3 }

    wmanIf2CmnT7Timeout OBJECT-TYPE
        SYNTAX              Integer32 (0..1000)
        UNITS               "milliseconds"
        MAX-ACCESS          read-write
        STATUS              current
        DESCRIPTION         "Wait for DSA/DSC/DSD Response Timeout in ms."
        ::= { wmanIf2CmnBsSsConfigurationEntry 4 }

    wmanIf2CmnT8Timeout OBJECT-TYPE
        SYNTAX              Integer32 (0..300)
        UNITS               "milliseconds"
        MAX-ACCESS          read-write
        STATUS              current
        DESCRIPTION         "Wait for DSA/DSC/DSD Acknowledge Timeout in ms."
        ::= { wmanIf2CmnBsSsConfigurationEntry 5 }

    wmanIf2CmnT10Timeout OBJECT-TYPE
        SYNTAX              Integer32 (0..3000)
        UNITS               "milliseconds"
        MAX-ACCESS          read-write
        STATUS              current
        DESCRIPTION         "Wait for Transaction End timeout in ms."
        ::= { wmanIf2CmnBsSsConfigurationEntry 6 }

    wmanIf2CmnT22Timeout OBJECT-TYPE
        SYNTAX              Integer32 (0..500)
        UNITS               "milliseconds"
        MAX-ACCESS          read-write
        STATUS              current
        DESCRIPTION         "Wait for ARQ Reset in ms."
        ::= { wmanIf2CmnBsSsConfigurationEntry 7 }

    --
    --
    --
    wmanIf2MibConformance OBJECT IDENTIFIER ::= { wmanIf2Mib 2 }

    wmanIf2MibGroups OBJECT IDENTIFIER ::= { wmanIf2MibConformance 1 }

    wmanIf2MibCommonGroup OBJECT-GROUP
        OBJECTS {           
                        wmanIf2CmnCpsTargetSaid,
                        wmanIf2CmnInvitedRangRetries,
                        wmanIf2CmnDSxReqRetries,
                        wmanIf2CmnDSxRespRetries,
                        wmanIf2CmnT7Timeout,
                        wmanIf2CmnT8Timeout,
                        wmanIf2CmnT10Timeout,
                        wmanIf2CmnT22Timeout
                }
        --Classification
        --Configuration parameters
        STATUS              current
        DESCRIPTION         "This group contains objects for both BS and SS,
                            and are independent of PHY."
        ::= { wmanIf2MibGroups 1 }

    wmanIf2MibQoSGroup OBJECT-GROUP
        OBJECTS {           
                        wmanIf2CmnCpsSfId,
                        wmanIf2CmnCpsSfCid,
                        wmanIf2CmnCpsSfDirection,
                        wmanIf2CmnCpsSfState,
                        wmanIf2CmnCpsTrafficPriority,
                        wmanIf2CmnCpsMaxSustainedRate,
                        wmanIf2CmnCpsMaxTrafficBurst,
                        wmanIf2CmnCpsMinReservedRate,
                        wmanIf2CmnCpsToleratedJitter,
                        wmanIf2CmnCpsMaxLatency,
                        wmanIf2CmnCpsFixedVsVariableSduInd,
                        wmanIf2CmnCpsSduSize,
                        wmanIf2CmnCpsSfSchedulingType,
                        wmanIf2CmnCpsArqEnable,
                        wmanIf2CmnCpsArqWindowSize,
                        wmanIf2CmnCpsArqBlockLifetime,
                        wmanIf2CmnCpsArqSyncLossTimeout,
                        wmanIf2CmnCpsArqDeliverInOrder,
                        wmanIf2CmnCpsArqRxPurgeTimeout,
                        wmanIf2CmnCpsArqBlockSize,
                        wmanIf2CmnCpsMinRsvdTolerableRate,
                        wmanIf2CmnCpsReqTxPolicy,
                        wmanIf2CmnSfCsSpecification
                }
        STATUS              current
        DESCRIPTION         "This group contains QoS objects for both BS and
                            SS."
        ::= { wmanIf2MibGroups 2 }

    wmanIf2MibBsGroup OBJECT-GROUP
        OBJECTS {           
                        wmanIf2BsSsMacSduCount,
                        wmanIf2BsSsOctetCount,
                        wmanIf2BsSsResetCounter,
                        wmanIf2BsSsResetCounterTime,
                        wmanIf2BsSsBasicCid,
                        wmanIf2BsSsPrimaryCid,
                        wmanIf2BsSsSecondaryCid,
                        wmanIf2BsSsManagementSupport,
                        wmanIf2BsSsIpManagementMode,
                        wmanIf2Bs2ndMgmtDlQoSProfileIndex,
                        wmanIf2Bs2ndMgmtUlQoSProfileIndex,
                        wmanIf2BsAutoSfidEnabled,
                        wmanIf2BsAutoSfidRangeMin,
                        wmanIf2BsAutoSfidRangeMax,
                        wmanIf2BsResetSector,
                        wmanIf2BsSs2ndMgmtArqEnable,
                        wmanIf2BsSs2ndMgmtArqWindowSize,
                        wmanIf2BsSs2ndMgmtArqDnLinkTxDelay,
                        wmanIf2BsSs2ndMgmtArqUpLinkTxDelay,
                        wmanIf2BsSs2ndMgmtArqDnLinkRxDelay,
                        wmanIf2BsSs2ndMgmtArqUpLinkRxDelay,
                        wmanIf2BsSs2ndMgmtArqBlockLifetime,
                        wmanIf2BsSs2ndMgmtArqSyncLossTimeout,
                        wmanIf2BsSs2ndMgmtArqDeliverInOrder,
                        wmanIf2BsSs2ndMgmtArqRxPurgeTimeout,
                        wmanIf2BsSs2ndMgmtArqBlockSize,
                        wmanIf2BsSsVendorIdEncoding,
                        wmanIf2BsSsAasBroadcastPermission,
                        wmanIf2BsSsMaxTxPowerBpsk,
                        wmanIf2BsSsMaxTxPowerQpsk,
                        wmanIf2BsSsMaxTxPower16Qam,
                        wmanIf2BsSsMaxTxPower64Qam,
                        wmanIf2BsSsMacVersion,
                        wmanIf2BsDcdInterval,
                        wmanIf2BsUcdInterval,
                        wmanIf2BsUcdTransition,
                        wmanIf2BsDcdTransition,
                        wmanIf2BsT9Timeout,
                        wmanIf2BsInitialRangingInterval,
                        wmanIf2BsSsULMapProcTime,
                        wmanIf2BsSsRangRespProcTime,
                        wmanIf2BsT13Timeout,
                        wmanIf2BsT15Timeout,
                        wmanIf2BsT17Timeout,
                        wmanIf2BsT27IdleTimer,
                        wmanIf2BsT27ActiveTimer,
                        wmanIf2BsHistogramIndex,
                        wmanIf2BsChannelNumber,
                        wmanIf2BsStartFrame,
                        wmanIf2BsDuration,
                        wmanIf2BsBasicReport,
                        wmanIf2BsMeanCinrReport,
                        wmanIf2BsMeanRssiReport,
                        wmanIf2BsStdDeviationCinrReport,
                        wmanIf2BsStdDeviationRssiReport,
                        wmanIf2BsCapUplinkCidSupport,
                        wmanIf2BsCapArqSupport,
                        wmanIf2BsCapDsxFlowControl,
                        wmanIf2BsCapMacCrcSupport,
                        wmanIf2BsCapMcaFlowControl,
                        wmanIf2BsCapMcpGroupCidSupport,
                        wmanIf2BsCapPkmFlowControl,
                        wmanIf2BsCapAuthPolicyControl,
                        wmanIf2BsCapMaxNumOfSupportedSA,
                        wmanIf2BsCapIpVersion,
                        wmanIf2BsCapMacCsSupportBitMap,
                        wmanIf2BsCapMaxNumOfClassifier,
                        wmanIf2BsCapPhsSupport,
                        wmanIf2BsCapBandwidthAllocSupport,
                        wmanIf2BsCapPduConstruction,
                        wmanIf2BsCapTtgTransitionGap,
                        wmanIf2BsCapRtgTransitionGap,
                        wmanIf2BsCapCfgUplinkCidSupport,
                        wmanIf2BsCapCfgArqSupport,
                        wmanIf2BsCapCfgDsxFlowControl,
                        wmanIf2BsCapCfgMacCrcSupport,
                        wmanIf2BsCapCfgMcaFlowControl,
                        wmanIf2BsCapCfgMcpGroupCidSupport,
                        wmanIf2BsCapCfgPkmFlowControl,
                        wmanIf2BsCapCfgAuthPolicyControl,
                        wmanIf2BsCapCfgMaxNumOfSupportedSA,
                        wmanIf2BsCapCfgIpVersion,
                        wmanIf2BsCapCfgMacCsSupportBitMap,
                        wmanIf2BsCapCfgMaxNumOfClassifier,
                        wmanIf2BsCapCfgPhsSupport,
                        wmanIf2BsCapCfgBandwidthAllocSupport,
                        wmanIf2BsCapCfgPduConstruction,
                        wmanIf2BsCapCfgTtgTransitionGap,
                        wmanIf2BsCapCfgRtgTransitionGap,
                        wmanIf2BsSsActionsResetSs,
                        wmanIf2BsSsActionsAbortSs,
                        wmanIf2BsSsActionsOverrideDnFreq,
                        wmanIf2BsSsActionsOverrideChannelId,
                        wmanIf2BsSsActionsDeReRegSs,
                        wmanIf2BsSsActionsDeReRegSsCode,
                        wmanIf2BsSsActionsRowStatus,
                        wmanIf2BsPkmV1AkLifetime,
                        wmanIf2BsPkmV1TekLifetime,
                        wmanIf2BsPkmV1SelfSigManufCertTrust,
                        wmanIf2BsPkmV1CheckCertValidityPeriods
                }
        --Service classes
        --Classification
        --Packet counters
        --Capability negotiation
        --Configuration parameters
        --Performance monitoring
        --Capability negotiation
        --Privacy sublayer
        --Notification
        STATUS              current
        DESCRIPTION         "This group contains objects for BS, and are independent
                            of PHY."
        ::= { wmanIf2MibGroups 3 }

    wmanIf2MibBsAasGroup OBJECT-GROUP
        OBJECTS {           
                        wmanIf2BsAasChanFbckReqFreq,
                        wmanIf2BsAasBeamSelectFreq,
                        wmanIf2BsAasChanFbckReqResolution,
                        wmanIf2BsAasBeamReqResolution,
                        wmanIf2BsAasNumOptDiversityZones
                }
        --AAS Configuration parameters
        STATUS              current
        DESCRIPTION         "This group contains objects for AAS in BS."
        ::= { wmanIf2MibGroups 4 }

    wmanIf2MibBsOfdmaGroup OBJECT-GROUP
        OBJECTS {           
                        wmanIf2BsOfdmaCtBasedResvTimeout,
                        wmanIf2BsOfdmaUplinkCenterFreq,
                        wmanIf2BsOfdmaStartOfRngCodes,
                        wmanIf2BsOfdmaPermutationBase,
                        wmanIf2BsOfdmaULAllocSubchBitmap,
                        wmanIf2BsOfdmaOptPermULAllocSubchBitmap,
                        wmanIf2BsOfdmaBandAMCAllocThreshold,
                        wmanIf2BsOfdmaBandAMCReleaseThreshold,
                        wmanIf2BsOfdmaBandAMCAllocTimer,
                        wmanIf2BsOfdmaBandAMCReleaseTimer,
                        wmanIf2BsOfdmaBandStatRepMAXPeriod,
                        wmanIf2BsOfdmaBandAMCRetryTimer,
                        wmanIf2BsOfdmaBsEIRP,
                        wmanIf2BsOfdmaChannelNumber,
                        wmanIf2BsOfdmaTTG,
                        wmanIf2BsOfdmaRTG,
                        wmanIf2BsOfdmaInitRngMaxRSS,
                        wmanIf2BsOfdmaDownlinkCenterFreq,
                        wmanIf2BsOfdmaBsId,
                        wmanIf2BsOfdmaMacVersion,
                        wmanIf2BsOfdmaFrameDurationCode,
                        wmanIf2BsOfdmaUcdFecCodeType,
                        wmanIf2BsOfdmaRangingDataRatio,
                        wmanIf2BsOfdmaUcdBurstProfileRowStatus,
                        wmanIf2BsOfdmaDownlinkFrequency,
                        wmanIf2BsOfdmaDcdFecCodeType,
                        wmanIf2BsOfdmaDcdBurstProfileRowStatus
                }
        STATUS              current
        DESCRIPTION         "This group contains objects for BS and OFDMA PHY."
        ::= { wmanIf2MibGroups 8 }

    wmanIf2MibAllObjects OBJECT-GROUP
        OBJECTS {           
                        wmanIf2BsSaChallengeTimer,
                        wmanIf2BsSaChallengeMaxResends,
                        wmanIf2BsSaTekTimer,
                        wmanIf2BsSaTekReqMaxResends,
                        wmanIf2Bs2ndEapTimeout,
                        wmanIf2BsEapCompleteResends,
                        wmanIf2BsCapDownlinkCidSupport,
                        wmanIf2BsCapPackingSupport,
                        wmanIf2BsCapExtendedRtpsSupport,
                        wmanIf2BsCapMaxNumBurstToMs,
                        wmanIf2BsCapIpAddrAllocMethod,
                        wmanIf2BsCapArqAckType,
                        wmanIf2BsCapMacHeader,
                        wmanIf2BsCapMaxMacLevelDlFrame,
                        wmanIf2BsCapMaxMacLevelUlFrame,
                        wmanIf2BsCapNumOfProvisionedSf,
                        wmanIf2BsCapPkmVersion,
                        wmanIf2BsCapAuthPolicy,
                        wmanIf2BsCapMacMode,
                        wmanIf2BsCapPnWindowSize,
                        wmanIf2BsCapExtCapability,
                        wmanIf2BsCapCfgDownlinkCidSupport,
                        wmanIf2BsCapCfgPackingSupport,
                        wmanIf2BsCapCfgExtendedRtpsSupport,
                        wmanIf2BsCapCfgMaxNumBurstToMs,
                        wmanIf2BsCapCfgIpAddrAllocMethod,
                        wmanIf2BsCapCfgArqAckType,
                        wmanIf2BsCapCfgMacHeader,
                        wmanIf2BsCapCfgMaxMacLevelDlFrame,
                        wmanIf2BsCapCfgMaxMacLevelUlFrame,
                        wmanIf2BsCapCfgNumOfProvisionedSf,
                        wmanIf2BsCapCfgPkmVersion,
                        wmanIf2BsCapCfgAuthPolicy,
                        wmanIf2BsCapCfgMacMode,
                        wmanIf2BsCapCfgPnWindowSize,
                        wmanIf2BsCapCfgExtCapability,
                        wmanIf2BsPkmScDataEncryptAlgorithm,
                        wmanIf2BsPkmScDataAuthentAlgorithm,
                        wmanIf2BsPkmScEncryptAlgorithm,
                        wmanIf2BsSsPkmScDataEncryptAlgorithm,
                        wmanIf2BsSsPkmScDataAuthentAlgorithm,
                        wmanIf2BsSsPkmScEncryptAlgorithm,
                        wmanIf2BsPkmV1AuthWaitTimeout,
                        wmanIf2BsPkmV1ReauthWaitTimeout,
                        wmanIf2BsPkmV1AuthGraceTime,
                        wmanIf2BsPkmV1OpWaitTimeout,
                        wmanIf2BsPkmV1RekeyWaitTimeout,
                        wmanIf2BsPkmV1TekGraceTime,
                        wmanIf2BsPkmV1AuthRejectWaitTimeout,
                        wmanIf2BsPkmPmkPrehandshakeLifetime,
                        wmanIf2BsPkmPmkLifetime,
                        wmanIf2BsSaChallengeTimeout,
                        wmanIf2BsMaxSaTekChallenge,
                        wmanIf2BsSaTekTimeout,
                        wmanIf2BsMaxSaTekRequest,
                        wmanIf2BsOfdmaCapFftSizes,
                        wmanIf2BsOfdmaCapDemodulator,
                        wmanIf2BsOfdmaCapModulator,
                        wmanIf2BsOfdmaCapNoHarqChannel,
                        wmanIf2BsOfdmaCapPermutation,
                        wmanIf2BsSsOfdmaCapDemMimo,
                        wmanIf2BsSsOfdmaCapMimoCapability,
                        wmanIf2BsSsOfdmaCapUlMimo,
                        wmanIf2BsSsOfdmaCapPrivateMap,
                        wmanIf2BsSsOfdmaCapAasCapability,
                        wmanIf2BsSsOfdmaCapCinrMeasurement,
                        wmanIf2BsSsOfdmaCapUlPowerControl,
                        wmanIf2BsSsOfdmaCapMapCapability,
                        wmanIf2BsSsOfdmaCapUlControlChannel,
                        wmanIf2BsSsOfdmaCapCistCapability,
                        wmanIf2BsSsOfdmaCapMaxHarqBurst,
                        wmanIf2BsSsOfdmaCapModMimo,
                        wmanIf2BsSsOfdmaCapSdmaPilot,
                        wmanIf2BsSsOfdmaCapMultipleBurst,
                        wmanIf2BsSsOfdmaCapIncrHarqBuffer,
                        wmanIf2BsSsOfdmaCapChaseHarqBuffer,
                        wmanIf2BsOfdmaCapCfgFftSizes,
                        wmanIf2BsOfdmaCapCfgDemodulator,
                        wmanIf2BsOfdmaCapCfgModulator,
                        wmanIf2BsOfdmaCapCfgNoHarqChannel,
                        wmanIf2BsOfdmaCapCfgPermutation,
                        wmanIf2BsSsOfdmaCapCfgDemMimo,
                        wmanIf2BsSsOfdmaCapCfgMimoCapability,
                        wmanIf2BsSsOfdmaCapCfgUlMimo,
                        wmanIf2BsSsOfdmaCapCfgPrivateMap,
                        wmanIf2BsSsOfdmaCapCfgAasCapability,
                        wmanIf2BsSsOfdmaCapCfgCinrMeasurement,
                        wmanIf2BsSsOfdmaCapCfgUlPowerControl,
                        wmanIf2BsSsOfdmaCapCfgMapCapability,
                        wmanIf2BsSsOfdmaCapCfgUlControlChannel,
                        wmanIf2BsSsOfdmaCapCfgCistCapability,
                        wmanIf2BsSsOfdmaCapCfgMaxHarqBurst,
                        wmanIf2BsSsOfdmaCapCfgModMimo,
                        wmanIf2BsSsOfdmaCapCfgSdmaPilot,
                        wmanIf2BsSsOfdmaCapCfgMultipleBurst,
                        wmanIf2BsSsOfdmaCapCfgIncrHarqBuffer,
                        wmanIf2BsSsOfdmaCapCfgChaseHarqBuffer,
                        wmanIf2BsOfdmaExHandoverRangingStart,
                        wmanIf2BsOfdmaExHandoverRangingEnd,
                        wmanIf2BsOfdmaExHARQAckDelayDLBurst,
                        wmanIf2BsOfdmaExUlAmcAlloPhyBandsBitmap,
                        wmanIf2BsOfdmaExMaxRetransmission,
                        wmanIf2BsOfdmaExNormalizedCnOverride,
                        wmanIf2BsOfdmaExSizeOfCqichId,
                        wmanIf2BsOfdmaExNormalizedCnValue,
                        wmanIf2BsOfdmaExNormalizedCnOverride2,
                        wmanIf2BsOfdmaExBandAmcEntryAvgCinr,
                        wmanIf2BsOfdmaExAasPreambleUpperBond,
                        wmanIf2BsOfdmaExAasPreambleLowerBond,
                        wmanIf2BsOfdmaExAasBeamSelectAllowed,
                        wmanIf2BsOfdmaExCqichIndicationFlag,
                        wmanIf2BsOfdmaExUpPowerAdjStep,
                        wmanIf2BsOfdmaExDownPowerAdjStep,
                        wmanIf2BsOfdmaExMinPowerOffsetAdj,
                        wmanIf2BsOfdmaExMaxPowerOffsetAdj,
                        wmanIf2BsOfdmaExHandoverRngCodes,
                        wmanIf2BsOfdmaExInitialRngInterval,
                        wmanIf2BsOfdmaExTxPwrRepThreshold,
                        wmanIf2BsOfdmaExTprPower,
                        wmanIf2BsOfdmaExAlphaPavg,
                        wmanIf2BsOfdmaExCqichTxPwrRepThreshold,
                        wmanIf2BsOfdmaExCqichTprPower,
                        wmanIf2BsOfdmaExCqichAlphaPavg,
                        wmanIf2BsOfdmaExNormalizedCnChSounding,
                        wmanIf2BsOfdmaExInitialRngBackoffStart,
                        wmanIf2BsOfdmaExInitialRngBackoffEnd,
                        wmanIf2BsOfdmaExBwRequestBackoffStart,
                        wmanIf2BsOfdmaExBwRequestBackoffEnd,
                        wmanIf2BsOfdmaExHARQAckDelayULBurst,
                        wmanIf2BsOfdmaExHarqZonePermutation,
                        wmanIf2BsOfdmaExHMaxRetransmission,
                        wmanIf2BsOfdmaExCinrAlphaAvg,
                        wmanIf2BsOfdmaExRssiAlphaAvg,
                        wmanIf2BsOfdmaExDlAmcAlloPhyBandsBitmap,
                        wmanIf2BsOfdmaExHandoverSupported,
                        wmanIf2BsOfdmaExThresholdAddBsDivSet,
                        wmanIf2BsOfdmaExThresholdDelBsDivSet,
                        wmanIf2BsOfdmaExAsrSlotLength,
                        wmanIf2BsOfdmaExAsrSwitchingPeriod,
                        wmanIf2BsOfdmaExHysteresisMargin,
                        wmanIf2BsOfdmaExTimeToTrigger,
                        wmanIf2BsOfdmaExRestartCount
                }
        STATUS              current
        DESCRIPTION         "This automatically created object group contains
                            all those objects that do not belong to any other
                            OBJECT-GROUP"
        ::= { wmanIf2MibGroups 14 }

    wmanIf2MibCompliances OBJECT IDENTIFIER ::= { wmanIf2MibConformance 2 }

    --compliance statements
    wmanIf2MibCompliance MODULE-COMPLIANCE
        STATUS              current
        DESCRIPTION         "The compliance statement for devices that implement
                            Wireless MAN interfaces as defined in IEEE Std
                            802.16-2004."

        MODULE  -- this module
                MANDATORY-GROUPS  {         
                                wmanIf2MibCommonGroup
                }

            --unconditionally mandatory groups
                GROUP               wmanIf2MibQoSGroup
        --unconditionally mandatory group
                DESCRIPTION         "This group is mandatory for Base Station and subscriber
                            station."

                GROUP               wmanIf2MibBsGroup
        --conditionally mandatory group
                DESCRIPTION         "This group is mandatory for Base Station."

                GROUP               wmanIf2MibBsAasGroup
        --optional group
                DESCRIPTION         "This group is mandatory for Base Station."

                GROUP               wmanIf2MibBsOfdmaGroup
        --conditionally mandatory group
                DESCRIPTION         "This group is mandatory for Base Station implementaing
                            the OFDMA PHY."


        ::= { wmanIf2MibCompliances 1 }



END
