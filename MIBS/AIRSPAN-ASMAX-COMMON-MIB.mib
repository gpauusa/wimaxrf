--
-- AIRSPAN-ASMAX-COMMON-MIB.mib
-- MIB generated by MG-SOFT Visual MIB Builder 2010 Version 8.0  Build 400
-- Tuesday, August 30, 2011 at 10:53:53
--

	AIRSPAN-ASMAX-COMMON-MIB DEFINITIONS ::= BEGIN
 
		IMPORTS
			asMax			
				FROM AIRSPAN-PRODUCTS-MIB			
			OBJECT-GROUP, MODULE-COMPLIANCE, NOTIFICATION-GROUP			
				FROM SNMPv2-CONF			
			Unsigned32, OBJECT-TYPE, MODULE-IDENTITY, NOTIFICATION-TYPE			
				FROM SNMPv2-SMI			
			DisplayString, MacAddress, TEXTUAL-CONVENTION			
				FROM SNMPv2-TC;
	
	
		-- 1.3.6.1.4.1.989.1.16.1
		asMaxCommon MODULE-IDENTITY 
			LAST-UPDATED "200909081713Z"		-- September 08, 2009 at 17:13 GMT
			ORGANIZATION 
				"Airspan"
			CONTACT-INFO 
				"Contact-info."
			DESCRIPTION 
				"Description."
			REVISION "200511231116Z"		-- November 23, 2005 at 11:16 GMT
			DESCRIPTION 
				"Draft 2.
				-Introduced MIB module AIRSPAN-ASMAX-COMMON-MIB
				 (changed file name to match module name)
				-Added tables:
				 -asMaxCmInventoryTable
				 -asMaxCmTemperatureMonitorTable"
			REVISION "200512081319Z"		-- December 08, 2005 at 13:19 GMT
			DESCRIPTION 
				"Draft 3.
				Inventory reworked. Columns added to inventory:
				-asMaxCmInventoryProductCode
				Changed definition of asMaxCmInventoryType"
			REVISION "200601060915Z"		-- January 06, 2006 at 09:15 GMT
			DESCRIPTION 
				"Draft 4
				- Added in asMaxCmInventoryTable:
				  - asMaxCmInventoryCleiCode
				  - asMaxCmInventoryItemDescription
				  - asMaxCmInventoryManufDate
				- Fixed error: type of asMaxCmInventoryAssemblyRevision to OCTET STRING"
			REVISION "200604041310Z"		-- April 04, 2006 at 13:10 GMT
			DESCRIPTION 
				"Draft 5
				- added traps with related control and status objects:
				  - asMaxCmTemperatureChangeTrap
				  - asMaxCmShutdownTrap"
			REVISION "200610271038Z"		-- October 27, 2006 at 10:38 GMT
			DESCRIPTION 
				"Draft 6
				- added asMaxCmInventoryHardwareMacAddress"
			REVISION "200803121138Z"		-- March 12, 2008 at 11:38 GMT
			DESCRIPTION 
				"Draft 7:
				asMaxCmTempMonValue corrected."
			REVISION "200803261038Z"		-- March 26, 2008 at 10:38 GMT
			DESCRIPTION 
				"Draft 8:
				- Added asMaxCmInventoryManufName
				- Added asMaxCmInventoryFactoryCode"
			REVISION "200804010917Z"		-- April 01, 2008 at 09:17 GMT
			DESCRIPTION 
				"Draft 9:
				- changed asMaxCmInventoryManufName to size 0-8.
				- changed asMaxCmInventoryFactoryCode to size 0-6."
			REVISION "200805221713Z"		-- May 22, 2008 at 17:13 GMT
			DESCRIPTION 
				"Draft 10:
				- added asMaxCmTempMonStatus for individual sensors
				- updated description in all trap and temperature related objects
				- added asMaxCmDcVoltageMonitorTable for viltage sensors
				- added asMaxCmDcVoltageTrap trap and associated objects
				- simplified conformance objects"
			REVISION "200909081713Z"		-- September 08, 2009 at 17:13 GMT
			DESCRIPTION 
				"Draft 11:
				- added additional value dcVoltageOutOfRange(3) for asMaxCmDcVoltageMonStatus"
			::= { asMax 1 }

		
	
--
-- Textual conventions
--
	
		AsmaxBooleanSwitch ::= TEXTUAL-CONVENTION
			STATUS current
			DESCRIPTION 
				"Description."
			SYNTAX INTEGER
				{
				booleanFalse(0),
				booleanTrue(1)
				}

	
--
-- Node definitions
--
	
		-- 1.3.6.1.4.1.989.1.16.1.0
		asMaxCmConformance OBJECT IDENTIFIER ::= { asMaxCommon 0 }

		
		-- 1.3.6.1.4.1.989.1.16.1.0.1
		asMaxCmCompliances OBJECT IDENTIFIER ::= { asMaxCmConformance 1 }

		
		-- 1.3.6.1.4.1.989.1.16.1.0.1.1
		asMaxCmCompliance MODULE-COMPLIANCE
			STATUS current
			DESCRIPTION 
				"Description."
			MODULE -- this module
				MANDATORY-GROUPS { asMaxCmNotificationGroup, asMaxCmObjectGroup }
			::= { asMaxCmCompliances 1 }

		
		-- 1.3.6.1.4.1.989.1.16.1.0.2
		asMaxCmGroups OBJECT IDENTIFIER ::= { asMaxCmConformance 2 }

		
		-- 1.3.6.1.4.1.989.1.16.1.0.2.1
		asMaxCmNotificationGroup NOTIFICATION-GROUP
			NOTIFICATIONS { asMaxCmTemperatureChangeTrap, asMaxCmShutdownTrap, asMaxCmDcVoltageTrap, asMaxCmSdrMainPllStatusTrap }
			STATUS current
			DESCRIPTION 
				"Description."
			::= { asMaxCmGroups 1 }

		
		-- 1.3.6.1.4.1.989.1.16.1.0.2.2
		asMaxCmObjectGroup OBJECT-GROUP
			OBJECTS { asMaxCmMonPcToTargetBuff, asMaxCmMonTargetToPcBuff, asMaxCmMonSnmpRelayStatus, asMaxCmMonTesting, asMaxCmInventoryType, 
				asMaxCmInventoryInstance, asMaxCmInventoryBoardNumber, asMaxCmInventoryBoardRevision, asMaxCmInventorySerialNumber, asMaxCmInventoryHardwareIdentifier, 
				asMaxCmInventorySoftwareProductNumber, asMaxCmInventoryDescription, asMaxCmInventoryCurrentSwVersion, asMaxCmInventoryProductCode, asMaxCmInventoryAssemblyNumber, 
				asMaxCmInventoryAssemblyRevision, asMaxCmInventoryCleiCode, asMaxCmInventoryItemDescription, asMaxCmInventoryManufDate, asMaxCmInventoryHardwareMacAddress, 
				asMaxCmInventoryManufName, asMaxCmInventoryFactoryCode, asMaxCmTempMonInventoryItem, asMaxCmTempMonSensorName, asMaxCmTempMonValue, 
				asMaxCmTempMonStatus, asMaxCmDcVoltageMonInventoryItem, asMaxCmDcVoltageMonSensorName, asMaxCmDcVoltageMonValue, asMaxCmDcVoltageMonStatus, 
				asMaxCmTemperatureChangeTrapEnabled, asMaxCmTemperatureStatus, asMaxCmTemperatureStatusInfo, asMaxShutdownReasonCode, asMaxShutdownReasonInfo, 
				asMaxCmShutdownTrapEnabled, asMaxCmDcVoltageStatus, asMaxCmSdrMainPllStatus, asMaxCmDcVoltageStatusInfo, asMaxCmDcVoltageTrapEnabled
				 }
			STATUS current
			DESCRIPTION 
				"Description."
			::= { asMaxCmGroups 2 }

		
		-- 1.3.6.1.4.1.989.1.16.1.1
		asMaxCmMonitor OBJECT IDENTIFIER ::= { asMaxCommon 1 }

		
		-- 1.3.6.1.4.1.989.1.16.1.1.1
		asMaxCmMonPcToTargetBuff OBJECT-TYPE
			SYNTAX OCTET STRING
			MAX-ACCESS read-write
			STATUS current
			DESCRIPTION
				"The buffer that is received by the PC monitor tool."
			::= { asMaxCmMonitor 1 }

		
		-- 1.3.6.1.4.1.989.1.16.1.1.2
		asMaxCmMonTargetToPcBuff OBJECT-TYPE
			SYNTAX OCTET STRING
			MAX-ACCESS read-write
			STATUS current
			DESCRIPTION
				"The buffer that is received by the monitor task."
			::= { asMaxCmMonitor 2 }

		
		-- 1.3.6.1.4.1.989.1.16.1.1.3
		asMaxCmMonSnmpRelayStatus OBJECT-TYPE
			SYNTAX INTEGER
				{
				enable(1),
				disable(2)
				}
			MAX-ACCESS read-write
			STATUS current
			DESCRIPTION
				"This attribute indicates whether the monitor tool
				can query the target via SNMP."
			::= { asMaxCmMonitor 3 }

		
		-- 1.3.6.1.4.1.989.1.16.1.1.100
		asMaxCmMonTesting OBJECT-TYPE
			SYNTAX INTEGER
				{
				setNetEntryParams(1),
				startNetEntryTest(2),
				stopNetEntryTest(3),
				startIpConnTest(4)
				}
			MAX-ACCESS read-write
			STATUS current
			DESCRIPTION
				"Used for test may be removed - Lika."
			::= { asMaxCmMonitor 100 }

		
		-- 1.3.6.1.4.1.989.1.16.1.2
		asMaxCmInventoryTable OBJECT-TYPE
			SYNTAX SEQUENCE OF AsMaxCmInventoryEntry
			MAX-ACCESS not-accessible
			STATUS current
			DESCRIPTION
				"This table would describe all inventories that constitute current product.
				(eg: 1 SDR + 2 SCRTs + 3 PSUs + ...)"
			::= { asMaxCommon 2 }

		
		-- 1.3.6.1.4.1.989.1.16.1.2.1
		asMaxCmInventoryEntry OBJECT-TYPE
			SYNTAX AsMaxCmInventoryEntry
			MAX-ACCESS not-accessible
			STATUS current
			DESCRIPTION
				"Each entry would describe the hardware & software properties of the inventory 
				that is part of current product. "
			INDEX { asMaxCmInventoryItem }
			::= { asMaxCmInventoryTable 1 }

		
		AsMaxCmInventoryEntry ::=
			SEQUENCE { 
				asMaxCmInventoryItem
					INTEGER,
				asMaxCmInventoryType
					INTEGER,
				asMaxCmInventoryInstance
					INTEGER,
				asMaxCmInventoryBoardNumber
					OCTET STRING,
				asMaxCmInventoryBoardRevision
					OCTET STRING,
				asMaxCmInventorySerialNumber
					OCTET STRING,
				asMaxCmInventoryHardwareIdentifier
					Unsigned32,
				asMaxCmInventorySoftwareProductNumber
					OCTET STRING,
				asMaxCmInventoryDescription
					DisplayString,
				asMaxCmInventoryCurrentSwVersion
					OCTET STRING,
				asMaxCmInventoryProductCode
					OCTET STRING,
				asMaxCmInventoryAssemblyNumber
					OCTET STRING,
				asMaxCmInventoryAssemblyRevision
					OCTET STRING,
				asMaxCmInventoryCleiCode
					OCTET STRING,
				asMaxCmInventoryItemDescription
					DisplayString,
				asMaxCmInventoryManufDate
					OCTET STRING,
				asMaxCmInventoryHardwareMacAddress
					MacAddress,
				asMaxCmInventoryManufName
					OCTET STRING,
				asMaxCmInventoryFactoryCode
					OCTET STRING
			 }

		-- 1.3.6.1.4.1.989.1.16.1.2.1.1
		asMaxCmInventoryItem OBJECT-TYPE
			SYNTAX INTEGER (1..65535)
			MAX-ACCESS not-accessible
			STATUS current
			DESCRIPTION
				"Uniquely identifies each inventory that constitute current product."
			::= { asMaxCmInventoryEntry 1 }

		
		-- 1.3.6.1.4.1.989.1.16.1.2.1.2
		asMaxCmInventoryType OBJECT-TYPE
			SYNTAX INTEGER
				{
				other(0),
				system(1),
				equipment(2)
				}
			MAX-ACCESS read-only
			STATUS current
			DESCRIPTION
				"Definition of available inventory types.
				system: top level inventory - identification of a product as a whole BS or SS. 
				    It doesn't have to have all the numbers filled.
				equipment: board level inventory - one row for inventory holding board (e.g.SDR, SCRT)
				    It has most of the numbers filled.
				other: used if none of the above fits the purpose.
				"
			::= { asMaxCmInventoryEntry 2 }

		
		-- 1.3.6.1.4.1.989.1.16.1.2.1.3
		asMaxCmInventoryInstance OBJECT-TYPE
			SYNTAX INTEGER (0..255)
			MAX-ACCESS read-only
			STATUS current
			DESCRIPTION
				"Instance of the inventory item for items having the same part number.
				e.g. SCRT instance 1 and 2 have the same BoardNumber and have 
				different SerialNumber.
				"
			::= { asMaxCmInventoryEntry 3 }

		
		-- 1.3.6.1.4.1.989.1.16.1.2.1.4
		asMaxCmInventoryBoardNumber OBJECT-TYPE
			SYNTAX OCTET STRING (SIZE (0..64))
			MAX-ACCESS read-only
			STATUS current
			DESCRIPTION
				"Octet string to identify the board number if relevant to this inventory type:
				eg: '303-xxxx-xxx'"
			::= { asMaxCmInventoryEntry 4 }

		
		-- 1.3.6.1.4.1.989.1.16.1.2.1.5
		asMaxCmInventoryBoardRevision OBJECT-TYPE
			SYNTAX OCTET STRING (SIZE (0..64))
			MAX-ACCESS read-only
			STATUS current
			DESCRIPTION
				"Octet string to identify the the revision of the board identified with BoardNumber."
			::= { asMaxCmInventoryEntry 5 }

		
		-- 1.3.6.1.4.1.989.1.16.1.2.1.6
		asMaxCmInventorySerialNumber OBJECT-TYPE
			SYNTAX OCTET STRING (SIZE (0..64))
			MAX-ACCESS read-only
			STATUS current
			DESCRIPTION
				"Octet string to uniquely identify a physical entity.
				eg: x########x####x"
			::= { asMaxCmInventoryEntry 6 }

		
		-- 1.3.6.1.4.1.989.1.16.1.2.1.7
		asMaxCmInventoryHardwareIdentifier OBJECT-TYPE
			SYNTAX Unsigned32 (0..2147483647)
			MAX-ACCESS read-only
			STATUS current
			DESCRIPTION
				"Identifier, which is read-only, hardwired in the schematics,
				design specific hardware identifier. 
				It can contain info about BOM and board version. 
				E.g. for BS it is defined as follows:
				7-5:bom_var
				4-0:Version
				"
			::= { asMaxCmInventoryEntry 7 }

		
		-- 1.3.6.1.4.1.989.1.16.1.2.1.8
		asMaxCmInventorySoftwareProductNumber OBJECT-TYPE
			SYNTAX OCTET STRING (SIZE (0..64))
			MAX-ACCESS read-only
			STATUS current
			DESCRIPTION
				"Octet string to identify the software product running 
				on the current inventory. Empty string when inventory item 
				doesn't have software or the software doesn't have software 
				produlct like identification."
			::= { asMaxCmInventoryEntry 8 }

		
		-- 1.3.6.1.4.1.989.1.16.1.2.1.9
		asMaxCmInventoryDescription OBJECT-TYPE
			SYNTAX DisplayString
			MAX-ACCESS read-only
			STATUS current
			DESCRIPTION
				"User friendly description about current inventory as entered by embedded software."
			::= { asMaxCmInventoryEntry 9 }

		
		-- 1.3.6.1.4.1.989.1.16.1.2.1.10
		asMaxCmInventoryCurrentSwVersion OBJECT-TYPE
			SYNTAX OCTET STRING (SIZE (0..64))
			MAX-ACCESS read-only
			STATUS current
			DESCRIPTION
				"Current software version running on this inventory item.
				There might be different software versions running on different
				instances of the same inventory part number.
				eg: reflecting software versions running on multiple SCRTs"
			::= { asMaxCmInventoryEntry 10 }

		
		-- 1.3.6.1.4.1.989.1.16.1.2.1.11
		asMaxCmInventoryProductCode OBJECT-TYPE
			SYNTAX OCTET STRING (SIZE (0..64))
			MAX-ACCESS read-only
			STATUS current
			DESCRIPTION
				"String based code dentifying product specified by this inventory row.
				e.g. SCRT-1-4.9T"
			::= { asMaxCmInventoryEntry 11 }

		
		-- 1.3.6.1.4.1.989.1.16.1.2.1.12
		asMaxCmInventoryAssemblyNumber OBJECT-TYPE
			SYNTAX OCTET STRING (SIZE (0..64))
			MAX-ACCESS read-only
			STATUS current
			DESCRIPTION
				"Number identifying assembly of this inventory item.
				e.g. 503-xxxx-xxx"
			::= { asMaxCmInventoryEntry 12 }

		
		-- 1.3.6.1.4.1.989.1.16.1.2.1.13
		asMaxCmInventoryAssemblyRevision OBJECT-TYPE
			SYNTAX OCTET STRING (SIZE (0..64))
			MAX-ACCESS read-only
			STATUS current
			DESCRIPTION
				"Revision of the assembly identified by AssemblyNumber."
			::= { asMaxCmInventoryEntry 13 }

		
		-- 1.3.6.1.4.1.989.1.16.1.2.1.14
		asMaxCmInventoryCleiCode OBJECT-TYPE
			SYNTAX OCTET STRING (SIZE (0..64))
			MAX-ACCESS read-only
			STATUS current
			DESCRIPTION
				"Common Language Equipment Identification. As defined by OEM / PM."
			::= { asMaxCmInventoryEntry 14 }

		
		-- 1.3.6.1.4.1.989.1.16.1.2.1.15
		asMaxCmInventoryItemDescription OBJECT-TYPE
			SYNTAX DisplayString
			MAX-ACCESS read-only
			STATUS current
			DESCRIPTION
				"User friendly description about current inventory as entered during manufacturing."
			::= { asMaxCmInventoryEntry 15 }

		
		-- 1.3.6.1.4.1.989.1.16.1.2.1.16
		asMaxCmInventoryManufDate OBJECT-TYPE
			SYNTAX OCTET STRING (SIZE (0..64))
			MAX-ACCESS read-only
			STATUS current
			DESCRIPTION
				"Date of Manufacture entered as string. Expected format: dd.mm.yyyy"
			::= { asMaxCmInventoryEntry 16 }

		
		-- 1.3.6.1.4.1.989.1.16.1.2.1.17
		asMaxCmInventoryHardwareMacAddress OBJECT-TYPE
			SYNTAX MacAddress
			MAX-ACCESS read-only
			STATUS current
			DESCRIPTION
				"Mac Address of the Front Panel Ethernet or another Mac Address selected for the purpose 
				of identification of this inventory item."
			::= { asMaxCmInventoryEntry 17 }

		
		-- 1.3.6.1.4.1.989.1.16.1.2.1.18
		asMaxCmInventoryManufName OBJECT-TYPE
			SYNTAX OCTET STRING (SIZE (0..8))
			MAX-ACCESS read-only
			STATUS current
			DESCRIPTION
				"Name of manufacturer entered as a string.
				Maximum 8 characters."
			::= { asMaxCmInventoryEntry 18 }

		
		-- 1.3.6.1.4.1.989.1.16.1.2.1.19
		asMaxCmInventoryFactoryCode OBJECT-TYPE
			SYNTAX OCTET STRING (SIZE (0..6))
			MAX-ACCESS read-only
			STATUS current
			DESCRIPTION
				"Factory code of manufacturer entered as a string.
				Maximum 6 characters."
			::= { asMaxCmInventoryEntry 19 }

		
		-- 1.3.6.1.4.1.989.1.16.1.5
		asMaxCmTemperatureMonitorTable OBJECT-TYPE
			SYNTAX SEQUENCE OF AsMaxCmTemperatureMonitorEntry
			MAX-ACCESS not-accessible
			STATUS current
			DESCRIPTION
				"Generic reporting table for all the temperature sensors in the system.
				Contains one row for each sensor."
			::= { asMaxCommon 5 }

		
		-- 1.3.6.1.4.1.989.1.16.1.5.1
		asMaxCmTemperatureMonitorEntry OBJECT-TYPE
			SYNTAX AsMaxCmTemperatureMonitorEntry
			MAX-ACCESS not-accessible
			STATUS current
			DESCRIPTION
				"Description."
			INDEX { asMaxCmTempMonItem }
			::= { asMaxCmTemperatureMonitorTable 1 }

		
		AsMaxCmTemperatureMonitorEntry ::=
			SEQUENCE { 
				asMaxCmTempMonItem
					INTEGER,
				asMaxCmTempMonInventoryItem
					INTEGER,
				asMaxCmTempMonSensorName
					DisplayString,
				asMaxCmTempMonValue
					INTEGER,
				asMaxCmTempMonStatus
					INTEGER
			 }

		-- 1.3.6.1.4.1.989.1.16.1.5.1.1
		asMaxCmTempMonItem OBJECT-TYPE
			SYNTAX INTEGER (1..255)
			MAX-ACCESS not-accessible
			STATUS current
			DESCRIPTION
				"Arbitrary identifyier of the sensor. Defined solely for the purpose of indexing of the rows in this table.
				Agent should use consecutive numbers starting with 1."
			::= { asMaxCmTemperatureMonitorEntry 1 }

		
		-- 1.3.6.1.4.1.989.1.16.1.5.1.2
		asMaxCmTempMonInventoryItem OBJECT-TYPE
			SYNTAX INTEGER (0..65535)
			MAX-ACCESS read-only
			STATUS current
			DESCRIPTION
				"Identifies the device instance the temperature sensor is installed on. 
				It is an index to generic inventory table. Zero means that the sensor is not installed on any 
				inventory item reported in the generic inventory table."
			::= { asMaxCmTemperatureMonitorEntry 2 }

		
		-- 1.3.6.1.4.1.989.1.16.1.5.1.3
		asMaxCmTempMonSensorName OBJECT-TYPE
			SYNTAX DisplayString
			MAX-ACCESS read-only
			STATUS current
			DESCRIPTION
				"Identifies the temperature sensor, the measured value of is reported in 
				asmacroTempMonValue. e.g. SDR CPU, SDR FPGA, SDR PICO
				"
			::= { asMaxCmTemperatureMonitorEntry 3 }

		
		-- 1.3.6.1.4.1.989.1.16.1.5.1.4
		asMaxCmTempMonValue OBJECT-TYPE
			SYNTAX INTEGER (-55..125)
			UNITS "deg C"
			MAX-ACCESS read-only
			STATUS current
			DESCRIPTION
				"The value of the measured temperature. The measurement algorithm should filter the small, 
				frequent changes in the temperature read from the sensor. 
				The details of the algorithm are implementation specific."
			::= { asMaxCmTemperatureMonitorEntry 4 }

		
		-- 1.3.6.1.4.1.989.1.16.1.5.1.5
		asMaxCmTempMonStatus OBJECT-TYPE
			SYNTAX INTEGER
				{
				tempNormal(0),
				tempTooHigh(1),
				tempTooLow(2)
				}
			MAX-ACCESS read-only
			STATUS current
			DESCRIPTION
				"The object reports the status of the temperature tested against some implementation
				specific criteria. This may be used by manager to indicate the abnormal temperature condition 
				of the sensor."
			::= { asMaxCmTemperatureMonitorEntry 5 }

		
		-- 1.3.6.1.4.1.989.1.16.1.6
		asMaxCmNotification OBJECT IDENTIFIER ::= { asMaxCommon 6 }

		
		-- 1.3.6.1.4.1.989.1.16.1.6.0
		asMaxCmTrapPrefix OBJECT IDENTIFIER ::= { asMaxCmNotification 0 }

		
		-- 1.3.6.1.4.1.989.1.16.1.6.0.1
		asMaxCmTemperatureChangeTrap NOTIFICATION-TYPE
			OBJECTS { asMaxCmTemperatureStatus, asMaxCmTemperatureStatusInfo }
			STATUS current
			DESCRIPTION 
				"The trap is send by agent when:
				- One or more sensors entered abnormal temperature range (alarm raise)
				- All the sensors returned to normal temperature (alarm cleared). 
				The reason of the trap is defined in its status object. The details of which sensor shows abnormal temperature
				are reported in asMaxCmTemperatureMonitorTable. The summary of reason can be reported
				in the trap StatusInfo object.
				Normally only one trap is sent when the first sensor goes out of the normal temperature range.
				Subsequent changes in the number of sensors showing abnormal temperature do not required 
				another trap, however the corresponding object in the asMaxCmTrapStatusTable should be updated on every change.
				Default severity: Major"
			::= { asMaxCmTrapPrefix 1 }

		
		-- 1.3.6.1.4.1.989.1.16.1.6.0.2
		asMaxCmShutdownTrap NOTIFICATION-TYPE
			OBJECTS { asMaxShutdownReasonCode, asMaxShutdownReasonInfo }
			STATUS current
			DESCRIPTION 
				"The trap is sent when the agent system controller identifies the condition critical to the system 
				operation e.g. overheating, and the imminent system shutdown is scheduled. 
				The exact reason of the shutdown is defined in ReasonCode object and additional details are given 
				in ReasonInfo trap object.
				This trap is not sent when the condition clears. Instead expect one of the start related traps (coldstart/warmstart).
				Default severity: Critical"
			::= { asMaxCmTrapPrefix 2 }

		
		-- 1.3.6.1.4.1.989.1.16.1.6.0.3
		asMaxCmDcVoltageTrap NOTIFICATION-TYPE
			OBJECTS { asMaxCmDcVoltageStatus, asMaxCmDcVoltageStatusInfo }
			STATUS current
			DESCRIPTION 
				"The trap is send by agent when:
				- One or more sensors entered abnormal DC voltage range (alarm raise)
				- All the sensors returned to nominal DC voltage range (alarm cleared)
				The reason of the trap is defined in its status object. The details of which sensor shows abnormal DC voltage
				are reported in asMaxCmDcVoltageMonitorTable. The summary of reason can be reported
				in the trap StatusInfo object.
				Normally only one trap is sent when the first sensor goes out of the normal DC voltage range.
				Subsequent changes in the number of sensors showing DC voltage out of range do not required 
				another trap, however the corresponding object in the asMaxCmTrapStatusTable should be updated on every change.
				Default severity: Major"
			::= { asMaxCmTrapPrefix 3 }

		
		-- 1.3.6.1.4.1.989.1.16.1.6.0.4
		asMaxCmSdrMainPllStatusTrap NOTIFICATION-TYPE
			OBJECTS { asMaxCmSdrMainPllStatus }
			STATUS current
			DESCRIPTION 
				"Description."
			::= { asMaxCmTrapPrefix 4 }

		
		-- 1.3.6.1.4.1.989.1.16.1.6.1
		asMaxCmTrapControlTable OBJECT-TYPE
			SYNTAX SEQUENCE OF AsMaxCmTrapControlEntry
			MAX-ACCESS not-accessible
			STATUS current
			DESCRIPTION
				"Description."
			::= { asMaxCmNotification 1 }

		
		-- 1.3.6.1.4.1.989.1.16.1.6.1.1
		asMaxCmTrapControlEntry OBJECT-TYPE
			SYNTAX AsMaxCmTrapControlEntry
			MAX-ACCESS not-accessible
			STATUS current
			DESCRIPTION
				"Single row."
			INDEX { asMaxCmTrapControlIndex }
			::= { asMaxCmTrapControlTable 1 }

		
		AsMaxCmTrapControlEntry ::=
			SEQUENCE { 
				asMaxCmTrapControlIndex
					INTEGER,
				asMaxCmTemperatureChangeTrapEnabled
					AsmaxBooleanSwitch,
				asMaxCmShutdownTrapEnabled
					AsmaxBooleanSwitch,
				asMaxCmDcVoltageTrapEnabled
					AsmaxBooleanSwitch
			 }

		-- 1.3.6.1.4.1.989.1.16.1.6.1.1.1
		asMaxCmTrapControlIndex OBJECT-TYPE
			SYNTAX INTEGER (1)
			MAX-ACCESS not-accessible
			STATUS current
			DESCRIPTION
				"Arbitrary index - one row only."
			::= { asMaxCmTrapControlEntry 1 }

		
		-- 1.3.6.1.4.1.989.1.16.1.6.1.1.2
		asMaxCmTemperatureChangeTrapEnabled OBJECT-TYPE
			SYNTAX AsmaxBooleanSwitch
			MAX-ACCESS read-write
			STATUS current
			DESCRIPTION
				"Enables/disables TemperatureChangeTrap"
			DEFVAL { booleanFalse }
			::= { asMaxCmTrapControlEntry 2 }

		
		-- 1.3.6.1.4.1.989.1.16.1.6.1.1.3
		asMaxCmShutdownTrapEnabled OBJECT-TYPE
			SYNTAX AsmaxBooleanSwitch
			MAX-ACCESS read-write
			STATUS current
			DESCRIPTION
				"Enables/disables ShutdownTrap"
			DEFVAL { booleanTrue }
			::= { asMaxCmTrapControlEntry 3 }

		
		-- 1.3.6.1.4.1.989.1.16.1.6.1.1.4
		asMaxCmDcVoltageTrapEnabled OBJECT-TYPE
			SYNTAX AsmaxBooleanSwitch
			MAX-ACCESS read-write
			STATUS current
			DESCRIPTION
				"Enables/disables Dc Voltage Trap"
			DEFVAL { booleanFalse }
			::= { asMaxCmTrapControlEntry 4 }

		
		-- 1.3.6.1.4.1.989.1.16.1.6.2
		asMaxCmTrapStatusTable OBJECT-TYPE
			SYNTAX SEQUENCE OF AsMaxCmTrapStatusEntry
			MAX-ACCESS not-accessible
			STATUS current
			DESCRIPTION
				"Reports current status of objects associated with traps. The table is designed for the single
				instance traps i.e. the table has only one row showing the status of all possible single instance traps
				defined in the system."
			::= { asMaxCmNotification 2 }

		
		-- 1.3.6.1.4.1.989.1.16.1.6.2.1
		asMaxCmTrapStatusEntry OBJECT-TYPE
			SYNTAX AsMaxCmTrapStatusEntry
			MAX-ACCESS not-accessible
			STATUS current
			DESCRIPTION
				"Single row."
			INDEX { asMaxCmTrapStatusIndex }
			::= { asMaxCmTrapStatusTable 1 }

		
		AsMaxCmTrapStatusEntry ::=
			SEQUENCE { 
				asMaxCmTrapStatusIndex
					INTEGER,
				asMaxCmTemperatureStatus
					INTEGER,
				asMaxCmTemperatureStatusInfo
					DisplayString,
				asMaxShutdownReasonCode
					INTEGER,
				asMaxShutdownReasonInfo
					DisplayString,
				asMaxCmDcVoltageStatus
					INTEGER,
				asMaxCmDcVoltageStatusInfo
					DisplayString,
				asMaxCmSdrMainPllStatus
					INTEGER
			 }

		-- 1.3.6.1.4.1.989.1.16.1.6.2.1.1
		asMaxCmTrapStatusIndex OBJECT-TYPE
			SYNTAX INTEGER (1)
			MAX-ACCESS not-accessible
			STATUS current
			DESCRIPTION
				"Arbitrary index - one row only."
			::= { asMaxCmTrapStatusEntry 1 }

		
		-- 1.3.6.1.4.1.989.1.16.1.6.2.1.2
		asMaxCmTemperatureStatus OBJECT-TYPE
			SYNTAX INTEGER
				{
				normalTemperature(0),
				lowTempReached(1),
				highTempReached(2),
				abnormalTemperature(3)
				}
			MAX-ACCESS read-only
			STATUS current
			DESCRIPTION
				"Reports current temperature alarm trap status as defined in the value list.
				The status reports overall temperature condition of the system based on the reading 
				from multiple sensors. The status values have the following meaning:
				- normalTemperature: all the sensors in the system show the temparature with normal range
				- lowTempReached: one or more sensors show temperature below the lower limit
				- highTempReached: one or more sensors show the temperature above the higher limit
				- abnormalTemperature: one or more sensors show the temperature outside the normal range (too low or too high)"
			::= { asMaxCmTrapStatusEntry 2 }

		
		-- 1.3.6.1.4.1.989.1.16.1.6.2.1.3
		asMaxCmTemperatureStatusInfo OBJECT-TYPE
			SYNTAX DisplayString
			MAX-ACCESS read-only
			STATUS current
			DESCRIPTION
				"Implementation specific free text description of the trap raised. e.g.
				- Hot/cold sensors=SDR,SCRT0,SCRT1
				- All sensors OK
				More details about the temperature sensors and their readings are reported
				in table asMaxCmTemperatureMonitorTable."
			::= { asMaxCmTrapStatusEntry 3 }

		
		-- 1.3.6.1.4.1.989.1.16.1.6.2.1.4
		asMaxShutdownReasonCode OBJECT-TYPE
			SYNTAX INTEGER
				{
				noShutdown(0),
				reasonManualReset(1),
				reasonUnrecoverableSoftError(2),
				reasonHotBoardProtection(3)
				}
			MAX-ACCESS read-only
			STATUS current
			DESCRIPTION
				"Reports the reason the board (box) executed shut down as defined in the value list."
			::= { asMaxCmTrapStatusEntry 4 }

		
		-- 1.3.6.1.4.1.989.1.16.1.6.2.1.5
		asMaxShutdownReasonInfo OBJECT-TYPE
			SYNTAX DisplayString
			MAX-ACCESS read-only
			STATUS current
			DESCRIPTION
				"Implementation specific free text description of the trap raised. e.g.
				- Manual reset requested from console
				- System overheated"
			::= { asMaxCmTrapStatusEntry 5 }

		
		-- 1.3.6.1.4.1.989.1.16.1.6.2.1.6
		asMaxCmDcVoltageStatus OBJECT-TYPE
			SYNTAX INTEGER
				{
				dcVoltageNominal(0),
				dcVoltageOutOfRange(1)
				}
			MAX-ACCESS read-only
			STATUS current
			DESCRIPTION
				"Reports current DC voltage alarm trap status as defined in the value list.
				The status reports overall DC voltage condition of the system based on the reading 
				from multiple sensors. The status values have the following meaning:
				- dcVoltageNominal: all the sensors in the system show the DC voltage values within acceptable range
				- dcVoltageOutOfRange: one or more sensors show the DC voltage outside the nominal range"
			::= { asMaxCmTrapStatusEntry 6 }

		
		-- 1.3.6.1.4.1.989.1.16.1.6.2.1.7
		asMaxCmDcVoltageStatusInfo OBJECT-TYPE
			SYNTAX DisplayString
			MAX-ACCESS read-only
			STATUS current
			DESCRIPTION
				"Implementation specific free text description of the trap raised. e.g.
				- DC voltage out of range: DPRF-1, PSU-3
				- All sensors OK."
			::= { asMaxCmTrapStatusEntry 7 }

		
		-- 1.3.6.1.4.1.989.1.16.1.6.2.1.8
		asMaxCmSdrMainPllStatus OBJECT-TYPE
			SYNTAX INTEGER
				{
				pllStatusLocked(0),
				pllStatusUnlocked(1)
				}
			MAX-ACCESS read-only
			STATUS current
			DESCRIPTION
				"Description."
			::= { asMaxCmTrapStatusEntry 8 }

		
		-- 1.3.6.1.4.1.989.1.16.1.7
		asMaxCmDcVoltageMonitorTable OBJECT-TYPE
			SYNTAX SEQUENCE OF AsMaxCmDcVoltageMonitorEntry
			MAX-ACCESS not-accessible
			STATUS current
			DESCRIPTION
				"Generic reporting table for all the DC voltage sensors in the system.
				Contains one row for each sensor."
			::= { asMaxCommon 7 }

		
		-- 1.3.6.1.4.1.989.1.16.1.7.1
		asMaxCmDcVoltageMonitorEntry OBJECT-TYPE
			SYNTAX AsMaxCmDcVoltageMonitorEntry
			MAX-ACCESS not-accessible
			STATUS current
			DESCRIPTION
				"Description."
			INDEX { asMaxCmDcVoltageMonItem }
			::= { asMaxCmDcVoltageMonitorTable 1 }

		
		AsMaxCmDcVoltageMonitorEntry ::=
			SEQUENCE { 
				asMaxCmDcVoltageMonItem
					INTEGER,
				asMaxCmDcVoltageMonInventoryItem
					INTEGER,
				asMaxCmDcVoltageMonSensorName
					DisplayString,
				asMaxCmDcVoltageMonValue
					INTEGER,
				asMaxCmDcVoltageMonStatus
					INTEGER
			 }

		-- 1.3.6.1.4.1.989.1.16.1.7.1.1
		asMaxCmDcVoltageMonItem OBJECT-TYPE
			SYNTAX INTEGER (1..255)
			MAX-ACCESS not-accessible
			STATUS current
			DESCRIPTION
				"Arbitrary identifyier of the sensor. Defined solely for the purpose of indexing of the rows in this table.
				Agent should use consecutive numbers starting with 1."
			::= { asMaxCmDcVoltageMonitorEntry 1 }

		
		-- 1.3.6.1.4.1.989.1.16.1.7.1.2
		asMaxCmDcVoltageMonInventoryItem OBJECT-TYPE
			SYNTAX INTEGER (0..65535)
			MAX-ACCESS read-only
			STATUS current
			DESCRIPTION
				"Identifies the device instance the dc voltage sensor is installed on. 
				It is an index to generic inventory table."
			::= { asMaxCmDcVoltageMonitorEntry 2 }

		
		-- 1.3.6.1.4.1.989.1.16.1.7.1.3
		asMaxCmDcVoltageMonSensorName OBJECT-TYPE
			SYNTAX DisplayString
			MAX-ACCESS read-only
			STATUS current
			DESCRIPTION
				"Identifies the dc voltage sensor e.g DPRF-1"
			::= { asMaxCmDcVoltageMonitorEntry 3 }

		
		-- 1.3.6.1.4.1.989.1.16.1.7.1.4
		asMaxCmDcVoltageMonValue OBJECT-TYPE
			SYNTAX INTEGER (0..50000)
			UNITS "mV"
			MAX-ACCESS read-only
			STATUS current
			DESCRIPTION
				"The value of the measured DC voltage The measurement algorithm should filter the small, 
				frequent changes in the voltage read from the sensor. 
				The details of the algorithm are implementation specific."
			DEFVAL { 0 }
			::= { asMaxCmDcVoltageMonitorEntry 4 }

		
		-- 1.3.6.1.4.1.989.1.16.1.7.1.5
		asMaxCmDcVoltageMonStatus OBJECT-TYPE
			SYNTAX INTEGER
				{
				dcVoltageNominal(0),
				dcVoltageTooHigh(1),
				dcVoltageTooLow(2),
				dcVoltageOutOfRange(3)
				}
			MAX-ACCESS read-only
			STATUS current
			DESCRIPTION
				"The object reports the status of the DC voltage tested against some implementation
				specific criteria. This may be used by manager to indicate the voltage out of nominal range."
			::= { asMaxCmDcVoltageMonitorEntry 5 }

		
	
	END

--
-- AIRSPAN-ASMAX-COMMON-MIB.mib
--
