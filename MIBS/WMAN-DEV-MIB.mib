WMAN-DEV-MIB DEFINITIONS ::= BEGIN
    IMPORTS
    MODULE-IDENTITY, OBJECT-TYPE, Integer32
        FROM SNMPv2-SMI
    TEXTUAL-CONVENTION, RowStatus
        FROM SNMPv2-TC
    InetAddressType, InetAddress
        FROM INET-ADDRESS-MIB
    OBJECT-GROUP, MODULE-COMPLIANCE
        FROM SNMPv2-CONF;

    wmanDevMib MODULE-IDENTITY
        LAST-UPDATED        "200508020000Z"
        --August 02, 2005
        ORGANIZATION        "IEEE 802.16"
        CONTACT-INFO        "WG E-mail: stds-802-16@ieee.org  
                            WG Chair: Roger B.
                            Marks
                            Postal: (U.S.) National
                            Institute
                            of Standards and Technology
                            E-mail: r.b.marks@ieee.org
                            TGf Chair: Phillip
                            Barber
                            Postal: Huawei Technoligies
                            Co., Ltd.
                            E-mail: pbarber@futurewei.com
                            Editor: Joey Chou
                            Postal: Intel Corporation
                            5000 W. Chandler Blvd,
                            Chandler, AZ 85227,
                            USA
                            E-mail: joey.chou@intel.com"
        DESCRIPTION         "This material is from IEEE Std 802.16f-2005 Copyright
                            (c) 2005 IEEE. This MIB Module defines device
                            related managed objects for IEEE 802.16-2004
                            based Subscriber Station and Base Station, and
                            is under iso(1).std(0).iso8802(8802).wman(16).wmanDevMib(1)"

        REVISION            "200508020000Z"
        DESCRIPTION         "The first version of WMAN-DEV-MIB module."
        ::= { iso(1) std(0) iso8802(8802) wman(16) 1 }

    --Textual Conventions
    WmanDevEventSeverity ::= TEXTUAL-CONVENTION
        STATUS              current
        DESCRIPTION         "wmanDevEventSeverity defines the alarm Severity
                            of an event."
        SYNTAX              INTEGER {
                                emergency( 1 ),
                                alert( 2 ),
                                critical( 3 ),
                                error( 4 ),
                                warning( 5 ),
                                notice( 6 ),
                                informational( 7 ),
                                debug( 8 )
                            }



    wmanDevMibObjects OBJECT IDENTIFIER ::= { wmanDevMib 1 }

    wmanDevCommonObjects OBJECT IDENTIFIER ::= { wmanDevMibObjects 3 }

    --
    --
    --
    --
    wmanDevCmnSnmpAgent OBJECT IDENTIFIER ::= { wmanDevCommonObjects 2 }

    --
    --
    --
    wmanDevCmnSnmpV1V2TrapDestTable OBJECT-TYPE
        SYNTAX              SEQUENCE OF WmanDevCmnSnmpV1V2TrapDestEntry
        MAX-ACCESS          not-accessible
        STATUS              current
        DESCRIPTION         "This table contains the configuration objects
                            for the device implementing SNMP agent."
        ::= { wmanDevCmnSnmpAgent 1 }

    wmanDevCmnSnmpV1V2TrapDestEntry OBJECT-TYPE
        SYNTAX              WmanDevCmnSnmpV1V2TrapDestEntry
        MAX-ACCESS          not-accessible
        STATUS              current
        DESCRIPTION         "This table is indexed by wmanDevCmnSnmpV1V2TrapDestIndex."
        INDEX               {
                                wmanDevCmnSnmpV1V2TrapDestIndex
                            }
        ::= { wmanDevCmnSnmpV1V2TrapDestTable 1 }

    WmanDevCmnSnmpV1V2TrapDestEntry ::= SEQUENCE {
        wmanDevCmnSnmpV1V2TrapDestIndex
            Integer32,
        wmanDevCmnSnmpV1V2TrapDestIpAddrType
            InetAddressType,
        wmanDevCmnSnmpV1V2TrapDestIpAddr
            InetAddress,
        wmanDevCmnSnmpV1V2TrapDestPort
            Integer32,
        wmanDevCmnSnmpV1V2TrapDestRowStatus
            RowStatus
    }

    wmanDevCmnSnmpV1V2TrapDestIndex OBJECT-TYPE
        SYNTAX              Integer32 (1..8)
        MAX-ACCESS          not-accessible
        STATUS              current
        DESCRIPTION         "The index identifies the trap destination. The
                            number of rows is limited to eight."
        ::= { wmanDevCmnSnmpV1V2TrapDestEntry 1 }

    wmanDevCmnSnmpV1V2TrapDestIpAddrType OBJECT-TYPE
        SYNTAX              InetAddressType
        MAX-ACCESS          read-create
        STATUS              current
        DESCRIPTION         "The type of IP address used in the object wmanDevCmnSnmpV1V2TrapDestV1V2TrapDestIpAddr."
        ::= { wmanDevCmnSnmpV1V2TrapDestEntry 2 }

    wmanDevCmnSnmpV1V2TrapDestIpAddr OBJECT-TYPE
        SYNTAX              InetAddress
        MAX-ACCESS          read-create
        STATUS              current
        DESCRIPTION         "IP address of SNMP manager configured as a trap
                            destination for versions V1 and V2 of SNMP. If
                            this object is not created or empty the traps
                            are not sent."
        ::= { wmanDevCmnSnmpV1V2TrapDestEntry 3 }

    wmanDevCmnSnmpV1V2TrapDestPort OBJECT-TYPE
        SYNTAX              Integer32 (0..65535)
        MAX-ACCESS          read-create
        STATUS              current
        DESCRIPTION         "Port number of SNMP manager configured as a trap
                            destination for versions V1 and V2 of SNMP."
        REFERENCE           "Subclause 11.13.19.3.4.6 in IEEE Std 802.16-2004"
        ::= { wmanDevCmnSnmpV1V2TrapDestEntry 4 }

    wmanDevCmnSnmpV1V2TrapDestRowStatus OBJECT-TYPE
        SYNTAX              RowStatus
        MAX-ACCESS          read-create
        STATUS              current
        DESCRIPTION         "This object is used to ensure that the write operation
                            to multiple columns is guaranteed to be treated
                            as atomic operation by agent."
        ::= { wmanDevCmnSnmpV1V2TrapDestEntry 5 }

    --
    --
    --
    --
    wmanDevCmnDeviceConfig OBJECT IDENTIFIER ::= { wmanDevCommonObjects 3 }

    wmanDevCmnResetDevice OBJECT-TYPE
        SYNTAX              INTEGER {
                                actionResetDeviceNoAction( 0 ),
                                actionResetDevice( 1 )
                            }
        MAX-ACCESS          read-write
        STATUS              current
        DESCRIPTION         "This object should be implemented as follows:
                            - When set to actionsResetDevice value, instructs
                            device to reset itself - When set to value different
                            than actionsResetDevice it should be ignored
                            - When read it should return actionsResetDeviceNoAction"
        ::= { wmanDevCmnDeviceConfig 1 }

    --
    --
    --
    wmanDevMibConformance OBJECT IDENTIFIER ::= { wmanDevMib 2 }

    wmanDevMibGroups OBJECT IDENTIFIER ::= { wmanDevMibConformance 1 }

    wmanDevMibCmnGroup OBJECT-GROUP
        OBJECTS {           
                        wmanDevCmnSnmpV1V2TrapDestIpAddrType,
                        wmanDevCmnSnmpV1V2TrapDestIpAddr,
                        wmanDevCmnSnmpV1V2TrapDestPort,
                        wmanDevCmnSnmpV1V2TrapDestRowStatus,
                        wmanDevCmnResetDevice
                }
        --SNMP agent configuration
        --Events and event notification
        STATUS              current
        DESCRIPTION         "This group contains objects for SS."
        ::= { wmanDevMibGroups 4 }

    wmanDevMibCompliances OBJECT IDENTIFIER ::= { wmanDevMibConformance 2 }

    --compliance statements
    wmanDevMibCompliance MODULE-COMPLIANCE
        STATUS              current
        DESCRIPTION         "The compliance statement for devices that implement
                            Wireless MAN interfaces as defined in IEEE Std
                            802.16-2004."

        MODULE  -- this module
                GROUP               wmanDevMibCmnGroup
        --conditionally mandatory group
                DESCRIPTION         "This group is mandatory for Base Station and Subscriber
                            Station."


        ::= { wmanDevMibCompliances 1 }



END
